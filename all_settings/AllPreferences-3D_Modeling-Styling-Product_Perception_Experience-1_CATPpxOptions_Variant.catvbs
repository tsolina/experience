Language="VBSCRIPT"

Sub CATMain()

Set settingControllers1 = CATIA.SettingControllers

Set settingRepository1 = settingControllers1.Item("CATPpxOptionData_Variant")

boolean1 = settingRepository1.GetAttr("MaterialVariantActivation")
'--------------------------------------------------
' Parameter 1 : (String) "MaterialVariantActivation"
' Returned value : (Variant) (Boolean) True
'--------------------------------------------------

Dim bSTR1
bSTR1 = ""
Dim bSTR2
bSTR2 = ""
Dim boolean2
settingRepository1.GetAttrInfo "MaterialVariantActivation", bSTR1, bSTR2, boolean2
'--------------------------------------------------
' Parameter 1 : (String) "MaterialVariantActivation"
' Parameter 2 : (String) "Default value"
' Parameter 3 : (String) "Unlocked"
' Parameter 4 : (Boolean) False
'--------------------------------------------------

boolean3 = settingRepository1.GetAttr("ViewpointShadingModes")
'--------------------------------------------------
' Parameter 1 : (String) "ViewpointShadingModes"
' Returned value : (Variant) (Boolean) True
'--------------------------------------------------

Dim bSTR3
bSTR3 = ""
Dim bSTR4
bSTR4 = ""
Dim boolean4
settingRepository1.GetAttrInfo "ViewpointShadingModes", bSTR3, bSTR4, boolean4
'--------------------------------------------------
' Parameter 1 : (String) "ViewpointShadingModes"
' Parameter 2 : (String) "Default value"
' Parameter 3 : (String) "Unlocked"
' Parameter 4 : (Boolean) False
'--------------------------------------------------

boolean5 = settingRepository1.GetAttr("ViewpointBloomEffectState")
'--------------------------------------------------
' Parameter 1 : (String) "ViewpointBloomEffectState"
' Returned value : (Variant) (Boolean) True
'--------------------------------------------------

Dim bSTR5
bSTR5 = ""
Dim bSTR6
bSTR6 = ""
Dim boolean6
settingRepository1.GetAttrInfo "ViewpointBloomEffectState", bSTR5, bSTR6, boolean6
'--------------------------------------------------
' Parameter 1 : (String) "ViewpointBloomEffectState"
' Parameter 2 : (String) "Default value"
' Parameter 3 : (String) "Unlocked"
' Parameter 4 : (Boolean) False
'--------------------------------------------------

float1 = settingRepository1.GetAttr("ViewpointBloomEffectValueF")
'--------------------------------------------------
' Parameter 1 : (String) "ViewpointBloomEffectValueF"
' Returned value : (Variant) (Float) 0.220000
'--------------------------------------------------

Dim bSTR7
bSTR7 = ""
Dim bSTR8
bSTR8 = ""
Dim boolean7
settingRepository1.GetAttrInfo "ViewpointBloomEffectValueF", bSTR7, bSTR8, boolean7
'--------------------------------------------------
' Parameter 1 : (String) "ViewpointBloomEffectValueF"
' Parameter 2 : (String) "Default value"
' Parameter 3 : (String) "Unlocked"
' Parameter 4 : (Boolean) False
'--------------------------------------------------

bSTR9 = settingRepository1.GetAttr("Product")
'--------------------------------------------------
' Parameter 1 : (String) "Product"
' Returned value : (Variant) (String) "Capture all 3D"
'--------------------------------------------------

Dim bSTR10
bSTR10 = ""
Dim bSTR11
bSTR11 = ""
Dim boolean8
settingRepository1.GetAttrInfo "Product", bSTR10, bSTR11, boolean8
'--------------------------------------------------
' Parameter 1 : (String) "Product"
' Parameter 2 : (String) "Default value"
' Parameter 3 : (String) "Unlocked"
' Parameter 4 : (Boolean) False
'--------------------------------------------------

boolean9 = settingRepository1.GetAttr("ProductEnvironment")
'--------------------------------------------------
' Parameter 1 : (String) "ProductEnvironment"
' Returned value : (Variant) (Boolean) False
'--------------------------------------------------

Dim bSTR12
bSTR12 = ""
Dim bSTR13
bSTR13 = ""
Dim boolean10
settingRepository1.GetAttrInfo "ProductEnvironment", bSTR12, bSTR13, boolean10
'--------------------------------------------------
' Parameter 1 : (String) "ProductEnvironment"
' Parameter 2 : (String) "Default value"
' Parameter 3 : (String) "Unlocked"
' Parameter 4 : (Boolean) False
'--------------------------------------------------

bSTR14 = settingRepository1.GetAttr("Position")
'--------------------------------------------------
' Parameter 1 : (String) "Position"
' Returned value : (Variant) (String) "Capture all 3D"
'--------------------------------------------------

Dim bSTR15
bSTR15 = ""
Dim bSTR16
bSTR16 = ""
Dim boolean11
settingRepository1.GetAttrInfo "Position", bSTR15, bSTR16, boolean11
'--------------------------------------------------
' Parameter 1 : (String) "Position"
' Parameter 2 : (String) "Default value"
' Parameter 3 : (String) "Unlocked"
' Parameter 4 : (Boolean) False
'--------------------------------------------------

boolean12 = settingRepository1.GetAttr("PositionEnvironment")
'--------------------------------------------------
' Parameter 1 : (String) "PositionEnvironment"
' Returned value : (Variant) (Boolean) False
'--------------------------------------------------

Dim bSTR17
bSTR17 = ""
Dim bSTR18
bSTR18 = ""
Dim boolean13
settingRepository1.GetAttrInfo "PositionEnvironment", bSTR17, bSTR18, boolean13
'--------------------------------------------------
' Parameter 1 : (String) "PositionEnvironment"
' Parameter 2 : (String) "Default value"
' Parameter 3 : (String) "Unlocked"
' Parameter 4 : (Boolean) False
'--------------------------------------------------

bSTR19 = settingRepository1.GetAttr("Material")
'--------------------------------------------------
' Parameter 1 : (String) "Material"
' Returned value : (Variant) (String) "Capture all 3D"
'--------------------------------------------------

Dim bSTR20
bSTR20 = ""
Dim bSTR21
bSTR21 = ""
Dim boolean14
settingRepository1.GetAttrInfo "Material", bSTR20, bSTR21, boolean14
'--------------------------------------------------
' Parameter 1 : (String) "Material"
' Parameter 2 : (String) "Default value"
' Parameter 3 : (String) "Unlocked"
' Parameter 4 : (Boolean) False
'--------------------------------------------------

boolean15 = settingRepository1.GetAttr("MaterialEnvironment")
'--------------------------------------------------
' Parameter 1 : (String) "MaterialEnvironment"
' Returned value : (Variant) (Boolean) False
'--------------------------------------------------

Dim bSTR22
bSTR22 = ""
Dim bSTR23
bSTR23 = ""
Dim boolean16
settingRepository1.GetAttrInfo "MaterialEnvironment", bSTR22, bSTR23, boolean16
'--------------------------------------------------
' Parameter 1 : (String) "MaterialEnvironment"
' Parameter 2 : (String) "Default value"
' Parameter 3 : (String) "Unlocked"
' Parameter 4 : (Boolean) False
'--------------------------------------------------

bSTR24 = settingRepository1.GetAttr("Human")
'--------------------------------------------------
' Parameter 1 : (String) "Human"
' Returned value : (Variant) (String) "Capture all 3D"
'--------------------------------------------------

Dim bSTR25
bSTR25 = ""
Dim bSTR26
bSTR26 = ""
Dim boolean17
settingRepository1.GetAttrInfo "Human", bSTR25, bSTR26, boolean17
'--------------------------------------------------
' Parameter 1 : (String) "Human"
' Parameter 2 : (String) "Default value"
' Parameter 3 : (String) "Unlocked"
' Parameter 4 : (Boolean) False
'--------------------------------------------------

boolean18 = settingRepository1.GetAttr("HumanEnvironment")
'--------------------------------------------------
' Parameter 1 : (String) "HumanEnvironment"
' Returned value : (Variant) (Boolean) False
'--------------------------------------------------

Dim bSTR27
bSTR27 = ""
Dim bSTR28
bSTR28 = ""
Dim boolean19
settingRepository1.GetAttrInfo "HumanEnvironment", bSTR27, bSTR28, boolean19
'--------------------------------------------------
' Parameter 1 : (String) "HumanEnvironment"
' Parameter 2 : (String) "Default value"
' Parameter 3 : (String) "Unlocked"
' Parameter 4 : (Boolean) False
'--------------------------------------------------

bSTR29 = settingRepository1.GetAttr("Simulation")
'--------------------------------------------------
' Parameter 1 : (String) "Simulation"
' Returned value : (Variant) (String) "Capture all 3D"
'--------------------------------------------------

Dim bSTR30
bSTR30 = ""
Dim bSTR31
bSTR31 = ""
Dim boolean20
settingRepository1.GetAttrInfo "Simulation", bSTR30, bSTR31, boolean20
'--------------------------------------------------
' Parameter 1 : (String) "Simulation"
' Parameter 2 : (String) "Default value"
' Parameter 3 : (String) "Unlocked"
' Parameter 4 : (Boolean) False
'--------------------------------------------------

boolean21 = settingRepository1.GetAttr("SimulationEnvironment")
'--------------------------------------------------
' Parameter 1 : (String) "SimulationEnvironment"
' Returned value : (Variant) (Boolean) False
'--------------------------------------------------

Dim bSTR32
bSTR32 = ""
Dim bSTR33
bSTR33 = ""
Dim boolean22
settingRepository1.GetAttrInfo "SimulationEnvironment", bSTR32, bSTR33, boolean22
'--------------------------------------------------
' Parameter 1 : (String) "SimulationEnvironment"
' Parameter 2 : (String) "Default value"
' Parameter 3 : (String) "Unlocked"
' Parameter 4 : (Boolean) False
'--------------------------------------------------

boolean23 = settingRepository1.GetAttr("ViewpointEnvironment")
'--------------------------------------------------
' Parameter 1 : (String) "ViewpointEnvironment"
' Returned value : (Variant) (Boolean) False
'--------------------------------------------------

Dim bSTR34
bSTR34 = ""
Dim bSTR35
bSTR35 = ""
Dim boolean24
settingRepository1.GetAttrInfo "ViewpointEnvironment", bSTR34, bSTR35, boolean24
'--------------------------------------------------
' Parameter 1 : (String) "ViewpointEnvironment"
' Parameter 2 : (String) "Default value"
' Parameter 3 : (String) "Unlocked"
' Parameter 4 : (Boolean) False
'--------------------------------------------------

bSTR36 = settingRepository1.GetAttr("Environment")
'--------------------------------------------------
' Parameter 1 : (String) "Environment"
' Returned value : (Variant) (String) "Capture all 3D + environment"
'--------------------------------------------------

Dim bSTR37
bSTR37 = ""
Dim bSTR38
bSTR38 = ""
Dim boolean25
settingRepository1.GetAttrInfo "Environment", bSTR37, bSTR38, boolean25
'--------------------------------------------------
' Parameter 1 : (String) "Environment"
' Parameter 2 : (String) "Default value"
' Parameter 3 : (String) "Unlocked"
' Parameter 4 : (Boolean) False
'--------------------------------------------------

boolean26 = settingRepository1.GetAttr("StageEnvironment")
'--------------------------------------------------
' Parameter 1 : (String) "StageEnvironment"
' Returned value : (Variant) (Boolean) False
'--------------------------------------------------

Dim bSTR39
bSTR39 = ""
Dim bSTR40
bSTR40 = ""
Dim boolean27
settingRepository1.GetAttrInfo "StageEnvironment", bSTR39, bSTR40, boolean27
'--------------------------------------------------
' Parameter 1 : (String) "StageEnvironment"
' Parameter 2 : (String) "Default value"
' Parameter 3 : (String) "Unlocked"
' Parameter 4 : (Boolean) False
'--------------------------------------------------

End Sub
