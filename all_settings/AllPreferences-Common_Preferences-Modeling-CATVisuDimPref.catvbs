Language="VBSCRIPT"

Sub CATMain()

Set settingControllers1 = CATIA.SettingControllers

Set settingRepository1 = settingControllers1.Item("ConstraintModeler")

Dim arrayOfVariantOfLong1
arrayOfVariantOfLong1 = settingRepository1.GetAttrArray("ResolvedConstraintColor")
'--------------------------------------------------
' Parameter 1 : (String) "ResolvedConstraintColor"
' Returned value : (Array) 
'    Array[0] : (Variant) (Long) 0
'    Array[1] : (Variant) (Long) 0
'    Array[2] : (Variant) (Long) 0
'--------------------------------------------------

Dim bSTR1
bSTR1 = ""
Dim bSTR2
bSTR2 = ""
Dim boolean1
settingRepository1.GetAttrInfo "ResolvedConstraintColor", bSTR1, bSTR2, boolean1
'--------------------------------------------------
' Parameter 1 : (String) "ResolvedConstraintColor"
' Parameter 2 : (String) "Default value"
' Parameter 3 : (String) "Unlocked"
' Parameter 4 : (Boolean) False
'--------------------------------------------------

Dim arrayOfVariantOfLong2
arrayOfVariantOfLong2 = settingRepository1.GetAttrArray("UnresolvedConstraintColor")
'--------------------------------------------------
' Parameter 1 : (String) "UnresolvedConstraintColor"
' Returned value : (Array) 
'    Array[0] : (Variant) (Long) 204
'    Array[1] : (Variant) (Long) 9
'    Array[2] : (Variant) (Long) 47
'--------------------------------------------------

Dim bSTR3
bSTR3 = ""
Dim bSTR4
bSTR4 = ""
Dim boolean2
settingRepository1.GetAttrInfo "UnresolvedConstraintColor", bSTR3, bSTR4, boolean2
'--------------------------------------------------
' Parameter 1 : (String) "UnresolvedConstraintColor"
' Parameter 2 : (String) "Default value"
' Parameter 3 : (String) "Unlocked"
' Parameter 4 : (Boolean) False
'--------------------------------------------------

Dim arrayOfVariantOfLong3
arrayOfVariantOfLong3 = settingRepository1.GetAttrArray("OverConstraintColor")
'--------------------------------------------------
' Parameter 1 : (String) "OverConstraintColor"
' Returned value : (Array) 
'    Array[0] : (Variant) (Long) 155
'    Array[1] : (Variant) (Long) 44
'    Array[2] : (Variant) (Long) 152
'--------------------------------------------------

Dim bSTR5
bSTR5 = ""
Dim bSTR6
bSTR6 = ""
Dim boolean3
settingRepository1.GetAttrInfo "OverConstraintColor", bSTR5, bSTR6, boolean3
'--------------------------------------------------
' Parameter 1 : (String) "OverConstraintColor"
' Parameter 2 : (String) "Default value"
' Parameter 3 : (String) "Unlocked"
' Parameter 4 : (Boolean) False
'--------------------------------------------------

Dim arrayOfVariantOfLong4
arrayOfVariantOfLong4 = settingRepository1.GetAttrArray("InvalidGeometryColor")
'--------------------------------------------------
' Parameter 1 : (String) "InvalidGeometryColor"
' Returned value : (Array) 
'    Array[0] : (Variant) (Long) 255
'    Array[1] : (Variant) (Long) 138
'    Array[2] : (Variant) (Long) 46
'--------------------------------------------------

Dim bSTR7
bSTR7 = ""
Dim bSTR8
bSTR8 = ""
Dim boolean4
settingRepository1.GetAttrInfo "InvalidGeometryColor", bSTR7, bSTR8, boolean4
'--------------------------------------------------
' Parameter 1 : (String) "InvalidGeometryColor"
' Parameter 2 : (String) "Default value"
' Parameter 3 : (String) "Unlocked"
' Parameter 4 : (Boolean) False
'--------------------------------------------------

long1 = settingRepository1.GetAttr("ShowColorStatus")
'--------------------------------------------------
' Parameter 1 : (String) "ShowColorStatus"
' Returned value : (Variant) (Long) 0
'--------------------------------------------------

Dim bSTR9
bSTR9 = ""
Dim bSTR10
bSTR10 = ""
Dim boolean5
settingRepository1.GetAttrInfo "ShowColorStatus", bSTR9, bSTR10, boolean5
'--------------------------------------------------
' Parameter 1 : (String) "ShowColorStatus"
' Parameter 2 : (String) "Default value"
' Parameter 3 : (String) "Unlocked"
' Parameter 4 : (Boolean) False
'--------------------------------------------------

double1 = settingRepository1.GetAttr("ViewAngle")
'--------------------------------------------------
' Parameter 1 : (String) "ViewAngle"
' Returned value : (Variant) (Double) 1.000000
'--------------------------------------------------

Dim bSTR11
bSTR11 = ""
Dim bSTR12
bSTR12 = ""
Dim boolean6
settingRepository1.GetAttrInfo "ViewAngle", bSTR11, bSTR12, boolean6
'--------------------------------------------------
' Parameter 1 : (String) "ViewAngle"
' Parameter 2 : (String) "Default value"
' Parameter 3 : (String) "Unlocked"
' Parameter 4 : (Boolean) False
'--------------------------------------------------

long2 = settingRepository1.GetAttr("DisplayMode")
'--------------------------------------------------
' Parameter 1 : (String) "DisplayMode"
' Returned value : (Variant) (Long) 0
'--------------------------------------------------

Dim bSTR13
bSTR13 = ""
Dim bSTR14
bSTR14 = ""
Dim boolean7
settingRepository1.GetAttrInfo "DisplayMode", bSTR13, bSTR14, boolean7
'--------------------------------------------------
' Parameter 1 : (String) "DisplayMode"
' Parameter 2 : (String) "Default value"
' Parameter 3 : (String) "Unlocked"
' Parameter 4 : (Boolean) False
'--------------------------------------------------

long3 = settingRepository1.GetAttr("Scale")
'--------------------------------------------------
' Parameter 1 : (String) "Scale"
' Returned value : (Variant) (Long) 1
'--------------------------------------------------

Dim bSTR15
bSTR15 = ""
Dim bSTR16
bSTR16 = ""
Dim boolean8
settingRepository1.GetAttrInfo "Scale", bSTR15, bSTR16, boolean8
'--------------------------------------------------
' Parameter 1 : (String) "Scale"
' Parameter 2 : (String) "Default value"
' Parameter 3 : (String) "Unlocked"
' Parameter 4 : (Boolean) False
'--------------------------------------------------

long4 = settingRepository1.GetAttr("DisplayIconifiedElements")
'--------------------------------------------------
' Parameter 1 : (String) "DisplayIconifiedElements"
' Returned value : (Variant) (Long) 1
'--------------------------------------------------

Dim bSTR17
bSTR17 = ""
Dim bSTR18
bSTR18 = ""
Dim boolean9
settingRepository1.GetAttrInfo "DisplayIconifiedElements", bSTR17, bSTR18, boolean9
'--------------------------------------------------
' Parameter 1 : (String) "DisplayIconifiedElements"
' Parameter 2 : (String) "Default value"
' Parameter 3 : (String) "Unlocked"
' Parameter 4 : (Boolean) False
'--------------------------------------------------

long5 = settingRepository1.GetAttr("HighlightElements")
'--------------------------------------------------
' Parameter 1 : (String) "HighlightElements"
' Returned value : (Variant) (Long) 1
'--------------------------------------------------

Dim bSTR19
bSTR19 = ""
Dim bSTR20
bSTR20 = ""
Dim boolean10
settingRepository1.GetAttrInfo "HighlightElements", bSTR19, bSTR20, boolean10
'--------------------------------------------------
' Parameter 1 : (String) "HighlightElements"
' Parameter 2 : (String) "Default value"
' Parameter 3 : (String) "Unlocked"
' Parameter 4 : (Boolean) False
'--------------------------------------------------

double2 = settingRepository1.GetAttr("Gap")
'--------------------------------------------------
' Parameter 1 : (String) "Gap"
' Returned value : (Variant) (Double) 2.000000
'--------------------------------------------------

Dim bSTR21
bSTR21 = ""
Dim bSTR22
bSTR22 = ""
Dim boolean11
settingRepository1.GetAttrInfo "Gap", bSTR21, bSTR22, boolean11
'--------------------------------------------------
' Parameter 1 : (String) "Gap"
' Parameter 2 : (String) "Default value"
' Parameter 3 : (String) "Unlocked"
' Parameter 4 : (Boolean) False
'--------------------------------------------------

double3 = settingRepository1.GetAttr("OverRun")
'--------------------------------------------------
' Parameter 1 : (String) "OverRun"
' Returned value : (Variant) (Double) 2.000000
'--------------------------------------------------

Dim bSTR23
bSTR23 = ""
Dim bSTR24
bSTR24 = ""
Dim boolean12
settingRepository1.GetAttrInfo "OverRun", bSTR23, bSTR24, boolean12
'--------------------------------------------------
' Parameter 1 : (String) "OverRun"
' Parameter 2 : (String) "Default value"
' Parameter 3 : (String) "Unlocked"
' Parameter 4 : (Boolean) False
'--------------------------------------------------

long6 = settingRepository1.GetAttr("FilterMode")
'--------------------------------------------------
' Parameter 1 : (String) "FilterMode"
' Returned value : (Variant) (Long) 1
'--------------------------------------------------

Dim bSTR25
bSTR25 = ""
Dim bSTR26
bSTR26 = ""
Dim boolean13
settingRepository1.GetAttrInfo "FilterMode", bSTR25, bSTR26, boolean13
'--------------------------------------------------
' Parameter 1 : (String) "FilterMode"
' Parameter 2 : (String) "Default value"
' Parameter 3 : (String) "Unlocked"
' Parameter 4 : (Boolean) False
'--------------------------------------------------

long7 = settingRepository1.GetAttr("StatusFilterMode")
'--------------------------------------------------
' Parameter 1 : (String) "StatusFilterMode"
' Returned value : (Variant) (Long) 0
'--------------------------------------------------

Dim bSTR27
bSTR27 = ""
Dim bSTR28
bSTR28 = ""
Dim boolean14
settingRepository1.GetAttrInfo "StatusFilterMode", bSTR27, bSTR28, boolean14
'--------------------------------------------------
' Parameter 1 : (String) "StatusFilterMode"
' Parameter 2 : (String) "Default value"
' Parameter 3 : (String) "Unlocked"
' Parameter 4 : (Boolean) False
'--------------------------------------------------

long8 = settingRepository1.GetAttr("Filter_Dimensions")
'--------------------------------------------------
' Parameter 1 : (String) "Filter_Dimensions"
' Returned value : (Variant) (Long) 1
'--------------------------------------------------

Dim bSTR29
bSTR29 = ""
Dim bSTR30
bSTR30 = ""
Dim boolean15
settingRepository1.GetAttrInfo "Filter_Dimensions", bSTR29, bSTR30, boolean15
'--------------------------------------------------
' Parameter 1 : (String) "Filter_Dimensions"
' Parameter 2 : (String) "Default value"
' Parameter 3 : (String) "Unlocked"
' Parameter 4 : (Boolean) False
'--------------------------------------------------

long9 = settingRepository1.GetAttr("Filter_Angle")
'--------------------------------------------------
' Parameter 1 : (String) "Filter_Angle"
' Returned value : (Variant) (Long) 1
'--------------------------------------------------

Dim bSTR31
bSTR31 = ""
Dim bSTR32
bSTR32 = ""
Dim boolean16
settingRepository1.GetAttrInfo "Filter_Angle", bSTR31, bSTR32, boolean16
'--------------------------------------------------
' Parameter 1 : (String) "Filter_Angle"
' Parameter 2 : (String) "Default value"
' Parameter 3 : (String) "Unlocked"
' Parameter 4 : (Boolean) False
'--------------------------------------------------

long10 = settingRepository1.GetAttr("Filter_FixedAngle")
'--------------------------------------------------
' Parameter 1 : (String) "Filter_FixedAngle"
' Returned value : (Variant) (Long) 1
'--------------------------------------------------

Dim bSTR33
bSTR33 = ""
Dim bSTR34
bSTR34 = ""
Dim boolean17
settingRepository1.GetAttrInfo "Filter_FixedAngle", bSTR33, bSTR34, boolean17
'--------------------------------------------------
' Parameter 1 : (String) "Filter_FixedAngle"
' Parameter 2 : (String) "Default value"
' Parameter 3 : (String) "Unlocked"
' Parameter 4 : (Boolean) False
'--------------------------------------------------

long11 = settingRepository1.GetAttr("Filter_Tangency")
'--------------------------------------------------
' Parameter 1 : (String) "Filter_Tangency"
' Returned value : (Variant) (Long) 1
'--------------------------------------------------

Dim bSTR35
bSTR35 = ""
Dim bSTR36
bSTR36 = ""
Dim boolean18
settingRepository1.GetAttrInfo "Filter_Tangency", bSTR35, bSTR36, boolean18
'--------------------------------------------------
' Parameter 1 : (String) "Filter_Tangency"
' Parameter 2 : (String) "Default value"
' Parameter 3 : (String) "Unlocked"
' Parameter 4 : (Boolean) False
'--------------------------------------------------

long12 = settingRepository1.GetAttr("Filter_Coincidence")
'--------------------------------------------------
' Parameter 1 : (String) "Filter_Coincidence"
' Returned value : (Variant) (Long) 1
'--------------------------------------------------

Dim bSTR37
bSTR37 = ""
Dim bSTR38
bSTR38 = ""
Dim boolean19
settingRepository1.GetAttrInfo "Filter_Coincidence", bSTR37, bSTR38, boolean19
'--------------------------------------------------
' Parameter 1 : (String) "Filter_Coincidence"
' Parameter 2 : (String) "Default value"
' Parameter 3 : (String) "Unlocked"
' Parameter 4 : (Boolean) False
'--------------------------------------------------

long13 = settingRepository1.GetAttr("Filter_Equality")
'--------------------------------------------------
' Parameter 1 : (String) "Filter_Equality"
' Returned value : (Variant) (Long) 1
'--------------------------------------------------

Dim bSTR39
bSTR39 = ""
Dim bSTR40
bSTR40 = ""
Dim boolean20
settingRepository1.GetAttrInfo "Filter_Equality", bSTR39, bSTR40, boolean20
'--------------------------------------------------
' Parameter 1 : (String) "Filter_Equality"
' Parameter 2 : (String) "Default value"
' Parameter 3 : (String) "Unlocked"
' Parameter 4 : (Boolean) False
'--------------------------------------------------

long14 = settingRepository1.GetAttr("Filter_Fixity")
'--------------------------------------------------
' Parameter 1 : (String) "Filter_Fixity"
' Returned value : (Variant) (Long) 1
'--------------------------------------------------

Dim bSTR41
bSTR41 = ""
Dim bSTR42
bSTR42 = ""
Dim boolean21
settingRepository1.GetAttrInfo "Filter_Fixity", bSTR41, bSTR42, boolean21
'--------------------------------------------------
' Parameter 1 : (String) "Filter_Fixity"
' Parameter 2 : (String) "Default value"
' Parameter 3 : (String) "Unlocked"
' Parameter 4 : (Boolean) False
'--------------------------------------------------

long15 = settingRepository1.GetAttr("Filter_Concentricity")
'--------------------------------------------------
' Parameter 1 : (String) "Filter_Concentricity"
' Returned value : (Variant) (Long) 1
'--------------------------------------------------

Dim bSTR43
bSTR43 = ""
Dim bSTR44
bSTR44 = ""
Dim boolean22
settingRepository1.GetAttrInfo "Filter_Concentricity", bSTR43, bSTR44, boolean22
'--------------------------------------------------
' Parameter 1 : (String) "Filter_Concentricity"
' Parameter 2 : (String) "Default value"
' Parameter 3 : (String) "Unlocked"
' Parameter 4 : (Boolean) False
'--------------------------------------------------

long16 = settingRepository1.GetAttr("Filter_Chamfer")
'--------------------------------------------------
' Parameter 1 : (String) "Filter_Chamfer"
' Returned value : (Variant) (Long) 1
'--------------------------------------------------

Dim bSTR45
bSTR45 = ""
Dim bSTR46
bSTR46 = ""
Dim boolean23
settingRepository1.GetAttrInfo "Filter_Chamfer", bSTR45, bSTR46, boolean23
'--------------------------------------------------
' Parameter 1 : (String) "Filter_Chamfer"
' Parameter 2 : (String) "Default value"
' Parameter 3 : (String) "Unlocked"
' Parameter 4 : (Boolean) False
'--------------------------------------------------

long17 = settingRepository1.GetAttr("Filter_Driven")
'--------------------------------------------------
' Parameter 1 : (String) "Filter_Driven"
' Returned value : (Variant) (Long) 1
'--------------------------------------------------

Dim bSTR47
bSTR47 = ""
Dim bSTR48
bSTR48 = ""
Dim boolean24
settingRepository1.GetAttrInfo "Filter_Driven", bSTR47, bSTR48, boolean24
'--------------------------------------------------
' Parameter 1 : (String) "Filter_Driven"
' Parameter 2 : (String) "Default value"
' Parameter 3 : (String) "Unlocked"
' Parameter 4 : (Boolean) False
'--------------------------------------------------

long18 = settingRepository1.GetAttr("Filter_Driving")
'--------------------------------------------------
' Parameter 1 : (String) "Filter_Driving"
' Returned value : (Variant) (Long) 1
'--------------------------------------------------

Dim bSTR49
bSTR49 = ""
Dim bSTR50
bSTR50 = ""
Dim boolean25
settingRepository1.GetAttrInfo "Filter_Driving", bSTR49, bSTR50, boolean25
'--------------------------------------------------
' Parameter 1 : (String) "Filter_Driving"
' Parameter 2 : (String) "Default value"
' Parameter 3 : (String) "Unlocked"
' Parameter 4 : (Boolean) False
'--------------------------------------------------

End Sub
