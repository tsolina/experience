Language="VBSCRIPT"

Sub CATMain()

Set settingControllers1 = CATIA.SettingControllers

Set settingRepository1 = settingControllers1.Item("GeolocationSettings")

bSTR1 = settingRepository1.GetAttr("Ceg_Geolocation_UrlLocate")
'--------------------------------------------------
' Parameter 1 : (String) "Ceg_Geolocation_UrlLocate"
' Returned value : (Variant) (String) "https://maps.google.com/maps?q=##Longitude##,##Latitude##&z=15"
'--------------------------------------------------

Dim bSTR2
bSTR2 = ""
Dim bSTR3
bSTR3 = ""
Dim boolean1
settingRepository1.GetAttrInfo "Ceg_Geolocation_UrlLocate", bSTR2, bSTR3, boolean1
'--------------------------------------------------
' Parameter 1 : (String) "Ceg_Geolocation_UrlLocate"
' Parameter 2 : (String) "Default value"
' Parameter 3 : (String) "Unlocked"
' Parameter 4 : (Boolean) False
'--------------------------------------------------

End Sub
