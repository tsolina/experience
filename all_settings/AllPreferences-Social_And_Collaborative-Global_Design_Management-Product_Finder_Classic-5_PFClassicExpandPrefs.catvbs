Language="VBSCRIPT"

Sub CATMain()

Set settingControllers1 = CATIA.SettingControllers

Set settingRepository1 = settingControllers1.Item("VPMNavigator")

long1 = settingRepository1.GetAttr("BeadFastenerLoading")
'--------------------------------------------------
' Parameter 1 : (String) "BeadFastenerLoading"
' Returned value : (Variant) (Long) 1
'--------------------------------------------------

Dim bSTR1
bSTR1 = ""
Dim bSTR2
bSTR2 = ""
Dim boolean1
settingRepository1.GetAttrInfo "BeadFastenerLoading", bSTR1, bSTR2, boolean1
'--------------------------------------------------
' Parameter 1 : (String) "BeadFastenerLoading"
' Parameter 2 : (String) "Default value"
' Parameter 3 : (String) "Unlocked"
' Parameter 4 : (Boolean) False
'--------------------------------------------------

long2 = settingRepository1.GetAttr("SpotFastenerLoading")
'--------------------------------------------------
' Parameter 1 : (String) "SpotFastenerLoading"
' Returned value : (Variant) (Long) 1
'--------------------------------------------------

Dim bSTR3
bSTR3 = ""
Dim bSTR4
bSTR4 = ""
Dim boolean2
settingRepository1.GetAttrInfo "SpotFastenerLoading", bSTR3, bSTR4, boolean2
'--------------------------------------------------
' Parameter 1 : (String) "SpotFastenerLoading"
' Parameter 2 : (String) "Default value"
' Parameter 3 : (String) "Unlocked"
' Parameter 4 : (Boolean) False
'--------------------------------------------------

long3 = settingRepository1.GetAttr("LocFastenerLoading")
'--------------------------------------------------
' Parameter 1 : (String) "LocFastenerLoading"
' Returned value : (Variant) (Long) 1
'--------------------------------------------------

Dim bSTR5
bSTR5 = ""
Dim bSTR6
bSTR6 = ""
Dim boolean3
settingRepository1.GetAttrInfo "LocFastenerLoading", bSTR5, bSTR6, boolean3
'--------------------------------------------------
' Parameter 1 : (String) "LocFastenerLoading"
' Parameter 2 : (String) "Default value"
' Parameter 3 : (String) "Unlocked"
' Parameter 4 : (Boolean) False
'--------------------------------------------------

long4 = settingRepository1.GetAttr("BundleFastenerLoading")
'--------------------------------------------------
' Parameter 1 : (String) "BundleFastenerLoading"
' Returned value : (Variant) (Long) 1
'--------------------------------------------------

Dim bSTR7
bSTR7 = ""
Dim bSTR8
bSTR8 = ""
Dim boolean4
settingRepository1.GetAttrInfo "BundleFastenerLoading", bSTR7, bSTR8, boolean4
'--------------------------------------------------
' Parameter 1 : (String) "BundleFastenerLoading"
' Parameter 2 : (String) "Default value"
' Parameter 3 : (String) "Unlocked"
' Parameter 4 : (Boolean) False
'--------------------------------------------------

long5 = settingRepository1.GetAttr("UseExpandAccelerator")
'--------------------------------------------------
' Parameter 1 : (String) "UseExpandAccelerator"
' Returned value : (Variant) (Long) 1
'--------------------------------------------------

Dim bSTR9
bSTR9 = ""
Dim bSTR10
bSTR10 = ""
Dim boolean5
settingRepository1.GetAttrInfo "UseExpandAccelerator", bSTR9, bSTR10, boolean5
'--------------------------------------------------
' Parameter 1 : (String) "UseExpandAccelerator"
' Parameter 2 : (String) "Default value"
' Parameter 3 : (String) "Unlocked"
' Parameter 4 : (Boolean) False
'--------------------------------------------------

End Sub
