Language="VBSCRIPT"

Sub CATMain()

Set settingControllers1 = CATIA.SettingControllers

Set settingRepository1 = settingControllers1.Item("4DNavigator")

uLong1 = settingRepository1.GetAttr("DMUGroundDisplayMode")
'--------------------------------------------------
' Parameter 1 : (String) "DMUGroundDisplayMode"
' Returned value : (Variant) (Unsigned Long) 0
'--------------------------------------------------

Dim bSTR1
bSTR1 = ""
Dim bSTR2
bSTR2 = ""
Dim boolean1
settingRepository1.GetAttrInfo "DMUGroundDisplayMode", bSTR1, bSTR2, boolean1
'--------------------------------------------------
' Parameter 1 : (String) "DMUGroundDisplayMode"
' Parameter 2 : (String) "Default value"
' Parameter 3 : (String) "Unlocked"
' Parameter 4 : (Boolean) False
'--------------------------------------------------

uLong2 = settingRepository1.GetAttr("DMUGroundDisplayLabels")
'--------------------------------------------------
' Parameter 1 : (String) "DMUGroundDisplayLabels"
' Returned value : (Variant) (Unsigned Long) 1
'--------------------------------------------------

Dim bSTR3
bSTR3 = ""
Dim bSTR4
bSTR4 = ""
Dim boolean2
settingRepository1.GetAttrInfo "DMUGroundDisplayLabels", bSTR3, bSTR4, boolean2
'--------------------------------------------------
' Parameter 1 : (String) "DMUGroundDisplayLabels"
' Parameter 2 : (String) "Default value"
' Parameter 3 : (String) "Unlocked"
' Parameter 4 : (Boolean) False
'--------------------------------------------------

uLong3 = settingRepository1.GetAttr("DMUGroundDisplayShadingStatus")
'--------------------------------------------------
' Parameter 1 : (String) "DMUGroundDisplayShadingStatus"
' Returned value : (Variant) (Unsigned Long) 0
'--------------------------------------------------

Dim bSTR5
bSTR5 = ""
Dim bSTR6
bSTR6 = ""
Dim boolean3
settingRepository1.GetAttrInfo "DMUGroundDisplayShadingStatus", bSTR5, bSTR6, boolean3
'--------------------------------------------------
' Parameter 1 : (String) "DMUGroundDisplayShadingStatus"
' Parameter 2 : (String) "Default value"
' Parameter 3 : (String) "Unlocked"
' Parameter 4 : (Boolean) False
'--------------------------------------------------

float1 = settingRepository1.GetAttr("DMUGroundDistanceBetweenFirstDirectionCurves")
'--------------------------------------------------
' Parameter 1 : (String) "DMUGroundDistanceBetweenFirstDirectionCurves"
' Returned value : (Variant) (Float) 10.000000
'--------------------------------------------------

Dim bSTR7
bSTR7 = ""
Dim bSTR8
bSTR8 = ""
Dim boolean4
settingRepository1.GetAttrInfo "DMUGroundDistanceBetweenFirstDirectionCurves", bSTR7, bSTR8, boolean4
'--------------------------------------------------
' Parameter 1 : (String) "DMUGroundDistanceBetweenFirstDirectionCurves"
' Parameter 2 : (String) "Default value"
' Parameter 3 : (String) "Unlocked"
' Parameter 4 : (Boolean) False
'--------------------------------------------------

float2 = settingRepository1.GetAttr("DMUGroundDistanceBetweenSecondDirectionCurves")
'--------------------------------------------------
' Parameter 1 : (String) "DMUGroundDistanceBetweenSecondDirectionCurves"
' Returned value : (Variant) (Float) 10.000000
'--------------------------------------------------

Dim bSTR9
bSTR9 = ""
Dim bSTR10
bSTR10 = ""
Dim boolean5
settingRepository1.GetAttrInfo "DMUGroundDistanceBetweenSecondDirectionCurves", bSTR9, bSTR10, boolean5
'--------------------------------------------------
' Parameter 1 : (String) "DMUGroundDistanceBetweenSecondDirectionCurves"
' Parameter 2 : (String) "Default value"
' Parameter 3 : (String) "Unlocked"
' Parameter 4 : (Boolean) False
'--------------------------------------------------

Dim arrayOfVariantOfULong1
arrayOfVariantOfULong1 = settingRepository1.GetAttrArray("DMUGroundColorOfFirstDirectionCurves")
'--------------------------------------------------
' Parameter 1 : (String) "DMUGroundColorOfFirstDirectionCurves"
' Returned value : (Array) 
'    Array[0] : (Variant) (Unsigned Long) 255
'    Array[1] : (Variant) (Unsigned Long) 255
'    Array[2] : (Variant) (Unsigned Long) 255
'--------------------------------------------------

Dim bSTR11
bSTR11 = ""
Dim bSTR12
bSTR12 = ""
Dim boolean6
settingRepository1.GetAttrInfo "DMUGroundColorOfFirstDirectionCurves", bSTR11, bSTR12, boolean6
'--------------------------------------------------
' Parameter 1 : (String) "DMUGroundColorOfFirstDirectionCurves"
' Parameter 2 : (String) "Default value"
' Parameter 3 : (String) "Unlocked"
' Parameter 4 : (Boolean) False
'--------------------------------------------------

Dim arrayOfVariantOfULong2
arrayOfVariantOfULong2 = settingRepository1.GetAttrArray("DMUGroundColorOfSecondDirectionCurves")
'--------------------------------------------------
' Parameter 1 : (String) "DMUGroundColorOfSecondDirectionCurves"
' Returned value : (Array) 
'    Array[0] : (Variant) (Unsigned Long) 255
'    Array[1] : (Variant) (Unsigned Long) 255
'    Array[2] : (Variant) (Unsigned Long) 255
'--------------------------------------------------

Dim bSTR13
bSTR13 = ""
Dim bSTR14
bSTR14 = ""
Dim boolean7
settingRepository1.GetAttrInfo "DMUGroundColorOfSecondDirectionCurves", bSTR13, bSTR14, boolean7
'--------------------------------------------------
' Parameter 1 : (String) "DMUGroundColorOfSecondDirectionCurves"
' Parameter 2 : (String) "Default value"
' Parameter 3 : (String) "Unlocked"
' Parameter 4 : (Boolean) False
'--------------------------------------------------

Dim arrayOfVariantOfULong3
arrayOfVariantOfULong3 = settingRepository1.GetAttrArray("DMUGroundDisplayShadingTopColor")
'--------------------------------------------------
' Parameter 1 : (String) "DMUGroundDisplayShadingTopColor"
' Returned value : (Array) 
'    Array[0] : (Variant) (Unsigned Long) 0
'    Array[1] : (Variant) (Unsigned Long) 0
'    Array[2] : (Variant) (Unsigned Long) 0
'--------------------------------------------------

Dim bSTR15
bSTR15 = ""
Dim bSTR16
bSTR16 = ""
Dim boolean8
settingRepository1.GetAttrInfo "DMUGroundDisplayShadingTopColor", bSTR15, bSTR16, boolean8
'--------------------------------------------------
' Parameter 1 : (String) "DMUGroundDisplayShadingTopColor"
' Parameter 2 : (String) "Default value"
' Parameter 3 : (String) "Unlocked"
' Parameter 4 : (Boolean) False
'--------------------------------------------------

uLong4 = settingRepository1.GetAttr("DMUGroundDisplayShadingTopTransparency")
'--------------------------------------------------
' Parameter 1 : (String) "DMUGroundDisplayShadingTopTransparency"
' Returned value : (Variant) (Unsigned Long) 1
'--------------------------------------------------

Dim bSTR17
bSTR17 = ""
Dim bSTR18
bSTR18 = ""
Dim boolean9
settingRepository1.GetAttrInfo "DMUGroundDisplayShadingTopTransparency", bSTR17, bSTR18, boolean9
'--------------------------------------------------
' Parameter 1 : (String) "DMUGroundDisplayShadingTopTransparency"
' Parameter 2 : (String) "Default value"
' Parameter 3 : (String) "Unlocked"
' Parameter 4 : (Boolean) False
'--------------------------------------------------

Dim arrayOfVariantOfULong4
arrayOfVariantOfULong4 = settingRepository1.GetAttrArray("DMUGroundDisplayShadingBottomColor")
'--------------------------------------------------
' Parameter 1 : (String) "DMUGroundDisplayShadingBottomColor"
' Returned value : (Array) 
'    Array[0] : (Variant) (Unsigned Long) 0
'    Array[1] : (Variant) (Unsigned Long) 0
'    Array[2] : (Variant) (Unsigned Long) 0
'--------------------------------------------------

Dim bSTR19
bSTR19 = ""
Dim bSTR20
bSTR20 = ""
Dim boolean10
settingRepository1.GetAttrInfo "DMUGroundDisplayShadingBottomColor", bSTR19, bSTR20, boolean10
'--------------------------------------------------
' Parameter 1 : (String) "DMUGroundDisplayShadingBottomColor"
' Parameter 2 : (String) "Default value"
' Parameter 3 : (String) "Unlocked"
' Parameter 4 : (Boolean) False
'--------------------------------------------------

uLong5 = settingRepository1.GetAttr("DMUGroundDisplayShadingBottomTransparency")
'--------------------------------------------------
' Parameter 1 : (String) "DMUGroundDisplayShadingBottomTransparency"
' Returned value : (Variant) (Unsigned Long) 2
'--------------------------------------------------

Dim bSTR21
bSTR21 = ""
Dim bSTR22
bSTR22 = ""
Dim boolean11
settingRepository1.GetAttrInfo "DMUGroundDisplayShadingBottomTransparency", bSTR21, bSTR22, boolean11
'--------------------------------------------------
' Parameter 1 : (String) "DMUGroundDisplayShadingBottomTransparency"
' Parameter 2 : (String) "Default value"
' Parameter 3 : (String) "Unlocked"
' Parameter 4 : (Boolean) False
'--------------------------------------------------

uLong6 = settingRepository1.GetAttr("DMUGroundDistanceBetweenCurvesLink")
'--------------------------------------------------
' Parameter 1 : (String) "DMUGroundDistanceBetweenCurvesLink"
' Returned value : (Variant) (Unsigned Long) 1
'--------------------------------------------------

Dim bSTR23
bSTR23 = ""
Dim bSTR24
bSTR24 = ""
Dim boolean12
settingRepository1.GetAttrInfo "DMUGroundDistanceBetweenCurvesLink", bSTR23, bSTR24, boolean12
'--------------------------------------------------
' Parameter 1 : (String) "DMUGroundDistanceBetweenCurvesLink"
' Parameter 2 : (String) "Default value"
' Parameter 3 : (String) "Unlocked"
' Parameter 4 : (Boolean) False
'--------------------------------------------------

uLong7 = settingRepository1.GetAttr("DMUGroundColorOfCurvesLink")
'--------------------------------------------------
' Parameter 1 : (String) "DMUGroundColorOfCurvesLink"
' Returned value : (Variant) (Unsigned Long) 1
'--------------------------------------------------

Dim bSTR25
bSTR25 = ""
Dim bSTR26
bSTR26 = ""
Dim boolean13
settingRepository1.GetAttrInfo "DMUGroundColorOfCurvesLink", bSTR25, bSTR26, boolean13
'--------------------------------------------------
' Parameter 1 : (String) "DMUGroundColorOfCurvesLink"
' Parameter 2 : (String) "Default value"
' Parameter 3 : (String) "Unlocked"
' Parameter 4 : (Boolean) False
'--------------------------------------------------

End Sub
