Language="VBSCRIPT"

Sub CATMain()

Set settingControllers1 = CATIA.SettingControllers

Set settingRepository1 = settingControllers1.Item("PLMEditorColor")

uLong1 = settingRepository1.GetAttr("CTDTitleFontSize")
'--------------------------------------------------
' Parameter 1 : (String) "CTDTitleFontSize"
' Returned value : (Variant) (Unsigned Long) 10
'--------------------------------------------------

Dim bSTR1
bSTR1 = ""
Dim bSTR2
bSTR2 = ""
Dim boolean1
settingRepository1.GetAttrInfo "CTDTitleFontSize", bSTR1, bSTR2, boolean1
'--------------------------------------------------
' Parameter 1 : (String) "CTDTitleFontSize"
' Parameter 2 : (String) "Default value"
' Parameter 3 : (String) "Unlocked"
' Parameter 4 : (Boolean) False
'--------------------------------------------------

Dim arrayOfVariantOfULong1
arrayOfVariantOfULong1 = settingRepository1.GetAttrArray("CTDTitleFontColor")
'--------------------------------------------------
' Parameter 1 : (String) "CTDTitleFontColor"
' Returned value : (Array) 
'    Array[0] : (Variant) (Unsigned Long) 0
'    Array[1] : (Variant) (Unsigned Long) 0
'    Array[2] : (Variant) (Unsigned Long) 0
'--------------------------------------------------

Dim bSTR3
bSTR3 = ""
Dim bSTR4
bSTR4 = ""
Dim boolean2
settingRepository1.GetAttrInfo "CTDTitleFontColor", bSTR3, bSTR4, boolean2
'--------------------------------------------------
' Parameter 1 : (String) "CTDTitleFontColor"
' Parameter 2 : (String) "Default value"
' Parameter 3 : (String) "Unlocked"
' Parameter 4 : (Boolean) False
'--------------------------------------------------

Dim arrayOfVariantOfULong2
arrayOfVariantOfULong2 = settingRepository1.GetAttrArray("CTDContextFillColor")
'--------------------------------------------------
' Parameter 1 : (String) "CTDContextFillColor"
' Returned value : (Array) 
'    Array[0] : (Variant) (Unsigned Long) 255
'    Array[1] : (Variant) (Unsigned Long) 255
'    Array[2] : (Variant) (Unsigned Long) 255
'--------------------------------------------------

Dim bSTR5
bSTR5 = ""
Dim bSTR6
bSTR6 = ""
Dim boolean3
settingRepository1.GetAttrInfo "CTDContextFillColor", bSTR5, bSTR6, boolean3
'--------------------------------------------------
' Parameter 1 : (String) "CTDContextFillColor"
' Parameter 2 : (String) "Default value"
' Parameter 3 : (String) "Unlocked"
' Parameter 4 : (Boolean) False
'--------------------------------------------------

uLong2 = settingRepository1.GetAttr("CTDContextFillTransparency")
'--------------------------------------------------
' Parameter 1 : (String) "CTDContextFillTransparency"
' Returned value : (Variant) (Unsigned Long) 50
'--------------------------------------------------

Dim bSTR7
bSTR7 = ""
Dim bSTR8
bSTR8 = ""
Dim boolean4
settingRepository1.GetAttrInfo "CTDContextFillTransparency", bSTR7, bSTR8, boolean4
'--------------------------------------------------
' Parameter 1 : (String) "CTDContextFillTransparency"
' Parameter 2 : (String) "Default value"
' Parameter 3 : (String) "Unlocked"
' Parameter 4 : (Boolean) False
'--------------------------------------------------

Dim arrayOfVariantOfULong3
arrayOfVariantOfULong3 = settingRepository1.GetAttrArray("CTDContextLineColor")
'--------------------------------------------------
' Parameter 1 : (String) "CTDContextLineColor"
' Returned value : (Array) 
'    Array[0] : (Variant) (Unsigned Long) 0
'    Array[1] : (Variant) (Unsigned Long) 0
'    Array[2] : (Variant) (Unsigned Long) 0
'--------------------------------------------------

Dim bSTR9
bSTR9 = ""
Dim bSTR10
bSTR10 = ""
Dim boolean5
settingRepository1.GetAttrInfo "CTDContextLineColor", bSTR9, bSTR10, boolean5
'--------------------------------------------------
' Parameter 1 : (String) "CTDContextLineColor"
' Parameter 2 : (String) "Default value"
' Parameter 3 : (String) "Unlocked"
' Parameter 4 : (Boolean) False
'--------------------------------------------------

uLong3 = settingRepository1.GetAttr("CTDContextLineType")
'--------------------------------------------------
' Parameter 1 : (String) "CTDContextLineType"
' Returned value : (Variant) (Unsigned Long) 1
'--------------------------------------------------

Dim bSTR11
bSTR11 = ""
Dim bSTR12
bSTR12 = ""
Dim boolean6
settingRepository1.GetAttrInfo "CTDContextLineType", bSTR11, bSTR12, boolean6
'--------------------------------------------------
' Parameter 1 : (String) "CTDContextLineType"
' Parameter 2 : (String) "Default value"
' Parameter 3 : (String) "Unlocked"
' Parameter 4 : (Boolean) False
'--------------------------------------------------

uLong4 = settingRepository1.GetAttr("CTDContextLineThickness")
'--------------------------------------------------
' Parameter 1 : (String) "CTDContextLineThickness"
' Returned value : (Variant) (Unsigned Long) 2
'--------------------------------------------------

Dim bSTR13
bSTR13 = ""
Dim bSTR14
bSTR14 = ""
Dim boolean7
settingRepository1.GetAttrInfo "CTDContextLineThickness", bSTR13, bSTR14, boolean7
'--------------------------------------------------
' Parameter 1 : (String) "CTDContextLineThickness"
' Parameter 2 : (String) "Default value"
' Parameter 3 : (String) "Unlocked"
' Parameter 4 : (Boolean) False
'--------------------------------------------------

uLong5 = settingRepository1.GetAttr("CTDContextFontSize")
'--------------------------------------------------
' Parameter 1 : (String) "CTDContextFontSize"
' Returned value : (Variant) (Unsigned Long) 7
'--------------------------------------------------

Dim bSTR15
bSTR15 = ""
Dim bSTR16
bSTR16 = ""
Dim boolean8
settingRepository1.GetAttrInfo "CTDContextFontSize", bSTR15, bSTR16, boolean8
'--------------------------------------------------
' Parameter 1 : (String) "CTDContextFontSize"
' Parameter 2 : (String) "Default value"
' Parameter 3 : (String) "Unlocked"
' Parameter 4 : (Boolean) False
'--------------------------------------------------

Dim arrayOfVariantOfULong4
arrayOfVariantOfULong4 = settingRepository1.GetAttrArray("CTDContextFontColor")
'--------------------------------------------------
' Parameter 1 : (String) "CTDContextFontColor"
' Returned value : (Array) 
'    Array[0] : (Variant) (Unsigned Long) 0
'    Array[1] : (Variant) (Unsigned Long) 0
'    Array[2] : (Variant) (Unsigned Long) 0
'--------------------------------------------------

Dim bSTR17
bSTR17 = ""
Dim bSTR18
bSTR18 = ""
Dim boolean9
settingRepository1.GetAttrInfo "CTDContextFontColor", bSTR17, bSTR18, boolean9
'--------------------------------------------------
' Parameter 1 : (String) "CTDContextFontColor"
' Parameter 2 : (String) "Default value"
' Parameter 3 : (String) "Unlocked"
' Parameter 4 : (Boolean) False
'--------------------------------------------------

Dim arrayOfVariantOfULong5
arrayOfVariantOfULong5 = settingRepository1.GetAttrArray("CTDContextualFillColor")
'--------------------------------------------------
' Parameter 1 : (String) "CTDContextualFillColor"
' Returned value : (Array) 
'    Array[0] : (Variant) (Unsigned Long) 255
'    Array[1] : (Variant) (Unsigned Long) 255
'    Array[2] : (Variant) (Unsigned Long) 255
'--------------------------------------------------

Dim bSTR19
bSTR19 = ""
Dim bSTR20
bSTR20 = ""
Dim boolean10
settingRepository1.GetAttrInfo "CTDContextualFillColor", bSTR19, bSTR20, boolean10
'--------------------------------------------------
' Parameter 1 : (String) "CTDContextualFillColor"
' Parameter 2 : (String) "Default value"
' Parameter 3 : (String) "Unlocked"
' Parameter 4 : (Boolean) False
'--------------------------------------------------

uLong6 = settingRepository1.GetAttr("CTDContextualFillTransparency")
'--------------------------------------------------
' Parameter 1 : (String) "CTDContextualFillTransparency"
' Returned value : (Variant) (Unsigned Long) 50
'--------------------------------------------------

Dim bSTR21
bSTR21 = ""
Dim bSTR22
bSTR22 = ""
Dim boolean11
settingRepository1.GetAttrInfo "CTDContextualFillTransparency", bSTR21, bSTR22, boolean11
'--------------------------------------------------
' Parameter 1 : (String) "CTDContextualFillTransparency"
' Parameter 2 : (String) "Default value"
' Parameter 3 : (String) "Unlocked"
' Parameter 4 : (Boolean) False
'--------------------------------------------------

Dim arrayOfVariantOfULong6
arrayOfVariantOfULong6 = settingRepository1.GetAttrArray("CTDContextualLineColor")
'--------------------------------------------------
' Parameter 1 : (String) "CTDContextualLineColor"
' Returned value : (Array) 
'    Array[0] : (Variant) (Unsigned Long) 0
'    Array[1] : (Variant) (Unsigned Long) 0
'    Array[2] : (Variant) (Unsigned Long) 0
'--------------------------------------------------

Dim bSTR23
bSTR23 = ""
Dim bSTR24
bSTR24 = ""
Dim boolean12
settingRepository1.GetAttrInfo "CTDContextualLineColor", bSTR23, bSTR24, boolean12
'--------------------------------------------------
' Parameter 1 : (String) "CTDContextualLineColor"
' Parameter 2 : (String) "Default value"
' Parameter 3 : (String) "Unlocked"
' Parameter 4 : (Boolean) False
'--------------------------------------------------

uLong7 = settingRepository1.GetAttr("CTDContextualLineType")
'--------------------------------------------------
' Parameter 1 : (String) "CTDContextualLineType"
' Returned value : (Variant) (Unsigned Long) 1
'--------------------------------------------------

Dim bSTR25
bSTR25 = ""
Dim bSTR26
bSTR26 = ""
Dim boolean13
settingRepository1.GetAttrInfo "CTDContextualLineType", bSTR25, bSTR26, boolean13
'--------------------------------------------------
' Parameter 1 : (String) "CTDContextualLineType"
' Parameter 2 : (String) "Default value"
' Parameter 3 : (String) "Unlocked"
' Parameter 4 : (Boolean) False
'--------------------------------------------------

uLong8 = settingRepository1.GetAttr("CTDContextualLineThickness")
'--------------------------------------------------
' Parameter 1 : (String) "CTDContextualLineThickness"
' Returned value : (Variant) (Unsigned Long) 2
'--------------------------------------------------

Dim bSTR27
bSTR27 = ""
Dim bSTR28
bSTR28 = ""
Dim boolean14
settingRepository1.GetAttrInfo "CTDContextualLineThickness", bSTR27, bSTR28, boolean14
'--------------------------------------------------
' Parameter 1 : (String) "CTDContextualLineThickness"
' Parameter 2 : (String) "Default value"
' Parameter 3 : (String) "Unlocked"
' Parameter 4 : (Boolean) False
'--------------------------------------------------

uLong9 = settingRepository1.GetAttr("CTDContextualFontSize")
'--------------------------------------------------
' Parameter 1 : (String) "CTDContextualFontSize"
' Returned value : (Variant) (Unsigned Long) 7
'--------------------------------------------------

Dim bSTR29
bSTR29 = ""
Dim bSTR30
bSTR30 = ""
Dim boolean15
settingRepository1.GetAttrInfo "CTDContextualFontSize", bSTR29, bSTR30, boolean15
'--------------------------------------------------
' Parameter 1 : (String) "CTDContextualFontSize"
' Parameter 2 : (String) "Default value"
' Parameter 3 : (String) "Unlocked"
' Parameter 4 : (Boolean) False
'--------------------------------------------------

Dim arrayOfVariantOfULong7
arrayOfVariantOfULong7 = settingRepository1.GetAttrArray("CTDContextualFontColor")
'--------------------------------------------------
' Parameter 1 : (String) "CTDContextualFontColor"
' Returned value : (Array) 
'    Array[0] : (Variant) (Unsigned Long) 0
'    Array[1] : (Variant) (Unsigned Long) 0
'    Array[2] : (Variant) (Unsigned Long) 0
'--------------------------------------------------

Dim bSTR31
bSTR31 = ""
Dim bSTR32
bSTR32 = ""
Dim boolean16
settingRepository1.GetAttrInfo "CTDContextualFontColor", bSTR31, bSTR32, boolean16
'--------------------------------------------------
' Parameter 1 : (String) "CTDContextualFontColor"
' Parameter 2 : (String) "Default value"
' Parameter 3 : (String) "Unlocked"
' Parameter 4 : (Boolean) False
'--------------------------------------------------

Dim arrayOfVariantOfULong8
arrayOfVariantOfULong8 = settingRepository1.GetAttrArray("CTDRelationLineColor")
'--------------------------------------------------
' Parameter 1 : (String) "CTDRelationLineColor"
' Returned value : (Array) 
'    Array[0] : (Variant) (Unsigned Long) 0
'    Array[1] : (Variant) (Unsigned Long) 0
'    Array[2] : (Variant) (Unsigned Long) 0
'--------------------------------------------------

Dim bSTR33
bSTR33 = ""
Dim bSTR34
bSTR34 = ""
Dim boolean17
settingRepository1.GetAttrInfo "CTDRelationLineColor", bSTR33, bSTR34, boolean17
'--------------------------------------------------
' Parameter 1 : (String) "CTDRelationLineColor"
' Parameter 2 : (String) "Default value"
' Parameter 3 : (String) "Unlocked"
' Parameter 4 : (Boolean) False
'--------------------------------------------------

uLong10 = settingRepository1.GetAttr("CTDRelationLineType")
'--------------------------------------------------
' Parameter 1 : (String) "CTDRelationLineType"
' Returned value : (Variant) (Unsigned Long) 1
'--------------------------------------------------

Dim bSTR35
bSTR35 = ""
Dim bSTR36
bSTR36 = ""
Dim boolean18
settingRepository1.GetAttrInfo "CTDRelationLineType", bSTR35, bSTR36, boolean18
'--------------------------------------------------
' Parameter 1 : (String) "CTDRelationLineType"
' Parameter 2 : (String) "Default value"
' Parameter 3 : (String) "Unlocked"
' Parameter 4 : (Boolean) False
'--------------------------------------------------

uLong11 = settingRepository1.GetAttr("CTDRelationLineThickness")
'--------------------------------------------------
' Parameter 1 : (String) "CTDRelationLineThickness"
' Returned value : (Variant) (Unsigned Long) 2
'--------------------------------------------------

Dim bSTR37
bSTR37 = ""
Dim bSTR38
bSTR38 = ""
Dim boolean19
settingRepository1.GetAttrInfo "CTDRelationLineThickness", bSTR37, bSTR38, boolean19
'--------------------------------------------------
' Parameter 1 : (String) "CTDRelationLineThickness"
' Parameter 2 : (String) "Default value"
' Parameter 3 : (String) "Unlocked"
' Parameter 4 : (Boolean) False
'--------------------------------------------------

uLong12 = settingRepository1.GetAttr("CTDRelationFontSize")
'--------------------------------------------------
' Parameter 1 : (String) "CTDRelationFontSize"
' Returned value : (Variant) (Unsigned Long) 5
'--------------------------------------------------

Dim bSTR39
bSTR39 = ""
Dim bSTR40
bSTR40 = ""
Dim boolean20
settingRepository1.GetAttrInfo "CTDRelationFontSize", bSTR39, bSTR40, boolean20
'--------------------------------------------------
' Parameter 1 : (String) "CTDRelationFontSize"
' Parameter 2 : (String) "Default value"
' Parameter 3 : (String) "Unlocked"
' Parameter 4 : (Boolean) False
'--------------------------------------------------

Dim arrayOfVariantOfULong9
arrayOfVariantOfULong9 = settingRepository1.GetAttrArray("CTDRelationFontColor")
'--------------------------------------------------
' Parameter 1 : (String) "CTDRelationFontColor"
' Returned value : (Array) 
'    Array[0] : (Variant) (Unsigned Long) 0
'    Array[1] : (Variant) (Unsigned Long) 0
'    Array[2] : (Variant) (Unsigned Long) 0
'--------------------------------------------------

Dim bSTR41
bSTR41 = ""
Dim bSTR42
bSTR42 = ""
Dim boolean21
settingRepository1.GetAttrInfo "CTDRelationFontColor", bSTR41, bSTR42, boolean21
'--------------------------------------------------
' Parameter 1 : (String) "CTDRelationFontColor"
' Parameter 2 : (String) "Default value"
' Parameter 3 : (String) "Unlocked"
' Parameter 4 : (Boolean) False
'--------------------------------------------------

End Sub
