Language="VBSCRIPT"

Sub CATMain()

Set settingControllers1 = CATIA.SettingControllers

Set settingRepository1 = settingControllers1.Item("CATLiveArchitectureSettings")

double1 = settingRepository1.GetAttr("DefaultGrossStoryHeight")
'--------------------------------------------------
' Parameter 1 : (String) "DefaultGrossStoryHeight"
' Returned value : (Variant) (Double) 3000.000000
'--------------------------------------------------

Dim bSTR1
bSTR1 = ""
Dim bSTR2
bSTR2 = ""
Dim boolean1
settingRepository1.GetAttrInfo "DefaultGrossStoryHeight", bSTR1, bSTR2, boolean1
'--------------------------------------------------
' Parameter 1 : (String) "DefaultGrossStoryHeight"
' Parameter 2 : (String) "Default value"
' Parameter 3 : (String) "Unlocked"
' Parameter 4 : (Boolean) False
'--------------------------------------------------

double2 = settingRepository1.GetAttr("DefaultGrossStoryHeightImperial")
'--------------------------------------------------
' Parameter 1 : (String) "DefaultGrossStoryHeightImperial"
' Returned value : (Variant) (Double) 3149.600000
'--------------------------------------------------

Dim bSTR3
bSTR3 = ""
Dim bSTR4
bSTR4 = ""
Dim boolean2
settingRepository1.GetAttrInfo "DefaultGrossStoryHeightImperial", bSTR3, bSTR4, boolean2
'--------------------------------------------------
' Parameter 1 : (String) "DefaultGrossStoryHeightImperial"
' Parameter 2 : (String) "Default value"
' Parameter 3 : (String) "Unlocked"
' Parameter 4 : (Boolean) False
'--------------------------------------------------

double3 = settingRepository1.GetAttr("DefaultSlabThicknessImperial")
'--------------------------------------------------
' Parameter 1 : (String) "DefaultSlabThicknessImperial"
' Returned value : (Variant) (Double) 152.400000
'--------------------------------------------------

Dim bSTR5
bSTR5 = ""
Dim bSTR6
bSTR6 = ""
Dim boolean3
settingRepository1.GetAttrInfo "DefaultSlabThicknessImperial", bSTR5, bSTR6, boolean3
'--------------------------------------------------
' Parameter 1 : (String) "DefaultSlabThicknessImperial"
' Parameter 2 : (String) "Default value"
' Parameter 3 : (String) "Unlocked"
' Parameter 4 : (Boolean) False
'--------------------------------------------------

double4 = settingRepository1.GetAttr("DefaultSlabThicknessMetric")
'--------------------------------------------------
' Parameter 1 : (String) "DefaultSlabThicknessMetric"
' Returned value : (Variant) (Double) 200.000000
'--------------------------------------------------

Dim bSTR7
bSTR7 = ""
Dim bSTR8
bSTR8 = ""
Dim boolean4
settingRepository1.GetAttrInfo "DefaultSlabThicknessMetric", bSTR7, bSTR8, boolean4
'--------------------------------------------------
' Parameter 1 : (String) "DefaultSlabThicknessMetric"
' Parameter 2 : (String) "Default value"
' Parameter 3 : (String) "Unlocked"
' Parameter 4 : (Boolean) False
'--------------------------------------------------

double5 = settingRepository1.GetAttr("DefaultSlabWidth")
'--------------------------------------------------
' Parameter 1 : (String) "DefaultSlabWidth"
' Returned value : (Variant) (Double) 30000.000000
'--------------------------------------------------

Dim bSTR9
bSTR9 = ""
Dim bSTR10
bSTR10 = ""
Dim boolean5
settingRepository1.GetAttrInfo "DefaultSlabWidth", bSTR9, bSTR10, boolean5
'--------------------------------------------------
' Parameter 1 : (String) "DefaultSlabWidth"
' Parameter 2 : (String) "Default value"
' Parameter 3 : (String) "Unlocked"
' Parameter 4 : (Boolean) False
'--------------------------------------------------

double6 = settingRepository1.GetAttr("DefaultSlabWidthImperial")
'--------------------------------------------------
' Parameter 1 : (String) "DefaultSlabWidthImperial"
' Returned value : (Variant) (Double) 30480.000000
'--------------------------------------------------

Dim bSTR11
bSTR11 = ""
Dim bSTR12
bSTR12 = ""
Dim boolean6
settingRepository1.GetAttrInfo "DefaultSlabWidthImperial", bSTR11, bSTR12, boolean6
'--------------------------------------------------
' Parameter 1 : (String) "DefaultSlabWidthImperial"
' Parameter 2 : (String) "Default value"
' Parameter 3 : (String) "Unlocked"
' Parameter 4 : (Boolean) False
'--------------------------------------------------

double7 = settingRepository1.GetAttr("DefaultExternalWallThickness")
'--------------------------------------------------
' Parameter 1 : (String) "DefaultExternalWallThickness"
' Returned value : (Variant) (Double) 250.000000
'--------------------------------------------------

Dim bSTR13
bSTR13 = ""
Dim bSTR14
bSTR14 = ""
Dim boolean7
settingRepository1.GetAttrInfo "DefaultExternalWallThickness", bSTR13, bSTR14, boolean7
'--------------------------------------------------
' Parameter 1 : (String) "DefaultExternalWallThickness"
' Parameter 2 : (String) "Default value"
' Parameter 3 : (String) "Unlocked"
' Parameter 4 : (Boolean) False
'--------------------------------------------------

double8 = settingRepository1.GetAttr("DefaultExternalWallThicknessImperial")
'--------------------------------------------------
' Parameter 1 : (String) "DefaultExternalWallThicknessImperial"
' Returned value : (Variant) (Double) 355.600000
'--------------------------------------------------

Dim bSTR15
bSTR15 = ""
Dim bSTR16
bSTR16 = ""
Dim boolean8
settingRepository1.GetAttrInfo "DefaultExternalWallThicknessImperial", bSTR15, bSTR16, boolean8
'--------------------------------------------------
' Parameter 1 : (String) "DefaultExternalWallThicknessImperial"
' Parameter 2 : (String) "Default value"
' Parameter 3 : (String) "Unlocked"
' Parameter 4 : (Boolean) False
'--------------------------------------------------

double9 = settingRepository1.GetAttr("DefaultInternalWallThickness")
'--------------------------------------------------
' Parameter 1 : (String) "DefaultInternalWallThickness"
' Returned value : (Variant) (Double) 100.000000
'--------------------------------------------------

Dim bSTR17
bSTR17 = ""
Dim bSTR18
bSTR18 = ""
Dim boolean9
settingRepository1.GetAttrInfo "DefaultInternalWallThickness", bSTR17, bSTR18, boolean9
'--------------------------------------------------
' Parameter 1 : (String) "DefaultInternalWallThickness"
' Parameter 2 : (String) "Default value"
' Parameter 3 : (String) "Unlocked"
' Parameter 4 : (Boolean) False
'--------------------------------------------------

double10 = settingRepository1.GetAttr("DefaultInternalWallThicknessImperial")
'--------------------------------------------------
' Parameter 1 : (String) "DefaultInternalWallThicknessImperial"
' Returned value : (Variant) (Double) 127.000000
'--------------------------------------------------

Dim bSTR19
bSTR19 = ""
Dim bSTR20
bSTR20 = ""
Dim boolean10
settingRepository1.GetAttrInfo "DefaultInternalWallThicknessImperial", bSTR19, bSTR20, boolean10
'--------------------------------------------------
' Parameter 1 : (String) "DefaultInternalWallThicknessImperial"
' Parameter 2 : (String) "Default value"
' Parameter 3 : (String) "Unlocked"
' Parameter 4 : (Boolean) False
'--------------------------------------------------

double11 = settingRepository1.GetAttr("DefaultVertCirWallThickness")
'--------------------------------------------------
' Parameter 1 : (String) "DefaultVertCirWallThickness"
' Returned value : (Variant) (Double) 100.000000
'--------------------------------------------------

Dim bSTR21
bSTR21 = ""
Dim bSTR22
bSTR22 = ""
Dim boolean11
settingRepository1.GetAttrInfo "DefaultVertCirWallThickness", bSTR21, bSTR22, boolean11
'--------------------------------------------------
' Parameter 1 : (String) "DefaultVertCirWallThickness"
' Parameter 2 : (String) "Default value"
' Parameter 3 : (String) "Unlocked"
' Parameter 4 : (Boolean) False
'--------------------------------------------------

double12 = settingRepository1.GetAttr("DefaultVertCirWallThicknessImperial")
'--------------------------------------------------
' Parameter 1 : (String) "DefaultVertCirWallThicknessImperial"
' Returned value : (Variant) (Double) 203.200000
'--------------------------------------------------

Dim bSTR23
bSTR23 = ""
Dim bSTR24
bSTR24 = ""
Dim boolean12
settingRepository1.GetAttrInfo "DefaultVertCirWallThicknessImperial", bSTR23, bSTR24, boolean12
'--------------------------------------------------
' Parameter 1 : (String) "DefaultVertCirWallThicknessImperial"
' Parameter 2 : (String) "Default value"
' Parameter 3 : (String) "Unlocked"
' Parameter 4 : (Boolean) False
'--------------------------------------------------

boolean13 = settingRepository1.GetAttr("Structure_NoPrefMsg")
'--------------------------------------------------
' Parameter 1 : (String) "Structure_NoPrefMsg"
' Returned value : (Variant) (Boolean) False
'--------------------------------------------------

Dim bSTR25
bSTR25 = ""
Dim bSTR26
bSTR26 = ""
Dim boolean14
settingRepository1.GetAttrInfo "Structure_NoPrefMsg", bSTR25, bSTR26, boolean14
'--------------------------------------------------
' Parameter 1 : (String) "Structure_NoPrefMsg"
' Parameter 2 : (String) "Default value"
' Parameter 3 : (String) "Unlocked"
' Parameter 4 : (Boolean) False
'--------------------------------------------------

End Sub
