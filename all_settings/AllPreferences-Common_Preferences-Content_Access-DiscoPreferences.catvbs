Language="VBSCRIPT"

Sub CATMain()

Set settingControllers1 = CATIA.SettingControllers

Set settingRepository1 = settingControllers1.Item("Disco")

long1 = settingRepository1.GetAttr("taquet")
'--------------------------------------------------
' Parameter 1 : (String) "taquet"
' Returned value : (Variant) (Long) 0
'--------------------------------------------------

Dim bSTR1
bSTR1 = ""
Dim bSTR2
bSTR2 = ""
Dim boolean1
settingRepository1.GetAttrInfo "taquet", bSTR1, bSTR2, boolean1
'--------------------------------------------------
' Parameter 1 : (String) "taquet"
' Parameter 2 : (String) "Default value"
' Parameter 3 : (String) "Unlocked"
' Parameter 4 : (Boolean) False
'--------------------------------------------------

End Sub
