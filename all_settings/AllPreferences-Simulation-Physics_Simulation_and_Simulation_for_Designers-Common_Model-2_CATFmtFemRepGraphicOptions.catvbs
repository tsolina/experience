Language="VBSCRIPT"

Sub CATMain()

Set settingControllers1 = CATIA.SettingControllers

Set settingRepository1 = settingControllers1.Item("CATFmtFemRepGraphicOptions")

bSTR1 = settingRepository1.GetAttr("Dummy")
'--------------------------------------------------
' Parameter 1 : (String) "Dummy"
' Returned value : (Variant) (String) ""
'--------------------------------------------------

Dim bSTR2
bSTR2 = ""
Dim bSTR3
bSTR3 = ""
Dim boolean1
settingRepository1.GetAttrInfo "Dummy", bSTR2, bSTR3, boolean1
'--------------------------------------------------
' Parameter 1 : (String) "Dummy"
' Parameter 2 : (String) "Default value"
' Parameter 3 : (String) "Unlocked"
' Parameter 4 : (Boolean) False
'--------------------------------------------------

long1 = settingRepository1.GetAttr("NodeSymbol")
'--------------------------------------------------
' Parameter 1 : (String) "NodeSymbol"
' Returned value : (Variant) (Long) 5
'--------------------------------------------------

Dim bSTR4
bSTR4 = ""
Dim bSTR5
bSTR5 = ""
Dim boolean2
settingRepository1.GetAttrInfo "NodeSymbol", bSTR4, bSTR5, boolean2
'--------------------------------------------------
' Parameter 1 : (String) "NodeSymbol"
' Parameter 2 : (String) "Default value"
' Parameter 3 : (String) "Unlocked"
' Parameter 4 : (Boolean) False
'--------------------------------------------------

Dim arrayOfVariantOfULong1
arrayOfVariantOfULong1 = settingRepository1.GetAttrArray("NodeColor")
'--------------------------------------------------
' Parameter 1 : (String) "NodeColor"
' Returned value : (Array) 
'    Array[0] : (Variant) (Unsigned Long) 255
'    Array[1] : (Variant) (Unsigned Long) 0
'    Array[2] : (Variant) (Unsigned Long) 0
'--------------------------------------------------

Dim bSTR6
bSTR6 = ""
Dim bSTR7
bSTR7 = ""
Dim boolean3
settingRepository1.GetAttrInfo "NodeColor", bSTR6, bSTR7, boolean3
'--------------------------------------------------
' Parameter 1 : (String) "NodeColor"
' Parameter 2 : (String) "Default value"
' Parameter 3 : (String) "Unlocked"
' Parameter 4 : (Boolean) False
'--------------------------------------------------

Dim arrayOfVariantOfULong2
arrayOfVariantOfULong2 = settingRepository1.GetAttrArray("ElementColor")
'--------------------------------------------------
' Parameter 1 : (String) "ElementColor"
' Returned value : (Array) 
'    Array[0] : (Variant) (Unsigned Long) 0
'    Array[1] : (Variant) (Unsigned Long) 128
'    Array[2] : (Variant) (Unsigned Long) 192
'--------------------------------------------------

Dim bSTR8
bSTR8 = ""
Dim bSTR9
bSTR9 = ""
Dim boolean4
settingRepository1.GetAttrInfo "ElementColor", bSTR8, bSTR9, boolean4
'--------------------------------------------------
' Parameter 1 : (String) "ElementColor"
' Parameter 2 : (String) "Default value"
' Parameter 3 : (String) "Unlocked"
' Parameter 4 : (Boolean) False
'--------------------------------------------------

short1 = settingRepository1.GetAttr("Shrink1D")
'--------------------------------------------------
' Parameter 1 : (String) "Shrink1D"
' Returned value : (Variant) (Short) 90
'--------------------------------------------------

Dim bSTR10
bSTR10 = ""
Dim bSTR11
bSTR11 = ""
Dim boolean5
settingRepository1.GetAttrInfo "Shrink1D", bSTR10, bSTR11, boolean5
'--------------------------------------------------
' Parameter 1 : (String) "Shrink1D"
' Parameter 2 : (String) "Default value"
' Parameter 3 : (String) "Unlocked"
' Parameter 4 : (Boolean) False
'--------------------------------------------------

short2 = settingRepository1.GetAttr("Shrink2D")
'--------------------------------------------------
' Parameter 1 : (String) "Shrink2D"
' Returned value : (Variant) (Short) 100
'--------------------------------------------------

Dim bSTR12
bSTR12 = ""
Dim bSTR13
bSTR13 = ""
Dim boolean6
settingRepository1.GetAttrInfo "Shrink2D", bSTR12, bSTR13, boolean6
'--------------------------------------------------
' Parameter 1 : (String) "Shrink2D"
' Parameter 2 : (String) "Default value"
' Parameter 3 : (String) "Unlocked"
' Parameter 4 : (Boolean) False
'--------------------------------------------------

short3 = settingRepository1.GetAttr("Shrink3D")
'--------------------------------------------------
' Parameter 1 : (String) "Shrink3D"
' Returned value : (Variant) (Short) 100
'--------------------------------------------------

Dim bSTR14
bSTR14 = ""
Dim bSTR15
bSTR15 = ""
Dim boolean7
settingRepository1.GetAttrInfo "Shrink3D", bSTR14, bSTR15, boolean7
'--------------------------------------------------
' Parameter 1 : (String) "Shrink3D"
' Parameter 2 : (String) "Default value"
' Parameter 3 : (String) "Unlocked"
' Parameter 4 : (Boolean) False
'--------------------------------------------------

double1 = settingRepository1.GetAttr("Resolution1D")
'--------------------------------------------------
' Parameter 1 : (String) "Resolution1D"
' Returned value : (Variant) (Double) 0.100000
'--------------------------------------------------

Dim bSTR16
bSTR16 = ""
Dim bSTR17
bSTR17 = ""
Dim boolean8
settingRepository1.GetAttrInfo "Resolution1D", bSTR16, bSTR17, boolean8
'--------------------------------------------------
' Parameter 1 : (String) "Resolution1D"
' Parameter 2 : (String) "Default value"
' Parameter 3 : (String) "Unlocked"
' Parameter 4 : (Boolean) False
'--------------------------------------------------

long2 = settingRepository1.GetAttr("NSBarDisplay")
'--------------------------------------------------
' Parameter 1 : (String) "NSBarDisplay"
' Returned value : (Variant) (Long) 1
'--------------------------------------------------

Dim bSTR18
bSTR18 = ""
Dim bSTR19
bSTR19 = ""
Dim boolean9
settingRepository1.GetAttrInfo "NSBarDisplay", bSTR18, bSTR19, boolean9
'--------------------------------------------------
' Parameter 1 : (String) "NSBarDisplay"
' Parameter 2 : (String) "Default value"
' Parameter 3 : (String) "Unlocked"
' Parameter 4 : (Boolean) False
'--------------------------------------------------

End Sub
