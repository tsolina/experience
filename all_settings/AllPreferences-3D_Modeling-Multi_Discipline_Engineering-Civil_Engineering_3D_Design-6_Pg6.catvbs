Language="VBSCRIPT"

Sub CATMain()

Set settingControllers1 = CATIA.SettingControllers

Set settingRepository1 = settingControllers1.Item("AlignmentSettings")

double1 = settingRepository1.GetAttr("AlignmentSolvingTime")
'--------------------------------------------------
' Parameter 1 : (String) "AlignmentSolvingTime"
' Returned value : (Variant) (Double) 2.000000
'--------------------------------------------------

Dim bSTR1
bSTR1 = ""
Dim bSTR2
bSTR2 = ""
Dim boolean1
settingRepository1.GetAttrInfo "AlignmentSolvingTime", bSTR1, bSTR2, boolean1
'--------------------------------------------------
' Parameter 1 : (String) "AlignmentSolvingTime"
' Parameter 2 : (String) "Default value"
' Parameter 3 : (String) "Unlocked"
' Parameter 4 : (Boolean) False
'--------------------------------------------------

End Sub
