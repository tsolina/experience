Language="VBSCRIPT"

Sub CATMain()

Set settingControllers1 = CATIA.SettingControllers

Set settingRepository1 = settingControllers1.Item("ELEditorToolsOffSheet")

long1 = settingRepository1.GetAttr("OffSheetXRefBreak")
'--------------------------------------------------
' Parameter 1 : (String) "OffSheetXRefBreak"
' Returned value : (Variant) (Long) 1
'--------------------------------------------------

Dim bSTR1
bSTR1 = ""
Dim bSTR2
bSTR2 = ""
Dim boolean1
settingRepository1.GetAttrInfo "OffSheetXRefBreak", bSTR1, bSTR2, boolean1
'--------------------------------------------------
' Parameter 1 : (String) "OffSheetXRefBreak"
' Parameter 2 : (String) "Default value"
' Parameter 3 : (String) "Unlocked"
' Parameter 4 : (Boolean) False
'--------------------------------------------------

long2 = settingRepository1.GetAttr("OffSheetWarningMessage")
'--------------------------------------------------
' Parameter 1 : (String) "OffSheetWarningMessage"
' Returned value : (Variant) (Long) 1
'--------------------------------------------------

Dim bSTR3
bSTR3 = ""
Dim bSTR4
bSTR4 = ""
Dim boolean2
settingRepository1.GetAttrInfo "OffSheetWarningMessage", bSTR3, bSTR4, boolean2
'--------------------------------------------------
' Parameter 1 : (String) "OffSheetWarningMessage"
' Parameter 2 : (String) "Default value"
' Parameter 3 : (String) "Unlocked"
' Parameter 4 : (Boolean) False
'--------------------------------------------------

End Sub
