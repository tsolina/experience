Language="VBSCRIPT"

Sub CATMain()

Set settingControllers1 = CATIA.SettingControllers

Set settingRepository1 = settingControllers1.Item("DNBOlpSettings")

bSTR1 = settingRepository1.GetAttr("JavaExe")
'--------------------------------------------------
' Parameter 1 : (String) "JavaExe"
' Returned value : (Variant) (String) "${JAVA_HOME}\bin\javaw.exe"
'--------------------------------------------------

Dim bSTR2
bSTR2 = ""
Dim bSTR3
bSTR3 = ""
Dim boolean1
settingRepository1.GetAttrInfo "JavaExe", bSTR2, bSTR3, boolean1
'--------------------------------------------------
' Parameter 1 : (String) "JavaExe"
' Parameter 2 : (String) "Default value"
' Parameter 3 : (String) "Unlocked"
' Parameter 4 : (Boolean) False
'--------------------------------------------------

bSTR4 = settingRepository1.GetAttr("JavaClassPath")
'--------------------------------------------------
' Parameter 1 : (String) "JavaClassPath"
' Returned value : (Variant) (String) "${CATInstallPath}\docs\java\DNBIgpOlpXSLExtension.jar;${CATInstallPath}\startup\OLP\Translators\DownloaderTools\EncodingConverter.jar"
'--------------------------------------------------

Dim bSTR5
bSTR5 = ""
Dim bSTR6
bSTR6 = ""
Dim boolean2
settingRepository1.GetAttrInfo "JavaClassPath", bSTR5, bSTR6, boolean2
'--------------------------------------------------
' Parameter 1 : (String) "JavaClassPath"
' Parameter 2 : (String) "Default value"
' Parameter 3 : (String) "Unlocked"
' Parameter 4 : (Boolean) False
'--------------------------------------------------

End Sub
