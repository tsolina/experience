Language="VBSCRIPT"

Sub CATMain()

Set settingControllers1 = CATIA.SettingControllers

Set settingRepository1 = settingControllers1.Item("FbdiSettingsRep")

long1 = settingRepository1.GetAttr("FBDI_Files_Filter_Size")
'--------------------------------------------------
' Parameter 1 : (String) "FBDI_Files_Filter_Size"
' Returned value : (Variant) (Long) 0
'--------------------------------------------------

Dim bSTR1
bSTR1 = ""
Dim bSTR2
bSTR2 = ""
Dim boolean1
settingRepository1.GetAttrInfo "FBDI_Files_Filter_Size", bSTR1, bSTR2, boolean1
'--------------------------------------------------
' Parameter 1 : (String) "FBDI_Files_Filter_Size"
' Parameter 2 : (String) "Default value"
' Parameter 3 : (String) "Unlocked"
' Parameter 4 : (Boolean) False
'--------------------------------------------------

boolean2 = settingRepository1.GetAttr("FBDI_ActivatedCAA")
'--------------------------------------------------
' Parameter 1 : (String) "FBDI_ActivatedCAA"
' Returned value : (Variant) (Boolean) False
'--------------------------------------------------

Dim bSTR3
bSTR3 = ""
Dim bSTR4
bSTR4 = ""
Dim boolean3
settingRepository1.GetAttrInfo "FBDI_ActivatedCAA", bSTR3, bSTR4, boolean3
'--------------------------------------------------
' Parameter 1 : (String) "FBDI_ActivatedCAA"
' Parameter 2 : (String) "Default value"
' Parameter 3 : (String) "Unlocked"
' Parameter 4 : (Boolean) False
'--------------------------------------------------

bSTR5 = settingRepository1.GetAttr("FBDI_XMLDirectoryCAA")
'--------------------------------------------------
' Parameter 1 : (String) "FBDI_XMLDirectoryCAA"
' Returned value : (Variant) (String) ""
'--------------------------------------------------

Dim bSTR6
bSTR6 = ""
Dim bSTR7
bSTR7 = ""
Dim boolean4
settingRepository1.GetAttrInfo "FBDI_XMLDirectoryCAA", bSTR6, bSTR7, boolean4
'--------------------------------------------------
' Parameter 1 : (String) "FBDI_XMLDirectoryCAA"
' Parameter 2 : (String) "Default value"
' Parameter 3 : (String) "Unlocked"
' Parameter 4 : (Boolean) False
'--------------------------------------------------

boolean5 = settingRepository1.GetAttr("FBDI_RemoveUnmigrableCAACont")
'--------------------------------------------------
' Parameter 1 : (String) "FBDI_RemoveUnmigrableCAACont"
' Returned value : (Variant) (Boolean) False
'--------------------------------------------------

Dim bSTR8
bSTR8 = ""
Dim bSTR9
bSTR9 = ""
Dim boolean6
settingRepository1.GetAttrInfo "FBDI_RemoveUnmigrableCAACont", bSTR8, bSTR9, boolean6
'--------------------------------------------------
' Parameter 1 : (String) "FBDI_RemoveUnmigrableCAACont"
' Parameter 2 : (String) "Default value"
' Parameter 3 : (String) "Unlocked"
' Parameter 4 : (Boolean) False
'--------------------------------------------------

long2 = settingRepository1.GetAttr("FBDI_LinkIsolationMode")
'--------------------------------------------------
' Parameter 1 : (String) "FBDI_LinkIsolationMode"
' Returned value : (Variant) (Long) 3
'--------------------------------------------------

Dim bSTR10
bSTR10 = ""
Dim bSTR11
bSTR11 = ""
Dim boolean7
settingRepository1.GetAttrInfo "FBDI_LinkIsolationMode", bSTR10, bSTR11, boolean7
'--------------------------------------------------
' Parameter 1 : (String) "FBDI_LinkIsolationMode"
' Parameter 2 : (String) "Default value"
' Parameter 3 : (String) "Unlocked"
' Parameter 4 : (Boolean) False
'--------------------------------------------------

long3 = settingRepository1.GetAttr("FBDI_CATPartMode")
'--------------------------------------------------
' Parameter 1 : (String) "FBDI_CATPartMode"
' Returned value : (Variant) (Long) 1
'--------------------------------------------------

Dim bSTR12
bSTR12 = ""
Dim bSTR13
bSTR13 = ""
Dim boolean8
settingRepository1.GetAttrInfo "FBDI_CATPartMode", bSTR12, bSTR13, boolean8
'--------------------------------------------------
' Parameter 1 : (String) "FBDI_CATPartMode"
' Parameter 2 : (String) "Default value"
' Parameter 3 : (String) "Unlocked"
' Parameter 4 : (Boolean) False
'--------------------------------------------------

long4 = settingRepository1.GetAttr("FBDI_UseMappingTablesMode")
'--------------------------------------------------
' Parameter 1 : (String) "FBDI_UseMappingTablesMode"
' Returned value : (Variant) (Long) 3
'--------------------------------------------------

Dim bSTR14
bSTR14 = ""
Dim bSTR15
bSTR15 = ""
Dim boolean9
settingRepository1.GetAttrInfo "FBDI_UseMappingTablesMode", bSTR14, bSTR15, boolean9
'--------------------------------------------------
' Parameter 1 : (String) "FBDI_UseMappingTablesMode"
' Parameter 2 : (String) "Default value"
' Parameter 3 : (String) "Unlocked"
' Parameter 4 : (Boolean) False
'--------------------------------------------------

long5 = settingRepository1.GetAttr("FBDI_ActV5PropertiesMode")
'--------------------------------------------------
' Parameter 1 : (String) "FBDI_ActV5PropertiesMode"
' Returned value : (Variant) (Long) 1
'--------------------------------------------------

Dim bSTR16
bSTR16 = ""
Dim bSTR17
bSTR17 = ""
Dim boolean10
settingRepository1.GetAttrInfo "FBDI_ActV5PropertiesMode", bSTR16, bSTR17, boolean10
'--------------------------------------------------
' Parameter 1 : (String) "FBDI_ActV5PropertiesMode"
' Parameter 2 : (String) "Default value"
' Parameter 3 : (String) "Unlocked"
' Parameter 4 : (Boolean) False
'--------------------------------------------------

End Sub
