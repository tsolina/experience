Language="VBSCRIPT"

Sub CATMain()

Set settingControllers1 = CATIA.SettingControllers

Set settingRepository1 = settingControllers1.Item("CATSrsSpaceReferentialPage")

long1 = settingRepository1.GetAttr("3DSsnGridInSktCombo")
'--------------------------------------------------
' Parameter 1 : (String) "3DSsnGridInSktCombo"
' Returned value : (Variant) (Long) 1
'--------------------------------------------------

Dim bSTR1
bSTR1 = ""
Dim bSTR2
bSTR2 = ""
Dim boolean1
settingRepository1.GetAttrInfo "3DSsnGridInSktCombo", bSTR1, bSTR2, boolean1
'--------------------------------------------------
' Parameter 1 : (String) "3DSsnGridInSktCombo"
' Parameter 2 : (String) "Default value"
' Parameter 3 : (String) "Unlocked"
' Parameter 4 : (Boolean) False
'--------------------------------------------------

End Sub
