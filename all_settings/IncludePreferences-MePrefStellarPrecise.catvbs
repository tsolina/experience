Language="VBSCRIPT"

Sub CATMain()

Set settingControllers1 = CATIA.SettingControllers

Set settingRepository1 = settingControllers1.Item("StellarPreciseRepository")

boolean1 = settingRepository1.GetAttr("DisableNoShowTranslation")
'--------------------------------------------------
' Parameter 1 : (String) "DisableNoShowTranslation"
' Returned value : (Variant) (Boolean) False
'--------------------------------------------------

Dim bSTR1
bSTR1 = ""
Dim bSTR2
bSTR2 = ""
Dim boolean2
settingRepository1.GetAttrInfo "DisableNoShowTranslation", bSTR1, bSTR2, boolean2
'--------------------------------------------------
' Parameter 1 : (String) "DisableNoShowTranslation"
' Parameter 2 : (String) "Default value"
' Parameter 3 : (String) "Unlocked"
' Parameter 4 : (Boolean) False
'--------------------------------------------------

uLong1 = settingRepository1.GetAttr("DynamicMode")
'--------------------------------------------------
' Parameter 1 : (String) "DynamicMode"
' Returned value : (Variant) (Unsigned Long) 0
'--------------------------------------------------

Dim bSTR3
bSTR3 = ""
Dim bSTR4
bSTR4 = ""
Dim boolean3
settingRepository1.GetAttrInfo "DynamicMode", bSTR3, bSTR4, boolean3
'--------------------------------------------------
' Parameter 1 : (String) "DynamicMode"
' Parameter 2 : (String) "Default value"
' Parameter 3 : (String) "Unlocked"
' Parameter 4 : (Boolean) False
'--------------------------------------------------

uLong2 = settingRepository1.GetAttr("TransitionFrames")
'--------------------------------------------------
' Parameter 1 : (String) "TransitionFrames"
' Returned value : (Variant) (Unsigned Long) 0
'--------------------------------------------------

Dim bSTR5
bSTR5 = ""
Dim bSTR6
bSTR6 = ""
Dim boolean4
settingRepository1.GetAttrInfo "TransitionFrames", bSTR5, bSTR6, boolean4
'--------------------------------------------------
' Parameter 1 : (String) "TransitionFrames"
' Parameter 2 : (String) "Default value"
' Parameter 3 : (String) "Unlocked"
' Parameter 4 : (Boolean) False
'--------------------------------------------------

uLong3 = settingRepository1.GetAttr("PerformanceQualityMode")
'--------------------------------------------------
' Parameter 1 : (String) "PerformanceQualityMode"
' Returned value : (Variant) (Unsigned Long) 4
'--------------------------------------------------

Dim bSTR7
bSTR7 = ""
Dim bSTR8
bSTR8 = ""
Dim boolean5
settingRepository1.GetAttrInfo "PerformanceQualityMode", bSTR7, bSTR8, boolean5
'--------------------------------------------------
' Parameter 1 : (String) "PerformanceQualityMode"
' Parameter 2 : (String) "Default value"
' Parameter 3 : (String) "Unlocked"
' Parameter 4 : (Boolean) False
'--------------------------------------------------

uLong4 = settingRepository1.GetAttr("HardwareMode")
'--------------------------------------------------
' Parameter 1 : (String) "HardwareMode"
' Returned value : (Variant) (Unsigned Long) 1
'--------------------------------------------------

Dim bSTR9
bSTR9 = ""
Dim bSTR10
bSTR10 = ""
Dim boolean6
settingRepository1.GetAttrInfo "HardwareMode", bSTR9, bSTR10, boolean6
'--------------------------------------------------
' Parameter 1 : (String) "HardwareMode"
' Parameter 2 : (String) "Default value"
' Parameter 3 : (String) "Unlocked"
' Parameter 4 : (Boolean) True
'--------------------------------------------------

boolean7 = settingRepository1.GetAttr("DistributedRendering")
'--------------------------------------------------
' Parameter 1 : (String) "DistributedRendering"
' Returned value : (Variant) (Boolean) False
'--------------------------------------------------

Dim bSTR11
bSTR11 = ""
Dim bSTR12
bSTR12 = ""
Dim boolean8
settingRepository1.GetAttrInfo "DistributedRendering", bSTR11, bSTR12, boolean8
'--------------------------------------------------
' Parameter 1 : (String) "DistributedRendering"
' Parameter 2 : (String) "Default value"
' Parameter 3 : (String) "Unlocked"
' Parameter 4 : (Boolean) True
'--------------------------------------------------

bSTR13 = settingRepository1.GetAttr("HostName")
'--------------------------------------------------
' Parameter 1 : (String) "HostName"
' Returned value : (Variant) (String) ""
'--------------------------------------------------

Dim bSTR14
bSTR14 = ""
Dim bSTR15
bSTR15 = ""
Dim boolean9
settingRepository1.GetAttrInfo "HostName", bSTR14, bSTR15, boolean9
'--------------------------------------------------
' Parameter 1 : (String) "HostName"
' Parameter 2 : (String) "Default value"
' Parameter 3 : (String) "Unlocked"
' Parameter 4 : (Boolean) False
'--------------------------------------------------

uLong5 = settingRepository1.GetAttr("Port")
'--------------------------------------------------
' Parameter 1 : (String) "Port"
' Returned value : (Variant) (Unsigned Long) 8080
'--------------------------------------------------

Dim bSTR16
bSTR16 = ""
Dim bSTR17
bSTR17 = ""
Dim boolean10
settingRepository1.GetAttrInfo "Port", bSTR16, bSTR17, boolean10
'--------------------------------------------------
' Parameter 1 : (String) "Port"
' Parameter 2 : (String) "Default value"
' Parameter 3 : (String) "Unlocked"
' Parameter 4 : (Boolean) False
'--------------------------------------------------

bSTR18 = settingRepository1.GetAttr("LocalHostName")
'--------------------------------------------------
' Parameter 1 : (String) "LocalHostName"
' Returned value : (Variant) (String) ""
'--------------------------------------------------

Dim bSTR19
bSTR19 = ""
Dim bSTR20
bSTR20 = ""
Dim boolean11
settingRepository1.GetAttrInfo "LocalHostName", bSTR19, bSTR20, boolean11
'--------------------------------------------------
' Parameter 1 : (String) "LocalHostName"
' Parameter 2 : (String) "Default value"
' Parameter 3 : (String) "Unlocked"
' Parameter 4 : (Boolean) False
'--------------------------------------------------

boolean12 = settingRepository1.GetAttr("EnableCompression")
'--------------------------------------------------
' Parameter 1 : (String) "EnableCompression"
' Returned value : (Variant) (Boolean) False
'--------------------------------------------------

Dim bSTR21
bSTR21 = ""
Dim bSTR22
bSTR22 = ""
Dim boolean13
settingRepository1.GetAttrInfo "EnableCompression", bSTR21, bSTR22, boolean13
'--------------------------------------------------
' Parameter 1 : (String) "EnableCompression"
' Parameter 2 : (String) "Default value"
' Parameter 3 : (String) "Unlocked"
' Parameter 4 : (Boolean) False
'--------------------------------------------------

uLong6 = settingRepository1.GetAttr("CompressionRatio")
'--------------------------------------------------
' Parameter 1 : (String) "CompressionRatio"
' Returned value : (Variant) (Unsigned Long) 60
'--------------------------------------------------

Dim bSTR23
bSTR23 = ""
Dim bSTR24
bSTR24 = ""
Dim boolean14
settingRepository1.GetAttrInfo "CompressionRatio", bSTR23, bSTR24, boolean14
'--------------------------------------------------
' Parameter 1 : (String) "CompressionRatio"
' Parameter 2 : (String) "Default value"
' Parameter 3 : (String) "Unlocked"
' Parameter 4 : (Boolean) False
'--------------------------------------------------

End Sub
