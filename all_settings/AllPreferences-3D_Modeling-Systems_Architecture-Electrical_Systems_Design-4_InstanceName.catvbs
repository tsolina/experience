Language="VBSCRIPT"

Sub CATMain()

Set settingControllers1 = CATIA.SettingControllers

Set settingRepository1 = settingControllers1.Item("ELEditorToolsOptions")

long1 = settingRepository1.GetAttr("InstNameEditActiveTypesNb")
'--------------------------------------------------
' Parameter 1 : (String) "InstNameEditActiveTypesNb"
' Returned value : (Variant) (Long) 0
'--------------------------------------------------

Dim bSTR1
bSTR1 = ""
Dim bSTR2
bSTR2 = ""
Dim boolean1
settingRepository1.GetAttrInfo "InstNameEditActiveTypesNb", bSTR1, bSTR2, boolean1
'--------------------------------------------------
' Parameter 1 : (String) "InstNameEditActiveTypesNb"
' Parameter 2 : (String) "Default value"
' Parameter 3 : (String) "Unlocked"
' Parameter 4 : (Boolean) False
'--------------------------------------------------

settingRepository1.GetAttrArray "InstNameEditActiveTypesNames"
'--------------------------------------------------
' Parameter 1 : (String) "InstNameEditActiveTypesNames"
'--------------------------------------------------

Dim bSTR3
bSTR3 = ""
Dim bSTR4
bSTR4 = ""
Dim boolean2
settingRepository1.GetAttrInfo "InstNameEditActiveTypesNames", bSTR3, bSTR4, boolean2
'--------------------------------------------------
' Parameter 1 : (String) "InstNameEditActiveTypesNames"
' Parameter 2 : (String) "Default value"
' Parameter 3 : (String) "Unlocked"
' Parameter 4 : (Boolean) False
'--------------------------------------------------

End Sub
