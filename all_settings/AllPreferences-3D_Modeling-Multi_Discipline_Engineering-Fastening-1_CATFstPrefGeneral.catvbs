Language="VBSCRIPT"

Sub CATMain()

Set settingControllers1 = CATIA.SettingControllers

Set settingRepository1 = settingControllers1.Item("FstGeneral")

bSTR1 = settingRepository1.GetAttr("FstReportDirectory")
'--------------------------------------------------
' Parameter 1 : (String) "FstReportDirectory"
' Returned value : (Variant) (String) "${CATTemp}"
'--------------------------------------------------

Dim bSTR2
bSTR2 = ""
Dim bSTR3
bSTR3 = ""
Dim boolean1
settingRepository1.GetAttrInfo "FstReportDirectory", bSTR2, bSTR3, boolean1
'--------------------------------------------------
' Parameter 1 : (String) "FstReportDirectory"
' Parameter 2 : (String) "Default value"
' Parameter 3 : (String) "Unlocked"
' Parameter 4 : (Boolean) False
'--------------------------------------------------

long1 = settingRepository1.GetAttr("FstLengthUnit")
'--------------------------------------------------
' Parameter 1 : (String) "FstLengthUnit"
' Returned value : (Variant) (Long) 0
'--------------------------------------------------

Dim bSTR4
bSTR4 = ""
Dim bSTR5
bSTR5 = ""
Dim boolean2
settingRepository1.GetAttrInfo "FstLengthUnit", bSTR4, bSTR5, boolean2
'--------------------------------------------------
' Parameter 1 : (String) "FstLengthUnit"
' Parameter 2 : (String) "Default value"
' Parameter 3 : (String) "Unlocked"
' Parameter 4 : (Boolean) False
'--------------------------------------------------

long2 = settingRepository1.GetAttr("FstWeightUnit")
'--------------------------------------------------
' Parameter 1 : (String) "FstWeightUnit"
' Returned value : (Variant) (Long) 0
'--------------------------------------------------

Dim bSTR6
bSTR6 = ""
Dim bSTR7
bSTR7 = ""
Dim boolean3
settingRepository1.GetAttrInfo "FstWeightUnit", bSTR6, bSTR7, boolean3
'--------------------------------------------------
' Parameter 1 : (String) "FstWeightUnit"
' Parameter 2 : (String) "Default value"
' Parameter 3 : (String) "Unlocked"
' Parameter 4 : (Boolean) False
'--------------------------------------------------

double1 = settingRepository1.GetAttr("FstPrecision")
'--------------------------------------------------
' Parameter 1 : (String) "FstPrecision"
' Returned value : (Variant) (Double) 1.000000
'--------------------------------------------------

Dim bSTR8
bSTR8 = ""
Dim bSTR9
bSTR9 = ""
Dim boolean4
settingRepository1.GetAttrInfo "FstPrecision", bSTR8, bSTR9, boolean4
'--------------------------------------------------
' Parameter 1 : (String) "FstPrecision"
' Parameter 2 : (String) "Default value"
' Parameter 3 : (String) "Unlocked"
' Parameter 4 : (Boolean) False
'--------------------------------------------------

boolean5 = settingRepository1.GetAttr("FstSctfNotation")
'--------------------------------------------------
' Parameter 1 : (String) "FstSctfNotation"
' Returned value : (Variant) (Boolean) False
'--------------------------------------------------

Dim bSTR10
bSTR10 = ""
Dim bSTR11
bSTR11 = ""
Dim boolean6
settingRepository1.GetAttrInfo "FstSctfNotation", bSTR10, bSTR11, boolean6
'--------------------------------------------------
' Parameter 1 : (String) "FstSctfNotation"
' Parameter 2 : (String) "Default value"
' Parameter 3 : (String) "Unlocked"
' Parameter 4 : (Boolean) False
'--------------------------------------------------

End Sub
