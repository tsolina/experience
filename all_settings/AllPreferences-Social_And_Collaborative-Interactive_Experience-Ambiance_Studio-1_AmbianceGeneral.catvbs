Language="VBSCRIPT"

Sub CATMain()

Set settingControllers1 = CATIA.SettingControllers

Set settingRepository1 = settingControllers1.Item("AmbianceStudioSettings")

bSTR1 = settingRepository1.GetAttr("InteractiveSourceSize")
'--------------------------------------------------
' Parameter 1 : (String) "InteractiveSourceSize"
' Returned value : (Variant) (String) "512*256"
'--------------------------------------------------

Dim bSTR2
bSTR2 = ""
Dim bSTR3
bSTR3 = ""
Dim boolean1
settingRepository1.GetAttrInfo "InteractiveSourceSize", bSTR2, bSTR3, boolean1
'--------------------------------------------------
' Parameter 1 : (String) "InteractiveSourceSize"
' Parameter 2 : (String) "Default value"
' Parameter 3 : (String) "Unlocked"
' Parameter 4 : (Boolean) False
'--------------------------------------------------

long1 = settingRepository1.GetAttr("InteractiveLightsBlur")
'--------------------------------------------------
' Parameter 1 : (String) "InteractiveLightsBlur"
' Returned value : (Variant) (Long) 1
'--------------------------------------------------

Dim bSTR4
bSTR4 = ""
Dim bSTR5
bSTR5 = ""
Dim boolean2
settingRepository1.GetAttrInfo "InteractiveLightsBlur", bSTR4, bSTR5, boolean2
'--------------------------------------------------
' Parameter 1 : (String) "InteractiveLightsBlur"
' Parameter 2 : (String) "Default value"
' Parameter 3 : (String) "Unlocked"
' Parameter 4 : (Boolean) False
'--------------------------------------------------

End Sub
