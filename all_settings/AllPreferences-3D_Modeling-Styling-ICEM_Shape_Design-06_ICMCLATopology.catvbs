Language="VBSCRIPT"

Sub CATMain()

Set settingControllers1 = CATIA.SettingControllers

Set settingRepository1 = settingControllers1.Item("ShapeDesignGeneral")

double1 = settingRepository1.GetAttr("TMMergingDistance")
'--------------------------------------------------
' Parameter 1 : (String) "TMMergingDistance"
' Returned value : (Variant) (Double) 0.001000
'--------------------------------------------------

Dim bSTR1
bSTR1 = ""
Dim bSTR2
bSTR2 = ""
Dim boolean1
settingRepository1.GetAttrInfo "TMMergingDistance", bSTR1, bSTR2, boolean1
'--------------------------------------------------
' Parameter 1 : (String) "TMMergingDistance"
' Parameter 2 : (String) "Default value"
' Parameter 3 : (String) "Unlocked"
' Parameter 4 : (Boolean) False
'--------------------------------------------------

Set settingRepository2 = settingControllers1.Item("ICMCLATopologySettings")

double2 = settingRepository2.GetAttr("G1")
'--------------------------------------------------
' Parameter 1 : (String) "G1"
' Returned value : (Variant) (Double) 0.500000
'--------------------------------------------------

Dim bSTR3
bSTR3 = ""
Dim bSTR4
bSTR4 = ""
Dim boolean2
settingRepository2.GetAttrInfo "G1", bSTR3, bSTR4, boolean2
'--------------------------------------------------
' Parameter 1 : (String) "G1"
' Parameter 2 : (String) "Default value"
' Parameter 3 : (String) "Unlocked"
' Parameter 4 : (Boolean) False
'--------------------------------------------------

double3 = settingRepository2.GetAttr("G2")
'--------------------------------------------------
' Parameter 1 : (String) "G2"
' Returned value : (Variant) (Double) 5.000000
'--------------------------------------------------

Dim bSTR5
bSTR5 = ""
Dim bSTR6
bSTR6 = ""
Dim boolean3
settingRepository2.GetAttrInfo "G2", bSTR5, bSTR6, boolean3
'--------------------------------------------------
' Parameter 1 : (String) "G2"
' Parameter 2 : (String) "Default value"
' Parameter 3 : (String) "Unlocked"
' Parameter 4 : (Boolean) False
'--------------------------------------------------

double4 = settingRepository2.GetAttr("G3")
'--------------------------------------------------
' Parameter 1 : (String) "G3"
' Returned value : (Variant) (Double) 3.141593
'--------------------------------------------------

Dim bSTR7
bSTR7 = ""
Dim bSTR8
bSTR8 = ""
Dim boolean4
settingRepository2.GetAttrInfo "G3", bSTR7, bSTR8, boolean4
'--------------------------------------------------
' Parameter 1 : (String) "G3"
' Parameter 2 : (String) "Default value"
' Parameter 3 : (String) "Unlocked"
' Parameter 4 : (Boolean) False
'--------------------------------------------------

End Sub
