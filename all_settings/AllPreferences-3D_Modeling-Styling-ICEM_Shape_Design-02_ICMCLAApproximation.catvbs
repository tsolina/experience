Language="VBSCRIPT"

Sub CATMain()

Set settingControllers1 = CATIA.SettingControllers

Set settingRepository1 = settingControllers1.Item("ICMCLAApproximationSettings")

double1 = settingRepository1.GetAttr("CurveG0")
'--------------------------------------------------
' Parameter 1 : (String) "CurveG0"
' Returned value : (Variant) (Double) 0.001000
'--------------------------------------------------

Dim bSTR1
bSTR1 = ""
Dim bSTR2
bSTR2 = ""
Dim boolean1
settingRepository1.GetAttrInfo "CurveG0", bSTR1, bSTR2, boolean1
'--------------------------------------------------
' Parameter 1 : (String) "CurveG0"
' Parameter 2 : (String) "Default value"
' Parameter 3 : (String) "Unlocked"
' Parameter 4 : (Boolean) False
'--------------------------------------------------

double2 = settingRepository1.GetAttr("SurfaceG0")
'--------------------------------------------------
' Parameter 1 : (String) "SurfaceG0"
' Returned value : (Variant) (Double) 0.001000
'--------------------------------------------------

Dim bSTR3
bSTR3 = ""
Dim bSTR4
bSTR4 = ""
Dim boolean2
settingRepository1.GetAttrInfo "SurfaceG0", bSTR3, bSTR4, boolean2
'--------------------------------------------------
' Parameter 1 : (String) "SurfaceG0"
' Parameter 2 : (String) "Default value"
' Parameter 3 : (String) "Unlocked"
' Parameter 4 : (Boolean) False
'--------------------------------------------------

double3 = settingRepository1.GetAttr("SurfaceG1")
'--------------------------------------------------
' Parameter 1 : (String) "SurfaceG1"
' Returned value : (Variant) (Double) 0.004363
'--------------------------------------------------

Dim bSTR5
bSTR5 = ""
Dim bSTR6
bSTR6 = ""
Dim boolean3
settingRepository1.GetAttrInfo "SurfaceG1", bSTR5, bSTR6, boolean3
'--------------------------------------------------
' Parameter 1 : (String) "SurfaceG1"
' Parameter 2 : (String) "Default value"
' Parameter 3 : (String) "Unlocked"
' Parameter 4 : (Boolean) False
'--------------------------------------------------

long1 = settingRepository1.GetAttr("CurveOrderUType")
'--------------------------------------------------
' Parameter 1 : (String) "CurveOrderUType"
' Returned value : (Variant) (Long) 0
'--------------------------------------------------

Dim bSTR7
bSTR7 = ""
Dim bSTR8
bSTR8 = ""
Dim boolean4
settingRepository1.GetAttrInfo "CurveOrderUType", bSTR7, bSTR8, boolean4
'--------------------------------------------------
' Parameter 1 : (String) "CurveOrderUType"
' Parameter 2 : (String) "Default value"
' Parameter 3 : (String) "Unlocked"
' Parameter 4 : (Boolean) False
'--------------------------------------------------

long2 = settingRepository1.GetAttr("CurveOrderU")
'--------------------------------------------------
' Parameter 1 : (String) "CurveOrderU"
' Returned value : (Variant) (Long) 7
'--------------------------------------------------

Dim bSTR9
bSTR9 = ""
Dim bSTR10
bSTR10 = ""
Dim boolean5
settingRepository1.GetAttrInfo "CurveOrderU", bSTR9, bSTR10, boolean5
'--------------------------------------------------
' Parameter 1 : (String) "CurveOrderU"
' Parameter 2 : (String) "Default value"
' Parameter 3 : (String) "Unlocked"
' Parameter 4 : (Boolean) False
'--------------------------------------------------

long3 = settingRepository1.GetAttr("CurveSegmentsUType")
'--------------------------------------------------
' Parameter 1 : (String) "CurveSegmentsUType"
' Returned value : (Variant) (Long) 1
'--------------------------------------------------

Dim bSTR11
bSTR11 = ""
Dim bSTR12
bSTR12 = ""
Dim boolean6
settingRepository1.GetAttrInfo "CurveSegmentsUType", bSTR11, bSTR12, boolean6
'--------------------------------------------------
' Parameter 1 : (String) "CurveSegmentsUType"
' Parameter 2 : (String) "Default value"
' Parameter 3 : (String) "Unlocked"
' Parameter 4 : (Boolean) False
'--------------------------------------------------

long4 = settingRepository1.GetAttr("CurveSegmentsU")
'--------------------------------------------------
' Parameter 1 : (String) "CurveSegmentsU"
' Returned value : (Variant) (Long) 1
'--------------------------------------------------

Dim bSTR13
bSTR13 = ""
Dim bSTR14
bSTR14 = ""
Dim boolean7
settingRepository1.GetAttrInfo "CurveSegmentsU", bSTR13, bSTR14, boolean7
'--------------------------------------------------
' Parameter 1 : (String) "CurveSegmentsU"
' Parameter 2 : (String) "Default value"
' Parameter 3 : (String) "Unlocked"
' Parameter 4 : (Boolean) False
'--------------------------------------------------

long5 = settingRepository1.GetAttr("SurfaceOrderUType")
'--------------------------------------------------
' Parameter 1 : (String) "SurfaceOrderUType"
' Returned value : (Variant) (Long) 0
'--------------------------------------------------

Dim bSTR15
bSTR15 = ""
Dim bSTR16
bSTR16 = ""
Dim boolean8
settingRepository1.GetAttrInfo "SurfaceOrderUType", bSTR15, bSTR16, boolean8
'--------------------------------------------------
' Parameter 1 : (String) "SurfaceOrderUType"
' Parameter 2 : (String) "Default value"
' Parameter 3 : (String) "Unlocked"
' Parameter 4 : (Boolean) False
'--------------------------------------------------

long6 = settingRepository1.GetAttr("SurfaceOrderU")
'--------------------------------------------------
' Parameter 1 : (String) "SurfaceOrderU"
' Returned value : (Variant) (Long) 7
'--------------------------------------------------

Dim bSTR17
bSTR17 = ""
Dim bSTR18
bSTR18 = ""
Dim boolean9
settingRepository1.GetAttrInfo "SurfaceOrderU", bSTR17, bSTR18, boolean9
'--------------------------------------------------
' Parameter 1 : (String) "SurfaceOrderU"
' Parameter 2 : (String) "Default value"
' Parameter 3 : (String) "Unlocked"
' Parameter 4 : (Boolean) False
'--------------------------------------------------

long7 = settingRepository1.GetAttr("SurfaceOrderLinked")
'--------------------------------------------------
' Parameter 1 : (String) "SurfaceOrderLinked"
' Returned value : (Variant) (Long) 0
'--------------------------------------------------

Dim bSTR19
bSTR19 = ""
Dim bSTR20
bSTR20 = ""
Dim boolean10
settingRepository1.GetAttrInfo "SurfaceOrderLinked", bSTR19, bSTR20, boolean10
'--------------------------------------------------
' Parameter 1 : (String) "SurfaceOrderLinked"
' Parameter 2 : (String) "Default value"
' Parameter 3 : (String) "Unlocked"
' Parameter 4 : (Boolean) False
'--------------------------------------------------

long8 = settingRepository1.GetAttr("SurfaceOrderVType")
'--------------------------------------------------
' Parameter 1 : (String) "SurfaceOrderVType"
' Returned value : (Variant) (Long) 0
'--------------------------------------------------

Dim bSTR21
bSTR21 = ""
Dim bSTR22
bSTR22 = ""
Dim boolean11
settingRepository1.GetAttrInfo "SurfaceOrderVType", bSTR21, bSTR22, boolean11
'--------------------------------------------------
' Parameter 1 : (String) "SurfaceOrderVType"
' Parameter 2 : (String) "Default value"
' Parameter 3 : (String) "Unlocked"
' Parameter 4 : (Boolean) False
'--------------------------------------------------

long9 = settingRepository1.GetAttr("SurfaceOrderV")
'--------------------------------------------------
' Parameter 1 : (String) "SurfaceOrderV"
' Returned value : (Variant) (Long) 7
'--------------------------------------------------

Dim bSTR23
bSTR23 = ""
Dim bSTR24
bSTR24 = ""
Dim boolean12
settingRepository1.GetAttrInfo "SurfaceOrderV", bSTR23, bSTR24, boolean12
'--------------------------------------------------
' Parameter 1 : (String) "SurfaceOrderV"
' Parameter 2 : (String) "Default value"
' Parameter 3 : (String) "Unlocked"
' Parameter 4 : (Boolean) False
'--------------------------------------------------

long10 = settingRepository1.GetAttr("SurfaceSegmentsUType")
'--------------------------------------------------
' Parameter 1 : (String) "SurfaceSegmentsUType"
' Returned value : (Variant) (Long) 1
'--------------------------------------------------

Dim bSTR25
bSTR25 = ""
Dim bSTR26
bSTR26 = ""
Dim boolean13
settingRepository1.GetAttrInfo "SurfaceSegmentsUType", bSTR25, bSTR26, boolean13
'--------------------------------------------------
' Parameter 1 : (String) "SurfaceSegmentsUType"
' Parameter 2 : (String) "Default value"
' Parameter 3 : (String) "Unlocked"
' Parameter 4 : (Boolean) False
'--------------------------------------------------

long11 = settingRepository1.GetAttr("SurfaceSegmentsU")
'--------------------------------------------------
' Parameter 1 : (String) "SurfaceSegmentsU"
' Returned value : (Variant) (Long) 1
'--------------------------------------------------

Dim bSTR27
bSTR27 = ""
Dim bSTR28
bSTR28 = ""
Dim boolean14
settingRepository1.GetAttrInfo "SurfaceSegmentsU", bSTR27, bSTR28, boolean14
'--------------------------------------------------
' Parameter 1 : (String) "SurfaceSegmentsU"
' Parameter 2 : (String) "Default value"
' Parameter 3 : (String) "Unlocked"
' Parameter 4 : (Boolean) False
'--------------------------------------------------

long12 = settingRepository1.GetAttr("SurfaceSegmentsLinked")
'--------------------------------------------------
' Parameter 1 : (String) "SurfaceSegmentsLinked"
' Returned value : (Variant) (Long) 0
'--------------------------------------------------

Dim bSTR29
bSTR29 = ""
Dim bSTR30
bSTR30 = ""
Dim boolean15
settingRepository1.GetAttrInfo "SurfaceSegmentsLinked", bSTR29, bSTR30, boolean15
'--------------------------------------------------
' Parameter 1 : (String) "SurfaceSegmentsLinked"
' Parameter 2 : (String) "Default value"
' Parameter 3 : (String) "Unlocked"
' Parameter 4 : (Boolean) False
'--------------------------------------------------

long13 = settingRepository1.GetAttr("SurfaceSegmentsVType")
'--------------------------------------------------
' Parameter 1 : (String) "SurfaceSegmentsVType"
' Returned value : (Variant) (Long) 1
'--------------------------------------------------

Dim bSTR31
bSTR31 = ""
Dim bSTR32
bSTR32 = ""
Dim boolean16
settingRepository1.GetAttrInfo "SurfaceSegmentsVType", bSTR31, bSTR32, boolean16
'--------------------------------------------------
' Parameter 1 : (String) "SurfaceSegmentsVType"
' Parameter 2 : (String) "Default value"
' Parameter 3 : (String) "Unlocked"
' Parameter 4 : (Boolean) False
'--------------------------------------------------

long14 = settingRepository1.GetAttr("SurfaceSegmentsV")
'--------------------------------------------------
' Parameter 1 : (String) "SurfaceSegmentsV"
' Returned value : (Variant) (Long) 1
'--------------------------------------------------

Dim bSTR33
bSTR33 = ""
Dim bSTR34
bSTR34 = ""
Dim boolean17
settingRepository1.GetAttrInfo "SurfaceSegmentsV", bSTR33, bSTR34, boolean17
'--------------------------------------------------
' Parameter 1 : (String) "SurfaceSegmentsV"
' Parameter 2 : (String) "Default value"
' Parameter 3 : (String) "Unlocked"
' Parameter 4 : (Boolean) False
'--------------------------------------------------

End Sub
