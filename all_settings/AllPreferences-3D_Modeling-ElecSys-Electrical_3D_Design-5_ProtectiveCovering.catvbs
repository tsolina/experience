Language="VBSCRIPT"

Sub CATMain()

Set settingControllers1 = CATIA.SettingControllers

Set settingRepository1 = settingControllers1.Item("ElectricalHarnessInstallation")

long1 = settingRepository1.GetAttr("Scratchmode")
'--------------------------------------------------
' Parameter 1 : (String) "Scratchmode"
' Returned value : (Variant) (Long) 1
'--------------------------------------------------

Dim bSTR1
bSTR1 = ""
Dim bSTR2
bSTR2 = ""
Dim boolean1
settingRepository1.GetAttrInfo "Scratchmode", bSTR1, bSTR2, boolean1
'--------------------------------------------------
' Parameter 1 : (String) "Scratchmode"
' Parameter 2 : (String) "Default value"
' Parameter 3 : (String) "Unlocked"
' Parameter 4 : (Boolean) False
'--------------------------------------------------

long2 = settingRepository1.GetAttr("DefaultLineType")
'--------------------------------------------------
' Parameter 1 : (String) "DefaultLineType"
' Returned value : (Variant) (Long) 0
'--------------------------------------------------

Dim bSTR3
bSTR3 = ""
Dim bSTR4
bSTR4 = ""
Dim boolean2
settingRepository1.GetAttrInfo "DefaultLineType", bSTR3, bSTR4, boolean2
'--------------------------------------------------
' Parameter 1 : (String) "DefaultLineType"
' Parameter 2 : (String) "Default value"
' Parameter 3 : (String) "Unlocked"
' Parameter 4 : (Boolean) False
'--------------------------------------------------

long3 = settingRepository1.GetAttr("DefaultLineType")
'--------------------------------------------------
' Parameter 1 : (String) "DefaultLineType"
' Returned value : (Variant) (Long) 0
'--------------------------------------------------

Dim bSTR5
bSTR5 = ""
Dim bSTR6
bSTR6 = ""
Dim boolean3
settingRepository1.GetAttrInfo "DefaultLineType", bSTR5, bSTR6, boolean3
'--------------------------------------------------
' Parameter 1 : (String) "DefaultLineType"
' Parameter 2 : (String) "Default value"
' Parameter 3 : (String) "Unlocked"
' Parameter 4 : (Boolean) False
'--------------------------------------------------

long4 = settingRepository1.GetAttr("SelectedLineType")
'--------------------------------------------------
' Parameter 1 : (String) "SelectedLineType"
' Returned value : (Variant) (Long) 1
'--------------------------------------------------

Dim bSTR7
bSTR7 = ""
Dim bSTR8
bSTR8 = ""
Dim boolean4
settingRepository1.GetAttrInfo "SelectedLineType", bSTR7, bSTR8, boolean4
'--------------------------------------------------
' Parameter 1 : (String) "SelectedLineType"
' Parameter 2 : (String) "Default value"
' Parameter 3 : (String) "Unlocked"
' Parameter 4 : (Boolean) False
'--------------------------------------------------

End Sub
