Language="VBSCRIPT"

Sub CATMain()

Set settingControllers1 = CATIA.SettingControllers

Set settingRepository1 = settingControllers1.Item("DELPLMWorkInstructionSettings")

long1 = settingRepository1.GetAttr("WorkInstructionPublishMode")
'--------------------------------------------------
' Parameter 1 : (String) "WorkInstructionPublishMode"
' Returned value : (Variant) (Long) 0
'--------------------------------------------------

Dim bSTR1
bSTR1 = ""
Dim bSTR2
bSTR2 = ""
Dim boolean1
settingRepository1.GetAttrInfo "WorkInstructionPublishMode", bSTR1, bSTR2, boolean1
'--------------------------------------------------
' Parameter 1 : (String) "WorkInstructionPublishMode"
' Parameter 2 : (String) "Default value"
' Parameter 3 : (String) "Unlocked"
' Parameter 4 : (Boolean) False
'--------------------------------------------------

boolean2 = settingRepository1.GetAttr("DoNotPublishPersonalData")
'--------------------------------------------------
' Parameter 1 : (String) "DoNotPublishPersonalData"
' Returned value : (Variant) (Boolean) False
'--------------------------------------------------

Dim bSTR3
bSTR3 = ""
Dim bSTR4
bSTR4 = ""
Dim boolean3
settingRepository1.GetAttrInfo "DoNotPublishPersonalData", bSTR3, bSTR4, boolean3
'--------------------------------------------------
' Parameter 1 : (String) "DoNotPublishPersonalData"
' Parameter 2 : (String) "Default value"
' Parameter 3 : (String) "Unlocked"
' Parameter 4 : (Boolean) False
'--------------------------------------------------

boolean4 = settingRepository1.GetAttr("GenDocAltSub")
'--------------------------------------------------
' Parameter 1 : (String) "GenDocAltSub"
' Returned value : (Variant) (Boolean) False
'--------------------------------------------------

Dim bSTR5
bSTR5 = ""
Dim bSTR6
bSTR6 = ""
Dim boolean5
settingRepository1.GetAttrInfo "GenDocAltSub", bSTR5, bSTR6, boolean5
'--------------------------------------------------
' Parameter 1 : (String) "GenDocAltSub"
' Parameter 2 : (String) "Default value"
' Parameter 3 : (String) "Unlocked"
' Parameter 4 : (Boolean) False
'--------------------------------------------------

boolean6 = settingRepository1.GetAttr("GenDocAllPrimary")
'--------------------------------------------------
' Parameter 1 : (String) "GenDocAllPrimary"
' Returned value : (Variant) (Boolean) False
'--------------------------------------------------

Dim bSTR7
bSTR7 = ""
Dim bSTR8
bSTR8 = ""
Dim boolean7
settingRepository1.GetAttrInfo "GenDocAllPrimary", bSTR7, bSTR8, boolean7
'--------------------------------------------------
' Parameter 1 : (String) "GenDocAllPrimary"
' Parameter 2 : (String) "Default value"
' Parameter 3 : (String) "Unlocked"
' Parameter 4 : (Boolean) False
'--------------------------------------------------

boolean8 = settingRepository1.GetAttr("PublishAutoSave")
'--------------------------------------------------
' Parameter 1 : (String) "PublishAutoSave"
' Returned value : (Variant) (Boolean) False
'--------------------------------------------------

Dim bSTR9
bSTR9 = ""
Dim bSTR10
bSTR10 = ""
Dim boolean9
settingRepository1.GetAttrInfo "PublishAutoSave", bSTR9, bSTR10, boolean9
'--------------------------------------------------
' Parameter 1 : (String) "PublishAutoSave"
' Parameter 2 : (String) "Default value"
' Parameter 3 : (String) "Unlocked"
' Parameter 4 : (Boolean) False
'--------------------------------------------------

bSTR11 = settingRepository1.GetAttr("PublishMaturity")
'--------------------------------------------------
' Parameter 1 : (String) "PublishMaturity"
' Returned value : (Variant) (String) "IN_WORK"
'--------------------------------------------------

Dim bSTR12
bSTR12 = ""
Dim bSTR13
bSTR13 = ""
Dim boolean10
settingRepository1.GetAttrInfo "PublishMaturity", bSTR12, bSTR13, boolean10
'--------------------------------------------------
' Parameter 1 : (String) "PublishMaturity"
' Parameter 2 : (String) "Default value"
' Parameter 3 : (String) "Unlocked"
' Parameter 4 : (Boolean) False
'--------------------------------------------------

boolean11 = settingRepository1.GetAttr("PublishGenDoc")
'--------------------------------------------------
' Parameter 1 : (String) "PublishGenDoc"
' Returned value : (Variant) (Boolean) False
'--------------------------------------------------

Dim bSTR14
bSTR14 = ""
Dim bSTR15
bSTR15 = ""
Dim boolean12
settingRepository1.GetAttrInfo "PublishGenDoc", bSTR14, bSTR15, boolean12
'--------------------------------------------------
' Parameter 1 : (String) "PublishGenDoc"
' Parameter 2 : (String) "Default value"
' Parameter 3 : (String) "Unlocked"
' Parameter 4 : (Boolean) False
'--------------------------------------------------

boolean13 = settingRepository1.GetAttr("CustomBackgroundColorRequired")
'--------------------------------------------------
' Parameter 1 : (String) "CustomBackgroundColorRequired"
' Returned value : (Variant) (Boolean) False
'--------------------------------------------------

Dim bSTR16
bSTR16 = ""
Dim bSTR17
bSTR17 = ""
Dim boolean14
settingRepository1.GetAttrInfo "CustomBackgroundColorRequired", bSTR16, bSTR17, boolean14
'--------------------------------------------------
' Parameter 1 : (String) "CustomBackgroundColorRequired"
' Parameter 2 : (String) "Default value"
' Parameter 3 : (String) "Unlocked"
' Parameter 4 : (Boolean) False
'--------------------------------------------------

uLong1 = settingRepository1.GetAttr("CustomBackgroundColor")
'--------------------------------------------------
' Parameter 1 : (String) "CustomBackgroundColor"
' Returned value : (Variant) (Unsigned Long) 16777215
'--------------------------------------------------

Dim bSTR18
bSTR18 = ""
Dim bSTR19
bSTR19 = ""
Dim boolean15
settingRepository1.GetAttrInfo "CustomBackgroundColor", bSTR18, bSTR19, boolean15
'--------------------------------------------------
' Parameter 1 : (String) "CustomBackgroundColor"
' Parameter 2 : (String) "Default value"
' Parameter 3 : (String) "Unlocked"
' Parameter 4 : (Boolean) False
'--------------------------------------------------

boolean16 = settingRepository1.GetAttr("Publish2DViews")
'--------------------------------------------------
' Parameter 1 : (String) "Publish2DViews"
' Returned value : (Variant) (Boolean) False
'--------------------------------------------------

Dim bSTR20
bSTR20 = ""
Dim bSTR21
bSTR21 = ""
Dim boolean17
settingRepository1.GetAttrInfo "Publish2DViews", bSTR20, bSTR21, boolean17
'--------------------------------------------------
' Parameter 1 : (String) "Publish2DViews"
' Parameter 2 : (String) "Default value"
' Parameter 3 : (String) "Unlocked"
' Parameter 4 : (Boolean) False
'--------------------------------------------------

boolean18 = settingRepository1.GetAttr("PublishPartialImageGen")
'--------------------------------------------------
' Parameter 1 : (String) "PublishPartialImageGen"
' Returned value : (Variant) (Boolean) False
'--------------------------------------------------

Dim bSTR22
bSTR22 = ""
Dim bSTR23
bSTR23 = ""
Dim boolean19
settingRepository1.GetAttrInfo "PublishPartialImageGen", bSTR22, bSTR23, boolean19
'--------------------------------------------------
' Parameter 1 : (String) "PublishPartialImageGen"
' Parameter 2 : (String) "Default value"
' Parameter 3 : (String) "Unlocked"
' Parameter 4 : (Boolean) False
'--------------------------------------------------

boolean20 = settingRepository1.GetAttr("Publish3DViews")
'--------------------------------------------------
' Parameter 1 : (String) "Publish3DViews"
' Returned value : (Variant) (Boolean) True
'--------------------------------------------------

Dim bSTR24
bSTR24 = ""
Dim bSTR25
bSTR25 = ""
Dim boolean21
settingRepository1.GetAttrInfo "Publish3DViews", bSTR24, bSTR25, boolean21
'--------------------------------------------------
' Parameter 1 : (String) "Publish3DViews"
' Parameter 2 : (String) "Default value"
' Parameter 3 : (String) "Unlocked"
' Parameter 4 : (Boolean) False
'--------------------------------------------------

boolean22 = settingRepository1.GetAttr("Publish3DBuildup")
'--------------------------------------------------
' Parameter 1 : (String) "Publish3DBuildup"
' Returned value : (Variant) (Boolean) True
'--------------------------------------------------

Dim bSTR26
bSTR26 = ""
Dim bSTR27
bSTR27 = ""
Dim boolean23
settingRepository1.GetAttrInfo "Publish3DBuildup", bSTR26, bSTR27, boolean23
'--------------------------------------------------
' Parameter 1 : (String) "Publish3DBuildup"
' Parameter 2 : (String) "Default value"
' Parameter 3 : (String) "Unlocked"
' Parameter 4 : (Boolean) False
'--------------------------------------------------

boolean24 = settingRepository1.GetAttr("PublishLight")
'--------------------------------------------------
' Parameter 1 : (String) "PublishLight"
' Returned value : (Variant) (Boolean) False
'--------------------------------------------------

Dim bSTR28
bSTR28 = ""
Dim bSTR29
bSTR29 = ""
Dim boolean25
settingRepository1.GetAttrInfo "PublishLight", bSTR28, bSTR29, boolean25
'--------------------------------------------------
' Parameter 1 : (String) "PublishLight"
' Parameter 2 : (String) "Default value"
' Parameter 3 : (String) "Unlocked"
' Parameter 4 : (Boolean) False
'--------------------------------------------------

boolean26 = settingRepository1.GetAttr("ChangeMaturity")
'--------------------------------------------------
' Parameter 1 : (String) "ChangeMaturity"
' Returned value : (Variant) (Boolean) False
'--------------------------------------------------

Dim bSTR30
bSTR30 = ""
Dim bSTR31
bSTR31 = ""
Dim boolean27
settingRepository1.GetAttrInfo "ChangeMaturity", bSTR30, bSTR31, boolean27
'--------------------------------------------------
' Parameter 1 : (String) "ChangeMaturity"
' Parameter 2 : (String) "Default value"
' Parameter 3 : (String) "Unlocked"
' Parameter 4 : (Boolean) False
'--------------------------------------------------

bSTR32 = settingRepository1.GetAttr("ChangeMaturityTo")
'--------------------------------------------------
' Parameter 1 : (String) "ChangeMaturityTo"
' Returned value : (Variant) (String) "FROZEN"
'--------------------------------------------------

Dim bSTR33
bSTR33 = ""
Dim bSTR34
bSTR34 = ""
Dim boolean28
settingRepository1.GetAttrInfo "ChangeMaturityTo", bSTR33, bSTR34, boolean28
'--------------------------------------------------
' Parameter 1 : (String) "ChangeMaturityTo"
' Parameter 2 : (String) "Default value"
' Parameter 3 : (String) "Unlocked"
' Parameter 4 : (Boolean) False
'--------------------------------------------------

End Sub
