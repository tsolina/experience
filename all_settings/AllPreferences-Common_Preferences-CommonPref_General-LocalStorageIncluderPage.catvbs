Language="VBSCRIPT"

Sub CATMain()

Set settingControllers1 = CATIA.SettingControllers

Set settingRepository1 = settingControllers1.Item("LocalStorage")

bSTR1 = settingRepository1.GetAttr("LSManagedPath")
'--------------------------------------------------
' Parameter 1 : (String) "LSManagedPath"
' Returned value : (Variant) (String) "CSIDL_LOCAL_APPDATA"
'--------------------------------------------------

Dim bSTR2
bSTR2 = ""
Dim bSTR3
bSTR3 = ""
Dim boolean1
settingRepository1.GetAttrInfo "LSManagedPath", bSTR2, bSTR3, boolean1
'--------------------------------------------------
' Parameter 1 : (String) "LSManagedPath"
' Parameter 2 : (String) "Default value"
' Parameter 3 : (String) "Unlocked"
' Parameter 4 : (Boolean) False
'--------------------------------------------------

End Sub
