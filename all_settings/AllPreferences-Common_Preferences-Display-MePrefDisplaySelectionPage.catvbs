Language="VBSCRIPT"

Sub CATMain()

Set settingControllers1 = CATIA.SettingControllers

Set settingRepository1 = settingControllers1.Item("VisualizationRepository")

boolean1 = settingRepository1.GetAttr("PreSelection")
'--------------------------------------------------
' Parameter 1 : (String) "PreSelection"
' Returned value : (Variant) (Boolean) True
'--------------------------------------------------

Dim bSTR1
bSTR1 = ""
Dim bSTR2
bSTR2 = ""
Dim boolean2
settingRepository1.GetAttrInfo "PreSelection", bSTR1, bSTR2, boolean2
'--------------------------------------------------
' Parameter 1 : (String) "PreSelection"
' Parameter 2 : (String) "Default value"
' Parameter 3 : (String) "Unlocked"
' Parameter 4 : (Boolean) False
'--------------------------------------------------

boolean3 = settingRepository1.GetAttr("PreSelNavigatorStartedByArrowKeys")
'--------------------------------------------------
' Parameter 1 : (String) "PreSelNavigatorStartedByArrowKeys"
' Returned value : (Variant) (Boolean) False
'--------------------------------------------------

Dim bSTR3
bSTR3 = ""
Dim bSTR4
bSTR4 = ""
Dim boolean4
settingRepository1.GetAttrInfo "PreSelNavigatorStartedByArrowKeys", bSTR3, bSTR4, boolean4
'--------------------------------------------------
' Parameter 1 : (String) "PreSelNavigatorStartedByArrowKeys"
' Parameter 2 : (String) "Default value"
' Parameter 3 : (String) "Unlocked"
' Parameter 4 : (Boolean) False
'--------------------------------------------------

boolean5 = settingRepository1.GetAttr("HighlightActivation")
'--------------------------------------------------
' Parameter 1 : (String) "HighlightActivation"
' Returned value : (Variant) (Boolean) True
'--------------------------------------------------

Dim bSTR5
bSTR5 = ""
Dim bSTR6
bSTR6 = ""
Dim boolean6
settingRepository1.GetAttrInfo "HighlightActivation", bSTR5, bSTR6, boolean6
'--------------------------------------------------
' Parameter 1 : (String) "HighlightActivation"
' Parameter 2 : (String) "Default value"
' Parameter 3 : (String) "Unlocked"
' Parameter 4 : (Boolean) False
'--------------------------------------------------

uLong1 = settingRepository1.GetAttr("MaxSelectionMove")
'--------------------------------------------------
' Parameter 1 : (String) "MaxSelectionMove"
' Returned value : (Variant) (Unsigned Long) 50
'--------------------------------------------------

Dim bSTR7
bSTR7 = ""
Dim bSTR8
bSTR8 = ""
Dim boolean7
settingRepository1.GetAttrInfo "MaxSelectionMove", bSTR7, bSTR8, boolean7
'--------------------------------------------------
' Parameter 1 : (String) "MaxSelectionMove"
' Parameter 2 : (String) "Default value"
' Parameter 3 : (String) "Unlocked"
' Parameter 4 : (Boolean) False
'--------------------------------------------------

boolean8 = settingRepository1.GetAttr("DrillListDisplay")
'--------------------------------------------------
' Parameter 1 : (String) "DrillListDisplay"
' Returned value : (Variant) (Boolean) True
'--------------------------------------------------

Dim bSTR9
bSTR9 = ""
Dim bSTR10
bSTR10 = ""
Dim boolean9
settingRepository1.GetAttrInfo "DrillListDisplay", bSTR9, bSTR10, boolean9
'--------------------------------------------------
' Parameter 1 : (String) "DrillListDisplay"
' Parameter 2 : (String) "Default value"
' Parameter 3 : (String) "Unlocked"
' Parameter 4 : (Boolean) False
'--------------------------------------------------

boolean10 = settingRepository1.GetAttr("AuxiliaryDrillViewer")
'--------------------------------------------------
' Parameter 1 : (String) "AuxiliaryDrillViewer"
' Returned value : (Variant) (Boolean) False
'--------------------------------------------------

Dim bSTR11
bSTR11 = ""
Dim bSTR12
bSTR12 = ""
Dim boolean11
settingRepository1.GetAttrInfo "AuxiliaryDrillViewer", bSTR11, bSTR12, boolean11
'--------------------------------------------------
' Parameter 1 : (String) "AuxiliaryDrillViewer"
' Parameter 2 : (String) "Default value"
' Parameter 3 : (String) "Unlocked"
' Parameter 4 : (Boolean) False
'--------------------------------------------------

boolean12 = settingRepository1.GetAttr("FaceHLDrill")
'--------------------------------------------------
' Parameter 1 : (String) "FaceHLDrill"
' Returned value : (Variant) (Boolean) False
'--------------------------------------------------

Dim bSTR13
bSTR13 = ""
Dim bSTR14
bSTR14 = ""
Dim boolean13
settingRepository1.GetAttrInfo "FaceHLDrill", bSTR13, bSTR14, boolean13
'--------------------------------------------------
' Parameter 1 : (String) "FaceHLDrill"
' Parameter 2 : (String) "Default value"
' Parameter 3 : (String) "Unlocked"
' Parameter 4 : (Boolean) False
'--------------------------------------------------

boolean14 = settingRepository1.GetAttr("DisplayImmersiveDrillViewer")
'--------------------------------------------------
' Parameter 1 : (String) "DisplayImmersiveDrillViewer"
' Returned value : (Variant) (Boolean) True
'--------------------------------------------------

Dim bSTR15
bSTR15 = ""
Dim bSTR16
bSTR16 = ""
Dim boolean15
settingRepository1.GetAttrInfo "DisplayImmersiveDrillViewer", bSTR15, bSTR16, boolean15
'--------------------------------------------------
' Parameter 1 : (String) "DisplayImmersiveDrillViewer"
' Parameter 2 : (String) "Default value"
' Parameter 3 : (String) "Unlocked"
' Parameter 4 : (Boolean) False
'--------------------------------------------------

boolean16 = settingRepository1.GetAttr("HighlightHiddenObjects")
'--------------------------------------------------
' Parameter 1 : (String) "HighlightHiddenObjects"
' Returned value : (Variant) (Boolean) False
'--------------------------------------------------

Dim bSTR17
bSTR17 = ""
Dim bSTR18
bSTR18 = ""
Dim boolean17
settingRepository1.GetAttrInfo "HighlightHiddenObjects", bSTR17, bSTR18, boolean17
'--------------------------------------------------
' Parameter 1 : (String) "HighlightHiddenObjects"
' Parameter 2 : (String) "Default value"
' Parameter 3 : (String) "Unlocked"
' Parameter 4 : (Boolean) False
'--------------------------------------------------

boolean18 = settingRepository1.GetAttr("PreHighlightHiddenObjects")
'--------------------------------------------------
' Parameter 1 : (String) "PreHighlightHiddenObjects"
' Returned value : (Variant) (Boolean) False
'--------------------------------------------------

Dim bSTR19
bSTR19 = ""
Dim bSTR20
bSTR20 = ""
Dim boolean19
settingRepository1.GetAttrInfo "PreHighlightHiddenObjects", bSTR19, bSTR20, boolean19
'--------------------------------------------------
' Parameter 1 : (String) "PreHighlightHiddenObjects"
' Parameter 2 : (String) "Default value"
' Parameter 3 : (String) "Unlocked"
' Parameter 4 : (Boolean) False
'--------------------------------------------------

uLong2 = settingRepository1.GetAttr("GhostedTransparencyValue")
'--------------------------------------------------
' Parameter 1 : (String) "GhostedTransparencyValue"
' Returned value : (Variant) (Unsigned Long) 90
'--------------------------------------------------

Dim bSTR21
bSTR21 = ""
Dim bSTR22
bSTR22 = ""
Dim boolean20
settingRepository1.GetAttrInfo "GhostedTransparencyValue", bSTR21, bSTR22, boolean20
'--------------------------------------------------
' Parameter 1 : (String) "GhostedTransparencyValue"
' Parameter 2 : (String) "Default value"
' Parameter 3 : (String) "Unlocked"
' Parameter 4 : (Boolean) False
'--------------------------------------------------

boolean21 = settingRepository1.GetAttr("GhostingAllInstancesValue")
'--------------------------------------------------
' Parameter 1 : (String) "GhostingAllInstancesValue"
' Returned value : (Variant) (Boolean) False
'--------------------------------------------------

Dim bSTR23
bSTR23 = ""
Dim bSTR24
bSTR24 = ""
Dim boolean22
settingRepository1.GetAttrInfo "GhostingAllInstancesValue", bSTR23, bSTR24, boolean22
'--------------------------------------------------
' Parameter 1 : (String) "GhostingAllInstancesValue"
' Parameter 2 : (String) "Default value"
' Parameter 3 : (String) "Unlocked"
' Parameter 4 : (Boolean) False
'--------------------------------------------------

uLong3 = settingRepository1.GetAttr("HighlightMode")
'--------------------------------------------------
' Parameter 1 : (String) "HighlightMode"
' Returned value : (Variant) (Unsigned Long) 3
'--------------------------------------------------

Dim bSTR25
bSTR25 = ""
Dim bSTR26
bSTR26 = ""
Dim boolean23
settingRepository1.GetAttrInfo "HighlightMode", bSTR25, bSTR26, boolean23
'--------------------------------------------------
' Parameter 1 : (String) "HighlightMode"
' Parameter 2 : (String) "Default value"
' Parameter 3 : (String) "Unlocked"
' Parameter 4 : (Boolean) False
'--------------------------------------------------

Dim arrayOfVariantOfULong1
arrayOfVariantOfULong1 = settingRepository1.GetAttrArray("Highlight")
'--------------------------------------------------
' Parameter 1 : (String) "Highlight"
' Returned value : (Array) 
'    Array[0] : (Variant) (Unsigned Long) 0
'    Array[1] : (Variant) (Unsigned Long) 200
'    Array[2] : (Variant) (Unsigned Long) 200
'--------------------------------------------------

Dim bSTR27
bSTR27 = ""
Dim bSTR28
bSTR28 = ""
Dim boolean24
settingRepository1.GetAttrInfo "Highlight", bSTR27, bSTR28, boolean24
'--------------------------------------------------
' Parameter 1 : (String) "Highlight"
' Parameter 2 : (String) "Default value"
' Parameter 3 : (String) "Unlocked"
' Parameter 4 : (Boolean) False
'--------------------------------------------------

Dim arrayOfVariantOfULong2
arrayOfVariantOfULong2 = settingRepository1.GetAttrArray("EdgeHighlight")
'--------------------------------------------------
' Parameter 1 : (String) "EdgeHighlight"
' Returned value : (Array) 
'    Array[0] : (Variant) (Unsigned Long) 255
'    Array[1] : (Variant) (Unsigned Long) 0
'    Array[2] : (Variant) (Unsigned Long) 0
'--------------------------------------------------

Dim bSTR29
bSTR29 = ""
Dim bSTR30
bSTR30 = ""
Dim boolean25
settingRepository1.GetAttrInfo "EdgeHighlight", bSTR29, bSTR30, boolean25
'--------------------------------------------------
' Parameter 1 : (String) "EdgeHighlight"
' Parameter 2 : (String) "Default value"
' Parameter 3 : (String) "Unlocked"
' Parameter 4 : (Boolean) False
'--------------------------------------------------

uLong4 = settingRepository1.GetAttr("PreHighlightMode")
'--------------------------------------------------
' Parameter 1 : (String) "PreHighlightMode"
' Returned value : (Variant) (Unsigned Long) 3
'--------------------------------------------------

Dim bSTR31
bSTR31 = ""
Dim bSTR32
bSTR32 = ""
Dim boolean26
settingRepository1.GetAttrInfo "PreHighlightMode", bSTR31, bSTR32, boolean26
'--------------------------------------------------
' Parameter 1 : (String) "PreHighlightMode"
' Parameter 2 : (String) "Default value"
' Parameter 3 : (String) "Unlocked"
' Parameter 4 : (Boolean) False
'--------------------------------------------------

Dim arrayOfVariantOfULong3
arrayOfVariantOfULong3 = settingRepository1.GetAttrArray("PrehighlightColor")
'--------------------------------------------------
' Parameter 1 : (String) "PrehighlightColor"
' Returned value : (Array) 
'    Array[0] : (Variant) (Unsigned Long) 247
'    Array[1] : (Variant) (Unsigned Long) 247
'    Array[2] : (Variant) (Unsigned Long) 247
'--------------------------------------------------

Dim bSTR33
bSTR33 = ""
Dim bSTR34
bSTR34 = ""
Dim boolean27
settingRepository1.GetAttrInfo "PrehighlightColor", bSTR33, bSTR34, boolean27
'--------------------------------------------------
' Parameter 1 : (String) "PrehighlightColor"
' Parameter 2 : (String) "Default value"
' Parameter 3 : (String) "Unlocked"
' Parameter 4 : (Boolean) False
'--------------------------------------------------

uLong5 = settingRepository1.GetAttr("PreHighlight")
'--------------------------------------------------
' Parameter 1 : (String) "PreHighlight"
' Returned value : (Variant) (Unsigned Long) 4
'--------------------------------------------------

Dim bSTR35
bSTR35 = ""
Dim bSTR36
bSTR36 = ""
Dim boolean28
settingRepository1.GetAttrInfo "PreHighlight", bSTR35, bSTR36, boolean28
'--------------------------------------------------
' Parameter 1 : (String) "PreHighlight"
' Parameter 2 : (String) "Default value"
' Parameter 3 : (String) "Unlocked"
' Parameter 4 : (Boolean) False
'--------------------------------------------------

boolean29 = settingRepository1.GetAttr("Selection")
'--------------------------------------------------
' Parameter 1 : (String) "Selection"
' Returned value : (Variant) (Boolean) False
'--------------------------------------------------

Dim bSTR37
bSTR37 = ""
Dim bSTR38
bSTR38 = ""
Dim boolean30
settingRepository1.GetAttrInfo "Selection", bSTR37, bSTR38, boolean30
'--------------------------------------------------
' Parameter 1 : (String) "Selection"
' Parameter 2 : (String) "Default value"
' Parameter 3 : (String) "Unlocked"
' Parameter 4 : (Boolean) False
'--------------------------------------------------

float1 = settingRepository1.GetAttr("Delay")
'--------------------------------------------------
' Parameter 1 : (String) "Delay"
' Returned value : (Variant) (Float) 2.000000
'--------------------------------------------------

Dim bSTR39
bSTR39 = ""
Dim bSTR40
bSTR40 = ""
Dim boolean31
settingRepository1.GetAttrInfo "Delay", bSTR39, bSTR40, boolean31
'--------------------------------------------------
' Parameter 1 : (String) "Delay"
' Parameter 2 : (String) "Default value"
' Parameter 3 : (String) "Unlocked"
' Parameter 4 : (Boolean) False
'--------------------------------------------------

boolean32 = settingRepository1.GetAttr("Bounding Box")
'--------------------------------------------------
' Parameter 1 : (String) "Bounding Box"
' Returned value : (Variant) (Boolean) False
'--------------------------------------------------

Dim bSTR41
bSTR41 = ""
Dim bSTR42
bSTR42 = ""
Dim boolean33
settingRepository1.GetAttrInfo "Bounding Box", bSTR41, bSTR42, boolean33
'--------------------------------------------------
' Parameter 1 : (String) "Bounding Box"
' Parameter 2 : (String) "Default value"
' Parameter 3 : (String) "Unlocked"
' Parameter 4 : (Boolean) False
'--------------------------------------------------

End Sub
