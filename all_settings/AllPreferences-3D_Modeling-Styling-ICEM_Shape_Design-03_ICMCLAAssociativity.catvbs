Language="VBSCRIPT"

Sub CATMain()

Set settingControllers1 = CATIA.SettingControllers

Set settingRepository1 = settingControllers1.Item("ICMCLAAssociativitySettings")

bSTR1 = settingRepository1.GetAttr("Local")
'--------------------------------------------------
' Parameter 1 : (String) "Local"
' Returned value : (Variant) (String) "1"
'--------------------------------------------------

Dim bSTR2
bSTR2 = ""
Dim bSTR3
bSTR3 = ""
Dim boolean1
settingRepository1.GetAttrInfo "Local", bSTR2, bSTR3, boolean1
'--------------------------------------------------
' Parameter 1 : (String) "Local"
' Parameter 2 : (String) "Default value"
' Parameter 3 : (String) "Unlocked"
' Parameter 4 : (Boolean) False
'--------------------------------------------------

long1 = settingRepository1.GetAttr("DummyLocal")
'--------------------------------------------------
' Parameter 1 : (String) "DummyLocal"
' Returned value : (Variant) (Long) 0
'--------------------------------------------------

Dim bSTR4
bSTR4 = ""
Dim bSTR5
bSTR5 = ""
Dim boolean2
settingRepository1.GetAttrInfo "DummyLocal", bSTR4, bSTR5, boolean2
'--------------------------------------------------
' Parameter 1 : (String) "DummyLocal"
' Parameter 2 : (String) "Default value"
' Parameter 3 : (String) "Unlocked"
' Parameter 4 : (Boolean) False
'--------------------------------------------------

bSTR6 = settingRepository1.GetAttr("ICMCLA3dCurveFss")
'--------------------------------------------------
' Parameter 1 : (String) "ICMCLA3dCurveFss"
' Returned value : (Variant) (String) "1"
'--------------------------------------------------

Dim bSTR7
bSTR7 = ""
Dim bSTR8
bSTR8 = ""
Dim boolean3
settingRepository1.GetAttrInfo "ICMCLA3dCurveFss", bSTR7, bSTR8, boolean3
'--------------------------------------------------
' Parameter 1 : (String) "ICMCLA3dCurveFss"
' Parameter 2 : (String) "Default value"
' Parameter 3 : (String) "Unlocked"
' Parameter 4 : (Boolean) False
'--------------------------------------------------

bSTR9 = settingRepository1.GetAttr("ICMDSIsoparametricCurveDef")
'--------------------------------------------------
' Parameter 1 : (String) "ICMDSIsoparametricCurveDef"
' Returned value : (Variant) (String) "1"
'--------------------------------------------------

Dim bSTR10
bSTR10 = ""
Dim bSTR11
bSTR11 = ""
Dim boolean4
settingRepository1.GetAttrInfo "ICMDSIsoparametricCurveDef", bSTR10, bSTR11, boolean4
'--------------------------------------------------
' Parameter 1 : (String) "ICMDSIsoparametricCurveDef"
' Parameter 2 : (String) "Default value"
' Parameter 3 : (String) "Unlocked"
' Parameter 4 : (Boolean) False
'--------------------------------------------------

bSTR12 = settingRepository1.GetAttr("ICMCLAShapeProjectCmd")
'--------------------------------------------------
' Parameter 1 : (String) "ICMCLAShapeProjectCmd"
' Returned value : (Variant) (String) "1"
'--------------------------------------------------

Dim bSTR13
bSTR13 = ""
Dim bSTR14
bSTR14 = ""
Dim boolean5
settingRepository1.GetAttrInfo "ICMCLAShapeProjectCmd", bSTR13, bSTR14, boolean5
'--------------------------------------------------
' Parameter 1 : (String) "ICMCLAShapeProjectCmd"
' Parameter 2 : (String) "Default value"
' Parameter 3 : (String) "Unlocked"
' Parameter 4 : (Boolean) False
'--------------------------------------------------

bSTR15 = settingRepository1.GetAttr("ICMCLAShapeStylingCornerCmd")
'--------------------------------------------------
' Parameter 1 : (String) "ICMCLAShapeStylingCornerCmd"
' Returned value : (Variant) (String) "1"
'--------------------------------------------------

Dim bSTR16
bSTR16 = ""
Dim bSTR17
bSTR17 = ""
Dim boolean6
settingRepository1.GetAttrInfo "ICMCLAShapeStylingCornerCmd", bSTR16, bSTR17, boolean6
'--------------------------------------------------
' Parameter 1 : (String) "ICMCLAShapeStylingCornerCmd"
' Parameter 2 : (String) "Default value"
' Parameter 3 : (String) "Unlocked"
' Parameter 4 : (Boolean) False
'--------------------------------------------------

bSTR18 = settingRepository1.GetAttr("ICMCLAShapeCurveBlendCmd")
'--------------------------------------------------
' Parameter 1 : (String) "ICMCLAShapeCurveBlendCmd"
' Returned value : (Variant) (String) "1"
'--------------------------------------------------

Dim bSTR19
bSTR19 = ""
Dim bSTR20
bSTR20 = ""
Dim boolean7
settingRepository1.GetAttrInfo "ICMCLAShapeCurveBlendCmd", bSTR19, bSTR20, boolean7
'--------------------------------------------------
' Parameter 1 : (String) "ICMCLAShapeCurveBlendCmd"
' Parameter 2 : (String) "Default value"
' Parameter 3 : (String) "Unlocked"
' Parameter 4 : (Boolean) False
'--------------------------------------------------

bSTR21 = settingRepository1.GetAttr("ICMCLAShapeCurveOffsetCmd")
'--------------------------------------------------
' Parameter 1 : (String) "ICMCLAShapeCurveOffsetCmd"
' Returned value : (Variant) (String) "1"
'--------------------------------------------------

Dim bSTR22
bSTR22 = ""
Dim bSTR23
bSTR23 = ""
Dim boolean8
settingRepository1.GetAttrInfo "ICMCLAShapeCurveOffsetCmd", bSTR22, bSTR23, boolean8
'--------------------------------------------------
' Parameter 1 : (String) "ICMCLAShapeCurveOffsetCmd"
' Parameter 2 : (String) "Default value"
' Parameter 3 : (String) "Unlocked"
' Parameter 4 : (Boolean) False
'--------------------------------------------------

bSTR24 = settingRepository1.GetAttr("ICMCLAShapeSplitCurveCmd")
'--------------------------------------------------
' Parameter 1 : (String) "ICMCLAShapeSplitCurveCmd"
' Returned value : (Variant) (String) "1"
'--------------------------------------------------

Dim bSTR25
bSTR25 = ""
Dim bSTR26
bSTR26 = ""
Dim boolean9
settingRepository1.GetAttrInfo "ICMCLAShapeSplitCurveCmd", bSTR25, bSTR26, boolean9
'--------------------------------------------------
' Parameter 1 : (String) "ICMCLAShapeSplitCurveCmd"
' Parameter 2 : (String) "Default value"
' Parameter 3 : (String) "Unlocked"
' Parameter 4 : (Boolean) False
'--------------------------------------------------

bSTR27 = settingRepository1.GetAttr("ICMCLAShapeIntersectionCmd")
'--------------------------------------------------
' Parameter 1 : (String) "ICMCLAShapeIntersectionCmd"
' Returned value : (Variant) (String) "1"
'--------------------------------------------------

Dim bSTR28
bSTR28 = ""
Dim bSTR29
bSTR29 = ""
Dim boolean10
settingRepository1.GetAttrInfo "ICMCLAShapeIntersectionCmd", bSTR28, bSTR29, boolean10
'--------------------------------------------------
' Parameter 1 : (String) "ICMCLAShapeIntersectionCmd"
' Parameter 2 : (String) "Default value"
' Parameter 3 : (String) "Unlocked"
' Parameter 4 : (Boolean) False
'--------------------------------------------------

bSTR30 = settingRepository1.GetAttr("ICMCLAShapeRevolSurfaceCmd")
'--------------------------------------------------
' Parameter 1 : (String) "ICMCLAShapeRevolSurfaceCmd"
' Returned value : (Variant) (String) "1"
'--------------------------------------------------

Dim bSTR31
bSTR31 = ""
Dim bSTR32
bSTR32 = ""
Dim boolean11
settingRepository1.GetAttrInfo "ICMCLAShapeRevolSurfaceCmd", bSTR31, bSTR32, boolean11
'--------------------------------------------------
' Parameter 1 : (String) "ICMCLAShapeRevolSurfaceCmd"
' Parameter 2 : (String) "Default value"
' Parameter 3 : (String) "Unlocked"
' Parameter 4 : (Boolean) False
'--------------------------------------------------

bSTR33 = settingRepository1.GetAttr("ICMCLAShapePatchFromCurves2Cmd")
'--------------------------------------------------
' Parameter 1 : (String) "ICMCLAShapePatchFromCurves2Cmd"
' Returned value : (Variant) (String) "1"
'--------------------------------------------------

Dim bSTR34
bSTR34 = ""
Dim bSTR35
bSTR35 = ""
Dim boolean12
settingRepository1.GetAttrInfo "ICMCLAShapePatchFromCurves2Cmd", bSTR34, bSTR35, boolean12
'--------------------------------------------------
' Parameter 1 : (String) "ICMCLAShapePatchFromCurves2Cmd"
' Parameter 2 : (String) "Default value"
' Parameter 3 : (String) "Unlocked"
' Parameter 4 : (Boolean) False
'--------------------------------------------------

bSTR36 = settingRepository1.GetAttr("ICMCLAShapePatchFromPatchesCmd")
'--------------------------------------------------
' Parameter 1 : (String) "ICMCLAShapePatchFromPatchesCmd"
' Returned value : (Variant) (String) "1"
'--------------------------------------------------

Dim bSTR37
bSTR37 = ""
Dim bSTR38
bSTR38 = ""
Dim boolean13
settingRepository1.GetAttrInfo "ICMCLAShapePatchFromPatchesCmd", bSTR37, bSTR38, boolean13
'--------------------------------------------------
' Parameter 1 : (String) "ICMCLAShapePatchFromPatchesCmd"
' Parameter 2 : (String) "Default value"
' Parameter 3 : (String) "Unlocked"
' Parameter 4 : (Boolean) False
'--------------------------------------------------

bSTR39 = settingRepository1.GetAttr("ICMCLAShapeFlangeCmd")
'--------------------------------------------------
' Parameter 1 : (String) "ICMCLAShapeFlangeCmd"
' Returned value : (Variant) (String) "1"
'--------------------------------------------------

Dim bSTR40
bSTR40 = ""
Dim bSTR41
bSTR41 = ""
Dim boolean14
settingRepository1.GetAttrInfo "ICMCLAShapeFlangeCmd", bSTR40, bSTR41, boolean14
'--------------------------------------------------
' Parameter 1 : (String) "ICMCLAShapeFlangeCmd"
' Parameter 2 : (String) "Default value"
' Parameter 3 : (String) "Unlocked"
' Parameter 4 : (Boolean) False
'--------------------------------------------------

bSTR42 = settingRepository1.GetAttr("ICMCLAShapeFilletFlangeCmd")
'--------------------------------------------------
' Parameter 1 : (String) "ICMCLAShapeFilletFlangeCmd"
' Returned value : (Variant) (String) "1"
'--------------------------------------------------

Dim bSTR43
bSTR43 = ""
Dim bSTR44
bSTR44 = ""
Dim boolean15
settingRepository1.GetAttrInfo "ICMCLAShapeFilletFlangeCmd", bSTR43, bSTR44, boolean15
'--------------------------------------------------
' Parameter 1 : (String) "ICMCLAShapeFilletFlangeCmd"
' Parameter 2 : (String) "Default value"
' Parameter 3 : (String) "Unlocked"
' Parameter 4 : (Boolean) False
'--------------------------------------------------

bSTR45 = settingRepository1.GetAttr("ICMClassAFilletFSS")
'--------------------------------------------------
' Parameter 1 : (String) "ICMClassAFilletFSS"
' Returned value : (Variant) (String) "1"
'--------------------------------------------------

Dim bSTR46
bSTR46 = ""
Dim bSTR47
bSTR47 = ""
Dim boolean16
settingRepository1.GetAttrInfo "ICMClassAFilletFSS", bSTR46, bSTR47, boolean16
'--------------------------------------------------
' Parameter 1 : (String) "ICMClassAFilletFSS"
' Parameter 2 : (String) "Default value"
' Parameter 3 : (String) "Unlocked"
' Parameter 4 : (Boolean) False
'--------------------------------------------------

bSTR48 = settingRepository1.GetAttr("ICMCLAShapeFillCmd")
'--------------------------------------------------
' Parameter 1 : (String) "ICMCLAShapeFillCmd"
' Returned value : (Variant) (String) "1"
'--------------------------------------------------

Dim bSTR49
bSTR49 = ""
Dim bSTR50
bSTR50 = ""
Dim boolean17
settingRepository1.GetAttrInfo "ICMCLAShapeFillCmd", bSTR49, bSTR50, boolean17
'--------------------------------------------------
' Parameter 1 : (String) "ICMCLAShapeFillCmd"
' Parameter 2 : (String) "Default value"
' Parameter 3 : (String) "Unlocked"
' Parameter 4 : (Boolean) False
'--------------------------------------------------

bSTR51 = settingRepository1.GetAttr("ICMCLAShapeSurfaceOffset2Cmd")
'--------------------------------------------------
' Parameter 1 : (String) "ICMCLAShapeSurfaceOffset2Cmd"
' Returned value : (Variant) (String) "1"
'--------------------------------------------------

Dim bSTR52
bSTR52 = ""
Dim bSTR53
bSTR53 = ""
Dim boolean18
settingRepository1.GetAttrInfo "ICMCLAShapeSurfaceOffset2Cmd", bSTR52, bSTR53, boolean18
'--------------------------------------------------
' Parameter 1 : (String) "ICMCLAShapeSurfaceOffset2Cmd"
' Parameter 2 : (String) "Default value"
' Parameter 3 : (String) "Unlocked"
' Parameter 4 : (Boolean) False
'--------------------------------------------------

bSTR54 = settingRepository1.GetAttr("ICMCLAShapeSurfaceBlendCmd")
'--------------------------------------------------
' Parameter 1 : (String) "ICMCLAShapeSurfaceBlendCmd"
' Returned value : (Variant) (String) "1"
'--------------------------------------------------

Dim bSTR55
bSTR55 = ""
Dim bSTR56
bSTR56 = ""
Dim boolean19
settingRepository1.GetAttrInfo "ICMCLAShapeSurfaceBlendCmd", bSTR55, bSTR56, boolean19
'--------------------------------------------------
' Parameter 1 : (String) "ICMCLAShapeSurfaceBlendCmd"
' Parameter 2 : (String) "Default value"
' Parameter 3 : (String) "Unlocked"
' Parameter 4 : (Boolean) False
'--------------------------------------------------

bSTR57 = settingRepository1.GetAttr("ICMCLAShapeSweepCmd")
'--------------------------------------------------
' Parameter 1 : (String) "ICMCLAShapeSweepCmd"
' Returned value : (Variant) (String) "1"
'--------------------------------------------------

Dim bSTR58
bSTR58 = ""
Dim bSTR59
bSTR59 = ""
Dim boolean20
settingRepository1.GetAttrInfo "ICMCLAShapeSweepCmd", bSTR58, bSTR59, boolean20
'--------------------------------------------------
' Parameter 1 : (String) "ICMCLAShapeSweepCmd"
' Parameter 2 : (String) "Default value"
' Parameter 3 : (String) "Unlocked"
' Parameter 4 : (Boolean) False
'--------------------------------------------------

bSTR60 = settingRepository1.GetAttr("ICMCLAShapeAdjustCmd")
'--------------------------------------------------
' Parameter 1 : (String) "ICMCLAShapeAdjustCmd"
' Returned value : (Variant) (String) "1"
'--------------------------------------------------

Dim bSTR61
bSTR61 = ""
Dim bSTR62
bSTR62 = ""
Dim boolean21
settingRepository1.GetAttrInfo "ICMCLAShapeAdjustCmd", bSTR61, bSTR62, boolean21
'--------------------------------------------------
' Parameter 1 : (String) "ICMCLAShapeAdjustCmd"
' Parameter 2 : (String) "Default value"
' Parameter 3 : (String) "Unlocked"
' Parameter 4 : (Boolean) False
'--------------------------------------------------

bSTR63 = settingRepository1.GetAttr("ICMCLAShapeCreateGapCmd")
'--------------------------------------------------
' Parameter 1 : (String) "ICMCLAShapeCreateGapCmd"
' Returned value : (Variant) (String) "1"
'--------------------------------------------------

Dim bSTR64
bSTR64 = ""
Dim bSTR65
bSTR65 = ""
Dim boolean22
settingRepository1.GetAttrInfo "ICMCLAShapeCreateGapCmd", bSTR64, bSTR65, boolean22
'--------------------------------------------------
' Parameter 1 : (String) "ICMCLAShapeCreateGapCmd"
' Parameter 2 : (String) "Default value"
' Parameter 3 : (String) "Unlocked"
' Parameter 4 : (Boolean) False
'--------------------------------------------------

bSTR66 = settingRepository1.GetAttr("ICMCLAShapeLoftCmd")
'--------------------------------------------------
' Parameter 1 : (String) "ICMCLAShapeLoftCmd"
' Returned value : (Variant) (String) "1"
'--------------------------------------------------

Dim bSTR67
bSTR67 = ""
Dim bSTR68
bSTR68 = ""
Dim boolean23
settingRepository1.GetAttrInfo "ICMCLAShapeLoftCmd", bSTR67, bSTR68, boolean23
'--------------------------------------------------
' Parameter 1 : (String) "ICMCLAShapeLoftCmd"
' Parameter 2 : (String) "Default value"
' Parameter 3 : (String) "Unlocked"
' Parameter 4 : (Boolean) False
'--------------------------------------------------

bSTR69 = settingRepository1.GetAttr("ICMCLAShapeFeatureModelingCmd")
'--------------------------------------------------
' Parameter 1 : (String) "ICMCLAShapeFeatureModelingCmd"
' Returned value : (Variant) (String) "1"
'--------------------------------------------------

Dim bSTR70
bSTR70 = ""
Dim bSTR71
bSTR71 = ""
Dim boolean24
settingRepository1.GetAttrInfo "ICMCLAShapeFeatureModelingCmd", bSTR70, bSTR71, boolean24
'--------------------------------------------------
' Parameter 1 : (String) "ICMCLAShapeFeatureModelingCmd"
' Parameter 2 : (String) "Default value"
' Parameter 3 : (String) "Unlocked"
' Parameter 4 : (Boolean) False
'--------------------------------------------------

bSTR72 = settingRepository1.GetAttr("ICMCLAShapeRefitCmd")
'--------------------------------------------------
' Parameter 1 : (String) "ICMCLAShapeRefitCmd"
' Returned value : (Variant) (String) "1"
'--------------------------------------------------

Dim bSTR73
bSTR73 = ""
Dim bSTR74
bSTR74 = ""
Dim boolean25
settingRepository1.GetAttrInfo "ICMCLAShapeRefitCmd", bSTR73, bSTR74, boolean25
'--------------------------------------------------
' Parameter 1 : (String) "ICMCLAShapeRefitCmd"
' Parameter 2 : (String) "Default value"
' Parameter 3 : (String) "Unlocked"
' Parameter 4 : (Boolean) False
'--------------------------------------------------

bSTR75 = settingRepository1.GetAttr("ICMCLAShapeExtrapolationFeatCmd")
'--------------------------------------------------
' Parameter 1 : (String) "ICMCLAShapeExtrapolationFeatCmd"
' Returned value : (Variant) (String) "1"
'--------------------------------------------------

Dim bSTR76
bSTR76 = ""
Dim bSTR77
bSTR77 = ""
Dim boolean26
settingRepository1.GetAttrInfo "ICMCLAShapeExtrapolationFeatCmd", bSTR76, bSTR77, boolean26
'--------------------------------------------------
' Parameter 1 : (String) "ICMCLAShapeExtrapolationFeatCmd"
' Parameter 2 : (String) "Default value"
' Parameter 3 : (String) "Unlocked"
' Parameter 4 : (Boolean) False
'--------------------------------------------------

bSTR78 = settingRepository1.GetAttr("ICMDSUntrimFeatureDef")
'--------------------------------------------------
' Parameter 1 : (String) "ICMDSUntrimFeatureDef"
' Returned value : (Variant) (String) "1"
'--------------------------------------------------

Dim bSTR79
bSTR79 = ""
Dim bSTR80
bSTR80 = ""
Dim boolean27
settingRepository1.GetAttrInfo "ICMDSUntrimFeatureDef", bSTR79, bSTR80, boolean27
'--------------------------------------------------
' Parameter 1 : (String) "ICMDSUntrimFeatureDef"
' Parameter 2 : (String) "Default value"
' Parameter 3 : (String) "Unlocked"
' Parameter 4 : (Boolean) False
'--------------------------------------------------

bSTR81 = settingRepository1.GetAttr("ICMCLAShapeConversionCmd")
'--------------------------------------------------
' Parameter 1 : (String) "ICMCLAShapeConversionCmd"
' Returned value : (Variant) (String) "1"
'--------------------------------------------------

Dim bSTR82
bSTR82 = ""
Dim bSTR83
bSTR83 = ""
Dim boolean28
settingRepository1.GetAttrInfo "ICMCLAShapeConversionCmd", bSTR82, bSTR83, boolean28
'--------------------------------------------------
' Parameter 1 : (String) "ICMCLAShapeConversionCmd"
' Parameter 2 : (String) "Default value"
' Parameter 3 : (String) "Unlocked"
' Parameter 4 : (Boolean) False
'--------------------------------------------------

bSTR84 = settingRepository1.GetAttr("ICMCLAShapeSurfaceConversionCmd")
'--------------------------------------------------
' Parameter 1 : (String) "ICMCLAShapeSurfaceConversionCmd"
' Returned value : (Variant) (String) "1"
'--------------------------------------------------

Dim bSTR85
bSTR85 = ""
Dim bSTR86
bSTR86 = ""
Dim boolean29
settingRepository1.GetAttrInfo "ICMCLAShapeSurfaceConversionCmd", bSTR85, bSTR86, boolean29
'--------------------------------------------------
' Parameter 1 : (String) "ICMCLAShapeSurfaceConversionCmd"
' Parameter 2 : (String) "Default value"
' Parameter 3 : (String) "Unlocked"
' Parameter 4 : (Boolean) False
'--------------------------------------------------

bSTR87 = settingRepository1.GetAttr("ICMCLAShapeHelixCmd")
'--------------------------------------------------
' Parameter 1 : (String) "ICMCLAShapeHelixCmd"
' Returned value : (Variant) (String) "1"
'--------------------------------------------------

Dim bSTR88
bSTR88 = ""
Dim bSTR89
bSTR89 = ""
Dim boolean30
settingRepository1.GetAttrInfo "ICMCLAShapeHelixCmd", bSTR88, bSTR89, boolean30
'--------------------------------------------------
' Parameter 1 : (String) "ICMCLAShapeHelixCmd"
' Parameter 2 : (String) "Default value"
' Parameter 3 : (String) "Unlocked"
' Parameter 4 : (Boolean) False
'--------------------------------------------------

bSTR90 = settingRepository1.GetAttr("ICMCLAShapeFilletCmd")
'--------------------------------------------------
' Parameter 1 : (String) "ICMCLAShapeFilletCmd"
' Returned value : (Variant) (String) "1"
'--------------------------------------------------

Dim bSTR91
bSTR91 = ""
Dim bSTR92
bSTR92 = ""
Dim boolean31
settingRepository1.GetAttrInfo "ICMCLAShapeFilletCmd", bSTR91, bSTR92, boolean31
'--------------------------------------------------
' Parameter 1 : (String) "ICMCLAShapeFilletCmd"
' Parameter 2 : (String) "Default value"
' Parameter 3 : (String) "Unlocked"
' Parameter 4 : (Boolean) False
'--------------------------------------------------

bSTR93 = settingRepository1.GetAttr("ICMCLAShapeTriTangentFilletCmd")
'--------------------------------------------------
' Parameter 1 : (String) "ICMCLAShapeTriTangentFilletCmd"
' Returned value : (Variant) (String) "1"
'--------------------------------------------------

Dim bSTR94
bSTR94 = ""
Dim bSTR95
bSTR95 = ""
Dim boolean32
settingRepository1.GetAttrInfo "ICMCLAShapeTriTangentFilletCmd", bSTR94, bSTR95, boolean32
'--------------------------------------------------
' Parameter 1 : (String) "ICMCLAShapeTriTangentFilletCmd"
' Parameter 2 : (String) "Default value"
' Parameter 3 : (String) "Unlocked"
' Parameter 4 : (Boolean) False
'--------------------------------------------------

bSTR96 = settingRepository1.GetAttr("ICMCLAShapeCornerFilletCmd")
'--------------------------------------------------
' Parameter 1 : (String) "ICMCLAShapeCornerFilletCmd"
' Returned value : (Variant) (String) "1"
'--------------------------------------------------

Dim bSTR97
bSTR97 = ""
Dim bSTR98
bSTR98 = ""
Dim boolean33
settingRepository1.GetAttrInfo "ICMCLAShapeCornerFilletCmd", bSTR97, bSTR98, boolean33
'--------------------------------------------------
' Parameter 1 : (String) "ICMCLAShapeCornerFilletCmd"
' Parameter 2 : (String) "Default value"
' Parameter 3 : (String) "Unlocked"
' Parameter 4 : (Boolean) False
'--------------------------------------------------

bSTR99 = settingRepository1.GetAttr("ICMCLAShapeGlobalSurfaceOffsetCmd")
'--------------------------------------------------
' Parameter 1 : (String) "ICMCLAShapeGlobalSurfaceOffsetCmd"
' Returned value : (Variant) (String) "1"
'--------------------------------------------------

Dim bSTR100
bSTR100 = ""
Dim bSTR101
bSTR101 = ""
Dim boolean34
settingRepository1.GetAttrInfo "ICMCLAShapeGlobalSurfaceOffsetCmd", bSTR100, bSTR101, boolean34
'--------------------------------------------------
' Parameter 1 : (String) "ICMCLAShapeGlobalSurfaceOffsetCmd"
' Parameter 2 : (String) "Default value"
' Parameter 3 : (String) "Unlocked"
' Parameter 4 : (Boolean) False
'--------------------------------------------------

bSTR102 = settingRepository1.GetAttr("ICMCLAShapeTubingCmd")
'--------------------------------------------------
' Parameter 1 : (String) "ICMCLAShapeTubingCmd"
' Returned value : (Variant) (String) "1"
'--------------------------------------------------

Dim bSTR103
bSTR103 = ""
Dim bSTR104
bSTR104 = ""
Dim boolean35
settingRepository1.GetAttrInfo "ICMCLAShapeTubingCmd", bSTR103, bSTR104, boolean35
'--------------------------------------------------
' Parameter 1 : (String) "ICMCLAShapeTubingCmd"
' Parameter 2 : (String) "Default value"
' Parameter 3 : (String) "Unlocked"
' Parameter 4 : (Boolean) False
'--------------------------------------------------

bSTR105 = settingRepository1.GetAttr("ICMCLAShapeAcceleratedSurfaceCmd")
'--------------------------------------------------
' Parameter 1 : (String) "ICMCLAShapeAcceleratedSurfaceCmd"
' Returned value : (Variant) (String) "1"
'--------------------------------------------------

Dim bSTR106
bSTR106 = ""
Dim bSTR107
bSTR107 = ""
Dim boolean36
settingRepository1.GetAttrInfo "ICMCLAShapeAcceleratedSurfaceCmd", bSTR106, bSTR107, boolean36
'--------------------------------------------------
' Parameter 1 : (String) "ICMCLAShapeAcceleratedSurfaceCmd"
' Parameter 2 : (String) "Default value"
' Parameter 3 : (String) "Unlocked"
' Parameter 4 : (Boolean) False
'--------------------------------------------------

bSTR108 = settingRepository1.GetAttr("ICMCLAShapeOvercrownCmd")
'--------------------------------------------------
' Parameter 1 : (String) "ICMCLAShapeOvercrownCmd"
' Returned value : (Variant) (String) "1"
'--------------------------------------------------

Dim bSTR109
bSTR109 = ""
Dim bSTR110
bSTR110 = ""
Dim boolean37
settingRepository1.GetAttrInfo "ICMCLAShapeOvercrownCmd", bSTR109, bSTR110, boolean37
'--------------------------------------------------
' Parameter 1 : (String) "ICMCLAShapeOvercrownCmd"
' Parameter 2 : (String) "Default value"
' Parameter 3 : (String) "Unlocked"
' Parameter 4 : (Boolean) False
'--------------------------------------------------

bSTR111 = settingRepository1.GetAttr("ICMCLAShapeMappingCmd")
'--------------------------------------------------
' Parameter 1 : (String) "ICMCLAShapeMappingCmd"
' Returned value : (Variant) (String) "1"
'--------------------------------------------------

Dim bSTR112
bSTR112 = ""
Dim bSTR113
bSTR113 = ""
Dim boolean38
settingRepository1.GetAttrInfo "ICMCLAShapeMappingCmd", bSTR112, bSTR113, boolean38
'--------------------------------------------------
' Parameter 1 : (String) "ICMCLAShapeMappingCmd"
' Parameter 2 : (String) "Default value"
' Parameter 3 : (String) "Unlocked"
' Parameter 4 : (Boolean) False
'--------------------------------------------------

End Sub
