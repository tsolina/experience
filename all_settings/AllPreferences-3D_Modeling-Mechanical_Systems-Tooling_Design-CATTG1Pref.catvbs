Language="VBSCRIPT"

Sub CATMain()

Set settingControllers1 = CATIA.SettingControllers

Set settingRepository1 = settingControllers1.Item("ToolingDesignGeneral")

boolean1 = settingRepository1.GetAttr("IconVisualization")
'--------------------------------------------------
' Parameter 1 : (String) "IconVisualization"
' Returned value : (Variant) (Boolean) True
'--------------------------------------------------

Dim bSTR1
bSTR1 = ""
Dim bSTR2
bSTR2 = ""
Dim boolean2
settingRepository1.GetAttrInfo "IconVisualization", bSTR1, bSTR2, boolean2
'--------------------------------------------------
' Parameter 1 : (String) "IconVisualization"
' Parameter 2 : (String) "Default value"
' Parameter 3 : (String) "Unlocked"
' Parameter 4 : (Boolean) False
'--------------------------------------------------

boolean3 = settingRepository1.GetAttr("CSInformationOnOverfly")
'--------------------------------------------------
' Parameter 1 : (String) "CSInformationOnOverfly"
' Returned value : (Variant) (Boolean) True
'--------------------------------------------------

Dim bSTR3
bSTR3 = ""
Dim bSTR4
bSTR4 = ""
Dim boolean4
settingRepository1.GetAttrInfo "CSInformationOnOverfly", bSTR3, bSTR4, boolean4
'--------------------------------------------------
' Parameter 1 : (String) "CSInformationOnOverfly"
' Parameter 2 : (String) "Default value"
' Parameter 3 : (String) "Unlocked"
' Parameter 4 : (Boolean) False
'--------------------------------------------------

boolean5 = settingRepository1.GetAttr("CSFreeStatusOnOverfly")
'--------------------------------------------------
' Parameter 1 : (String) "CSFreeStatusOnOverfly"
' Returned value : (Variant) (Boolean) False
'--------------------------------------------------

Dim bSTR5
bSTR5 = ""
Dim bSTR6
bSTR6 = ""
Dim boolean6
settingRepository1.GetAttrInfo "CSFreeStatusOnOverfly", bSTR5, bSTR6, boolean6
'--------------------------------------------------
' Parameter 1 : (String) "CSFreeStatusOnOverfly"
' Parameter 2 : (String) "Default value"
' Parameter 3 : (String) "Unlocked"
' Parameter 4 : (Boolean) False
'--------------------------------------------------

boolean7 = settingRepository1.GetAttr("PopulateAnchorVisualization")
'--------------------------------------------------
' Parameter 1 : (String) "PopulateAnchorVisualization"
' Returned value : (Variant) (Boolean) True
'--------------------------------------------------

Dim bSTR7
bSTR7 = ""
Dim bSTR8
bSTR8 = ""
Dim boolean8
settingRepository1.GetAttrInfo "PopulateAnchorVisualization", bSTR7, bSTR8, boolean8
'--------------------------------------------------
' Parameter 1 : (String) "PopulateAnchorVisualization"
' Parameter 2 : (String) "Default value"
' Parameter 3 : (String) "Unlocked"
' Parameter 4 : (Boolean) False
'--------------------------------------------------

boolean9 = settingRepository1.GetAttr("CheckPartInterface")
'--------------------------------------------------
' Parameter 1 : (String) "CheckPartInterface"
' Returned value : (Variant) (Boolean) False
'--------------------------------------------------

Dim bSTR9
bSTR9 = ""
Dim bSTR10
bSTR10 = ""
Dim boolean10
settingRepository1.GetAttrInfo "CheckPartInterface", bSTR9, bSTR10, boolean10
'--------------------------------------------------
' Parameter 1 : (String) "CheckPartInterface"
' Parameter 2 : (String) "Default value"
' Parameter 3 : (String) "Unlocked"
' Parameter 4 : (Boolean) False
'--------------------------------------------------

boolean11 = settingRepository1.GetAttr("CheckSkeletonRep")
'--------------------------------------------------
' Parameter 1 : (String) "CheckSkeletonRep"
' Returned value : (Variant) (Boolean) True
'--------------------------------------------------

Dim bSTR11
bSTR11 = ""
Dim bSTR12
bSTR12 = ""
Dim boolean12
settingRepository1.GetAttrInfo "CheckSkeletonRep", bSTR11, bSTR12, boolean12
'--------------------------------------------------
' Parameter 1 : (String) "CheckSkeletonRep"
' Parameter 2 : (String) "Default value"
' Parameter 3 : (String) "Unlocked"
' Parameter 4 : (Boolean) False
'--------------------------------------------------

boolean13 = settingRepository1.GetAttr("CheckDefineAFInSkeleton")
'--------------------------------------------------
' Parameter 1 : (String) "CheckDefineAFInSkeleton"
' Returned value : (Variant) (Boolean) False
'--------------------------------------------------

Dim bSTR13
bSTR13 = ""
Dim bSTR14
bSTR14 = ""
Dim boolean14
settingRepository1.GetAttrInfo "CheckDefineAFInSkeleton", bSTR13, bSTR14, boolean14
'--------------------------------------------------
' Parameter 1 : (String) "CheckDefineAFInSkeleton"
' Parameter 2 : (String) "Default value"
' Parameter 3 : (String) "Unlocked"
' Parameter 4 : (Boolean) False
'--------------------------------------------------

boolean15 = settingRepository1.GetAttr("FilterOnType")
'--------------------------------------------------
' Parameter 1 : (String) "FilterOnType"
' Returned value : (Variant) (Boolean) False
'--------------------------------------------------

Dim bSTR15
bSTR15 = ""
Dim bSTR16
bSTR16 = ""
Dim boolean16
settingRepository1.GetAttrInfo "FilterOnType", bSTR15, bSTR16, boolean16
'--------------------------------------------------
' Parameter 1 : (String) "FilterOnType"
' Parameter 2 : (String) "Default value"
' Parameter 3 : (String) "Unlocked"
' Parameter 4 : (Boolean) False
'--------------------------------------------------

boolean17 = settingRepository1.GetAttr("FilterOnDimensions")
'--------------------------------------------------
' Parameter 1 : (String) "FilterOnDimensions"
' Returned value : (Variant) (Boolean) False
'--------------------------------------------------

Dim bSTR17
bSTR17 = ""
Dim bSTR18
bSTR18 = ""
Dim boolean18
settingRepository1.GetAttrInfo "FilterOnDimensions", bSTR17, bSTR18, boolean18
'--------------------------------------------------
' Parameter 1 : (String) "FilterOnDimensions"
' Parameter 2 : (String) "Default value"
' Parameter 3 : (String) "Unlocked"
' Parameter 4 : (Boolean) False
'--------------------------------------------------

boolean19 = settingRepository1.GetAttr("CheckAutoDefineDuringPos")
'--------------------------------------------------
' Parameter 1 : (String) "CheckAutoDefineDuringPos"
' Returned value : (Variant) (Boolean) False
'--------------------------------------------------

Dim bSTR19
bSTR19 = ""
Dim bSTR20
bSTR20 = ""
Dim boolean20
settingRepository1.GetAttrInfo "CheckAutoDefineDuringPos", bSTR19, bSTR20, boolean20
'--------------------------------------------------
' Parameter 1 : (String) "CheckAutoDefineDuringPos"
' Parameter 2 : (String) "Default value"
' Parameter 3 : (String) "Unlocked"
' Parameter 4 : (Boolean) False
'--------------------------------------------------

boolean21 = settingRepository1.GetAttr("DesignInContextSelection")
'--------------------------------------------------
' Parameter 1 : (String) "DesignInContextSelection"
' Returned value : (Variant) (Boolean) True
'--------------------------------------------------

Dim bSTR21
bSTR21 = ""
Dim bSTR22
bSTR22 = ""
Dim boolean22
settingRepository1.GetAttrInfo "DesignInContextSelection", bSTR21, bSTR22, boolean22
'--------------------------------------------------
' Parameter 1 : (String) "DesignInContextSelection"
' Parameter 2 : (String) "Default value"
' Parameter 3 : (String) "Unlocked"
' Parameter 4 : (Boolean) False
'--------------------------------------------------

boolean23 = settingRepository1.GetAttr("AutomaticUpdateAfterImpactComputation")
'--------------------------------------------------
' Parameter 1 : (String) "AutomaticUpdateAfterImpactComputation"
' Returned value : (Variant) (Boolean) True
'--------------------------------------------------

Dim bSTR23
bSTR23 = ""
Dim bSTR24
bSTR24 = ""
Dim boolean24
settingRepository1.GetAttrInfo "AutomaticUpdateAfterImpactComputation", bSTR23, bSTR24, boolean24
'--------------------------------------------------
' Parameter 1 : (String) "AutomaticUpdateAfterImpactComputation"
' Parameter 2 : (String) "Default value"
' Parameter 3 : (String) "Unlocked"
' Parameter 4 : (Boolean) False
'--------------------------------------------------

boolean25 = settingRepository1.GetAttr("TRCreationAfterImpactComputation")
'--------------------------------------------------
' Parameter 1 : (String) "TRCreationAfterImpactComputation"
' Returned value : (Variant) (Boolean) False
'--------------------------------------------------

Dim bSTR25
bSTR25 = ""
Dim bSTR26
bSTR26 = ""
Dim boolean26
settingRepository1.GetAttrInfo "TRCreationAfterImpactComputation", bSTR25, bSTR26, boolean26
'--------------------------------------------------
' Parameter 1 : (String) "TRCreationAfterImpactComputation"
' Parameter 2 : (String) "Default value"
' Parameter 3 : (String) "Unlocked"
' Parameter 4 : (Boolean) False
'--------------------------------------------------

boolean27 = settingRepository1.GetAttr("GroupAssemblyImpactAfterImpactComputation")
'--------------------------------------------------
' Parameter 1 : (String) "GroupAssemblyImpactAfterImpactComputation"
' Returned value : (Variant) (Boolean) True
'--------------------------------------------------

Dim bSTR27
bSTR27 = ""
Dim bSTR28
bSTR28 = ""
Dim boolean28
settingRepository1.GetAttrInfo "GroupAssemblyImpactAfterImpactComputation", bSTR27, bSTR28, boolean28
'--------------------------------------------------
' Parameter 1 : (String) "GroupAssemblyImpactAfterImpactComputation"
' Parameter 2 : (String) "Default value"
' Parameter 3 : (String) "Unlocked"
' Parameter 4 : (Boolean) False
'--------------------------------------------------

boolean29 = settingRepository1.GetAttr("PlatesTransparencyProduct")
'--------------------------------------------------
' Parameter 1 : (String) "PlatesTransparencyProduct"
' Returned value : (Variant) (Boolean) True
'--------------------------------------------------

Dim bSTR29
bSTR29 = ""
Dim bSTR30
bSTR30 = ""
Dim boolean30
settingRepository1.GetAttrInfo "PlatesTransparencyProduct", bSTR29, bSTR30, boolean30
'--------------------------------------------------
' Parameter 1 : (String) "PlatesTransparencyProduct"
' Parameter 2 : (String) "Default value"
' Parameter 3 : (String) "Unlocked"
' Parameter 4 : (Boolean) False
'--------------------------------------------------

boolean31 = settingRepository1.GetAttr("PlatesTransparencyBody")
'--------------------------------------------------
' Parameter 1 : (String) "PlatesTransparencyBody"
' Returned value : (Variant) (Boolean) False
'--------------------------------------------------

Dim bSTR31
bSTR31 = ""
Dim bSTR32
bSTR32 = ""
Dim boolean32
settingRepository1.GetAttrInfo "PlatesTransparencyBody", bSTR31, bSTR32, boolean32
'--------------------------------------------------
' Parameter 1 : (String) "PlatesTransparencyBody"
' Parameter 2 : (String) "Default value"
' Parameter 3 : (String) "Unlocked"
' Parameter 4 : (Boolean) False
'--------------------------------------------------

boolean33 = settingRepository1.GetAttr("EditModeTransparencyBody")
'--------------------------------------------------
' Parameter 1 : (String) "EditModeTransparencyBody"
' Returned value : (Variant) (Boolean) False
'--------------------------------------------------

Dim bSTR33
bSTR33 = ""
Dim bSTR34
bSTR34 = ""
Dim boolean34
settingRepository1.GetAttrInfo "EditModeTransparencyBody", bSTR33, bSTR34, boolean34
'--------------------------------------------------
' Parameter 1 : (String) "EditModeTransparencyBody"
' Parameter 2 : (String) "Default value"
' Parameter 3 : (String) "Unlocked"
' Parameter 4 : (Boolean) False
'--------------------------------------------------

boolean35 = settingRepository1.GetAttr("ManageDeformability")
'--------------------------------------------------
' Parameter 1 : (String) "ManageDeformability"
' Returned value : (Variant) (Boolean) False
'--------------------------------------------------

Dim bSTR35
bSTR35 = ""
Dim bSTR36
bSTR36 = ""
Dim boolean36
settingRepository1.GetAttrInfo "ManageDeformability", bSTR35, bSTR36, boolean36
'--------------------------------------------------
' Parameter 1 : (String) "ManageDeformability"
' Parameter 2 : (String) "Default value"
' Parameter 3 : (String) "Unlocked"
' Parameter 4 : (Boolean) False
'--------------------------------------------------

End Sub
