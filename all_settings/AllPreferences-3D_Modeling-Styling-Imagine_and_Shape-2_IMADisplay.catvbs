Language="VBSCRIPT"

Sub CATMain()

Set settingControllers1 = CATIA.SettingControllers

Set settingRepository1 = settingControllers1.Item("CATDesSettingDisplay")

long1 = settingRepository1.GetAttr("CurveType")
'--------------------------------------------------
' Parameter 1 : (String) "CurveType"
' Returned value : (Variant) (Long) 1
'--------------------------------------------------

Dim bSTR1
bSTR1 = ""
Dim bSTR2
bSTR2 = ""
Dim boolean1
settingRepository1.GetAttrInfo "CurveType", bSTR1, bSTR2, boolean1
'--------------------------------------------------
' Parameter 1 : (String) "CurveType"
' Parameter 2 : (String) "Default value"
' Parameter 3 : (String) "Unlocked"
' Parameter 4 : (Boolean) False
'--------------------------------------------------

long2 = settingRepository1.GetAttr("CurveThickness")
'--------------------------------------------------
' Parameter 1 : (String) "CurveThickness"
' Returned value : (Variant) (Long) 2
'--------------------------------------------------

Dim bSTR3
bSTR3 = ""
Dim bSTR4
bSTR4 = ""
Dim boolean2
settingRepository1.GetAttrInfo "CurveThickness", bSTR3, bSTR4, boolean2
'--------------------------------------------------
' Parameter 1 : (String) "CurveThickness"
' Parameter 2 : (String) "Default value"
' Parameter 3 : (String) "Unlocked"
' Parameter 4 : (Boolean) False
'--------------------------------------------------

long3 = settingRepository1.GetAttr("IsHiddenLink")
'--------------------------------------------------
' Parameter 1 : (String) "IsHiddenLink"
' Returned value : (Variant) (Long) 1
'--------------------------------------------------

Dim bSTR5
bSTR5 = ""
Dim bSTR6
bSTR6 = ""
Dim boolean3
settingRepository1.GetAttrInfo "IsHiddenLink", bSTR5, bSTR6, boolean3
'--------------------------------------------------
' Parameter 1 : (String) "IsHiddenLink"
' Parameter 2 : (String) "Default value"
' Parameter 3 : (String) "Unlocked"
' Parameter 4 : (Boolean) False
'--------------------------------------------------

Dim arrayOfVariantOfULong1
arrayOfVariantOfULong1 = settingRepository1.GetAttrArray("BMColor")
'--------------------------------------------------
' Parameter 1 : (String) "BMColor"
' Returned value : (Array) 
'    Array[0] : (Variant) (Unsigned Long) 0
'    Array[1] : (Variant) (Unsigned Long) 0
'    Array[2] : (Variant) (Unsigned Long) 0
'--------------------------------------------------

Dim bSTR7
bSTR7 = ""
Dim bSTR8
bSTR8 = ""
Dim boolean4
settingRepository1.GetAttrInfo "BMColor", bSTR7, bSTR8, boolean4
'--------------------------------------------------
' Parameter 1 : (String) "BMColor"
' Parameter 2 : (String) "Default value"
' Parameter 3 : (String) "Unlocked"
' Parameter 4 : (Boolean) False
'--------------------------------------------------

long4 = settingRepository1.GetAttr("BMLineType")
'--------------------------------------------------
' Parameter 1 : (String) "BMLineType"
' Returned value : (Variant) (Long) 1
'--------------------------------------------------

Dim bSTR9
bSTR9 = ""
Dim bSTR10
bSTR10 = ""
Dim boolean5
settingRepository1.GetAttrInfo "BMLineType", bSTR9, bSTR10, boolean5
'--------------------------------------------------
' Parameter 1 : (String) "BMLineType"
' Parameter 2 : (String) "Default value"
' Parameter 3 : (String) "Unlocked"
' Parameter 4 : (Boolean) False
'--------------------------------------------------

long5 = settingRepository1.GetAttr("BMLineWeightType")
'--------------------------------------------------
' Parameter 1 : (String) "BMLineWeightType"
' Returned value : (Variant) (Long) 1
'--------------------------------------------------

Dim bSTR11
bSTR11 = ""
Dim bSTR12
bSTR12 = ""
Dim boolean6
settingRepository1.GetAttrInfo "BMLineWeightType", bSTR11, bSTR12, boolean6
'--------------------------------------------------
' Parameter 1 : (String) "BMLineWeightType"
' Parameter 2 : (String) "Default value"
' Parameter 3 : (String) "Unlocked"
' Parameter 4 : (Boolean) False
'--------------------------------------------------

long6 = settingRepository1.GetAttr("BMLineColouredType")
'--------------------------------------------------
' Parameter 1 : (String) "BMLineColouredType"
' Returned value : (Variant) (Long) 4
'--------------------------------------------------

Dim bSTR13
bSTR13 = ""
Dim bSTR14
bSTR14 = ""
Dim boolean7
settingRepository1.GetAttrInfo "BMLineColouredType", bSTR13, bSTR14, boolean7
'--------------------------------------------------
' Parameter 1 : (String) "BMLineColouredType"
' Parameter 2 : (String) "Default value"
' Parameter 3 : (String) "Unlocked"
' Parameter 4 : (Boolean) False
'--------------------------------------------------

long7 = settingRepository1.GetAttr("BMLineThickness")
'--------------------------------------------------
' Parameter 1 : (String) "BMLineThickness"
' Returned value : (Variant) (Long) 1
'--------------------------------------------------

Dim bSTR15
bSTR15 = ""
Dim bSTR16
bSTR16 = ""
Dim boolean8
settingRepository1.GetAttrInfo "BMLineThickness", bSTR15, bSTR16, boolean8
'--------------------------------------------------
' Parameter 1 : (String) "BMLineThickness"
' Parameter 2 : (String) "Default value"
' Parameter 3 : (String) "Unlocked"
' Parameter 4 : (Boolean) False
'--------------------------------------------------

long8 = settingRepository1.GetAttr("BMLineWeightThickness")
'--------------------------------------------------
' Parameter 1 : (String) "BMLineWeightThickness"
' Returned value : (Variant) (Long) 3
'--------------------------------------------------

Dim bSTR17
bSTR17 = ""
Dim bSTR18
bSTR18 = ""
Dim boolean9
settingRepository1.GetAttrInfo "BMLineWeightThickness", bSTR17, bSTR18, boolean9
'--------------------------------------------------
' Parameter 1 : (String) "BMLineWeightThickness"
' Parameter 2 : (String) "Default value"
' Parameter 3 : (String) "Unlocked"
' Parameter 4 : (Boolean) False
'--------------------------------------------------

long9 = settingRepository1.GetAttr("IsBMLineHiddenOn")
'--------------------------------------------------
' Parameter 1 : (String) "IsBMLineHiddenOn"
' Returned value : (Variant) (Long) 1
'--------------------------------------------------

Dim bSTR19
bSTR19 = ""
Dim bSTR20
bSTR20 = ""
Dim boolean10
settingRepository1.GetAttrInfo "IsBMLineHiddenOn", bSTR19, bSTR20, boolean10
'--------------------------------------------------
' Parameter 1 : (String) "IsBMLineHiddenOn"
' Parameter 2 : (String) "Default value"
' Parameter 3 : (String) "Unlocked"
' Parameter 4 : (Boolean) False
'--------------------------------------------------

long10 = settingRepository1.GetAttr("BMPointSymbol")
'--------------------------------------------------
' Parameter 1 : (String) "BMPointSymbol"
' Returned value : (Variant) (Long) 5
'--------------------------------------------------

Dim bSTR21
bSTR21 = ""
Dim bSTR22
bSTR22 = ""
Dim boolean11
settingRepository1.GetAttrInfo "BMPointSymbol", bSTR21, bSTR22, boolean11
'--------------------------------------------------
' Parameter 1 : (String) "BMPointSymbol"
' Parameter 2 : (String) "Default value"
' Parameter 3 : (String) "Unlocked"
' Parameter 4 : (Boolean) False
'--------------------------------------------------

long11 = settingRepository1.GetAttr("BMPointWeightSymbol")
'--------------------------------------------------
' Parameter 1 : (String) "BMPointWeightSymbol"
' Returned value : (Variant) (Long) 4
'--------------------------------------------------

Dim bSTR23
bSTR23 = ""
Dim bSTR24
bSTR24 = ""
Dim boolean12
settingRepository1.GetAttrInfo "BMPointWeightSymbol", bSTR23, bSTR24, boolean12
'--------------------------------------------------
' Parameter 1 : (String) "BMPointWeightSymbol"
' Parameter 2 : (String) "Default value"
' Parameter 3 : (String) "Unlocked"
' Parameter 4 : (Boolean) False
'--------------------------------------------------

long12 = settingRepository1.GetAttr("BMPointColouredSymbol")
'--------------------------------------------------
' Parameter 1 : (String) "BMPointColouredSymbol"
' Returned value : (Variant) (Long) 3
'--------------------------------------------------

Dim bSTR25
bSTR25 = ""
Dim bSTR26
bSTR26 = ""
Dim boolean13
settingRepository1.GetAttrInfo "BMPointColouredSymbol", bSTR25, bSTR26, boolean13
'--------------------------------------------------
' Parameter 1 : (String) "BMPointColouredSymbol"
' Parameter 2 : (String) "Default value"
' Parameter 3 : (String) "Unlocked"
' Parameter 4 : (Boolean) False
'--------------------------------------------------

long13 = settingRepository1.GetAttr("IsBMEnlargedDotSymbol")
'--------------------------------------------------
' Parameter 1 : (String) "IsBMEnlargedDotSymbol"
' Returned value : (Variant) (Long) 0
'--------------------------------------------------

Dim bSTR27
bSTR27 = ""
Dim bSTR28
bSTR28 = ""
Dim boolean14
settingRepository1.GetAttrInfo "IsBMEnlargedDotSymbol", bSTR27, bSTR28, boolean14
'--------------------------------------------------
' Parameter 1 : (String) "IsBMEnlargedDotSymbol"
' Parameter 2 : (String) "Default value"
' Parameter 3 : (String) "Unlocked"
' Parameter 4 : (Boolean) False
'--------------------------------------------------

long14 = settingRepository1.GetAttr("IsBMMultiColorOn")
'--------------------------------------------------
' Parameter 1 : (String) "IsBMMultiColorOn"
' Returned value : (Variant) (Long) 1
'--------------------------------------------------

Dim bSTR29
bSTR29 = ""
Dim bSTR30
bSTR30 = ""
Dim boolean15
settingRepository1.GetAttrInfo "IsBMMultiColorOn", bSTR29, bSTR30, boolean15
'--------------------------------------------------
' Parameter 1 : (String) "IsBMMultiColorOn"
' Parameter 2 : (String) "Default value"
' Parameter 3 : (String) "Unlocked"
' Parameter 4 : (Boolean) False
'--------------------------------------------------

long15 = settingRepository1.GetAttr("IsBMSpecificSelColorOn")
'--------------------------------------------------
' Parameter 1 : (String) "IsBMSpecificSelColorOn"
' Returned value : (Variant) (Long) 0
'--------------------------------------------------

Dim bSTR31
bSTR31 = ""
Dim bSTR32
bSTR32 = ""
Dim boolean16
settingRepository1.GetAttrInfo "IsBMSpecificSelColorOn", bSTR31, bSTR32, boolean16
'--------------------------------------------------
' Parameter 1 : (String) "IsBMSpecificSelColorOn"
' Parameter 2 : (String) "Default value"
' Parameter 3 : (String) "Unlocked"
' Parameter 4 : (Boolean) False
'--------------------------------------------------

Dim arrayOfVariantOfULong2
arrayOfVariantOfULong2 = settingRepository1.GetAttrArray("BMSpecificSelColor")
'--------------------------------------------------
' Parameter 1 : (String) "BMSpecificSelColor"
' Returned value : (Array) 
'    Array[0] : (Variant) (Unsigned Long) 0
'    Array[1] : (Variant) (Unsigned Long) 0
'    Array[2] : (Variant) (Unsigned Long) 0
'--------------------------------------------------

Dim bSTR33
bSTR33 = ""
Dim bSTR34
bSTR34 = ""
Dim boolean17
settingRepository1.GetAttrInfo "BMSpecificSelColor", bSTR33, bSTR34, boolean17
'--------------------------------------------------
' Parameter 1 : (String) "BMSpecificSelColor"
' Parameter 2 : (String) "Default value"
' Parameter 3 : (String) "Unlocked"
' Parameter 4 : (Boolean) False
'--------------------------------------------------

long16 = settingRepository1.GetAttr("HTTextLevel")
'--------------------------------------------------
' Parameter 1 : (String) "HTTextLevel"
' Returned value : (Variant) (Long) 0
'--------------------------------------------------

Dim bSTR35
bSTR35 = ""
Dim bSTR36
bSTR36 = ""
Dim boolean18
settingRepository1.GetAttrInfo "HTTextLevel", bSTR35, bSTR36, boolean18
'--------------------------------------------------
' Parameter 1 : (String) "HTTextLevel"
' Parameter 2 : (String) "Default value"
' Parameter 3 : (String) "Unlocked"
' Parameter 4 : (Boolean) False
'--------------------------------------------------

long17 = settingRepository1.GetAttr("IsHTPinned")
'--------------------------------------------------
' Parameter 1 : (String) "IsHTPinned"
' Returned value : (Variant) (Long) 1
'--------------------------------------------------

Dim bSTR37
bSTR37 = ""
Dim bSTR38
bSTR38 = ""
Dim boolean19
settingRepository1.GetAttrInfo "IsHTPinned", bSTR37, bSTR38, boolean19
'--------------------------------------------------
' Parameter 1 : (String) "IsHTPinned"
' Parameter 2 : (String) "Default value"
' Parameter 3 : (String) "Unlocked"
' Parameter 4 : (Boolean) False
'--------------------------------------------------

long18 = settingRepository1.GetAttr("HTCoordMode")
'--------------------------------------------------
' Parameter 1 : (String) "HTCoordMode"
' Returned value : (Variant) (Long) 0
'--------------------------------------------------

Dim bSTR39
bSTR39 = ""
Dim bSTR40
bSTR40 = ""
Dim boolean20
settingRepository1.GetAttrInfo "HTCoordMode", bSTR39, bSTR40, boolean20
'--------------------------------------------------
' Parameter 1 : (String) "HTCoordMode"
' Parameter 2 : (String) "Default value"
' Parameter 3 : (String) "Unlocked"
' Parameter 4 : (Boolean) False
'--------------------------------------------------

End Sub
