Language="VBSCRIPT"

Sub CATMain()

Set settingControllers1 = CATIA.SettingControllers

Set settingRepository1 = settingControllers1.Item("RFLPNavigator")

long1 = settingRepository1.GetAttr("ExpandWithFlowType")
'--------------------------------------------------
' Parameter 1 : (String) "ExpandWithFlowType"
' Returned value : (Variant) (Long) 0
'--------------------------------------------------

Dim bSTR1
bSTR1 = ""
Dim bSTR2
bSTR2 = ""
Dim boolean1
settingRepository1.GetAttrInfo "ExpandWithFlowType", bSTR1, bSTR2, boolean1
'--------------------------------------------------
' Parameter 1 : (String) "ExpandWithFlowType"
' Parameter 2 : (String) "Default value"
' Parameter 3 : (String) "Unlocked"
' Parameter 4 : (Boolean) False
'--------------------------------------------------

Set settingRepository2 = settingControllers1.Item("VPMNavigator")

long2 = settingRepository2.GetAttr("BeadFastenerLoading")
'--------------------------------------------------
' Parameter 1 : (String) "BeadFastenerLoading"
' Returned value : (Variant) (Long) 1
'--------------------------------------------------

Dim bSTR3
bSTR3 = ""
Dim bSTR4
bSTR4 = ""
Dim boolean2
settingRepository2.GetAttrInfo "BeadFastenerLoading", bSTR3, bSTR4, boolean2
'--------------------------------------------------
' Parameter 1 : (String) "BeadFastenerLoading"
' Parameter 2 : (String) "Default value"
' Parameter 3 : (String) "Unlocked"
' Parameter 4 : (Boolean) False
'--------------------------------------------------

long3 = settingRepository2.GetAttr("SpotFastenerLoading")
'--------------------------------------------------
' Parameter 1 : (String) "SpotFastenerLoading"
' Returned value : (Variant) (Long) 1
'--------------------------------------------------

Dim bSTR5
bSTR5 = ""
Dim bSTR6
bSTR6 = ""
Dim boolean3
settingRepository2.GetAttrInfo "SpotFastenerLoading", bSTR5, bSTR6, boolean3
'--------------------------------------------------
' Parameter 1 : (String) "SpotFastenerLoading"
' Parameter 2 : (String) "Default value"
' Parameter 3 : (String) "Unlocked"
' Parameter 4 : (Boolean) False
'--------------------------------------------------

long4 = settingRepository2.GetAttr("LocFastenerLoading")
'--------------------------------------------------
' Parameter 1 : (String) "LocFastenerLoading"
' Returned value : (Variant) (Long) 1
'--------------------------------------------------

Dim bSTR7
bSTR7 = ""
Dim bSTR8
bSTR8 = ""
Dim boolean4
settingRepository2.GetAttrInfo "LocFastenerLoading", bSTR7, bSTR8, boolean4
'--------------------------------------------------
' Parameter 1 : (String) "LocFastenerLoading"
' Parameter 2 : (String) "Default value"
' Parameter 3 : (String) "Unlocked"
' Parameter 4 : (Boolean) False
'--------------------------------------------------

long5 = settingRepository2.GetAttr("BundleFastenerLoading")
'--------------------------------------------------
' Parameter 1 : (String) "BundleFastenerLoading"
' Returned value : (Variant) (Long) 1
'--------------------------------------------------

Dim bSTR9
bSTR9 = ""
Dim bSTR10
bSTR10 = ""
Dim boolean5
settingRepository2.GetAttrInfo "BundleFastenerLoading", bSTR9, bSTR10, boolean5
'--------------------------------------------------
' Parameter 1 : (String) "BundleFastenerLoading"
' Parameter 2 : (String) "Default value"
' Parameter 3 : (String) "Unlocked"
' Parameter 4 : (Boolean) False
'--------------------------------------------------

End Sub
