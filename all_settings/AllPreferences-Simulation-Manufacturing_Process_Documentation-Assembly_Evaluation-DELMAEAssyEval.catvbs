Language="VBSCRIPT"

Sub CATMain()

Set settingControllers1 = CATIA.SettingControllers

Set settingRepository1 = settingControllers1.Item("DNBFittingSettings")

long1 = settingRepository1.GetAttr("PreviewWindowAvailability")
'--------------------------------------------------
' Parameter 1 : (String) "PreviewWindowAvailability"
' Returned value : (Variant) (Long) 0
'--------------------------------------------------

Dim bSTR1
bSTR1 = ""
Dim bSTR2
bSTR2 = ""
Dim boolean1
settingRepository1.GetAttrInfo "PreviewWindowAvailability", bSTR1, bSTR2, boolean1
'--------------------------------------------------
' Parameter 1 : (String) "PreviewWindowAvailability"
' Parameter 2 : (String) "Default value"
' Parameter 3 : (String) "Unlocked"
' Parameter 4 : (Boolean) False
'--------------------------------------------------

long2 = settingRepository1.GetAttr("CreateFuncProcTrack")
'--------------------------------------------------
' Parameter 1 : (String) "CreateFuncProcTrack"
' Returned value : (Variant) (Long) 0
'--------------------------------------------------

Dim bSTR3
bSTR3 = ""
Dim bSTR4
bSTR4 = ""
Dim boolean2
settingRepository1.GetAttrInfo "CreateFuncProcTrack", bSTR3, bSTR4, boolean2
'--------------------------------------------------
' Parameter 1 : (String) "CreateFuncProcTrack"
' Parameter 2 : (String) "Default value"
' Parameter 3 : (String) "Unlocked"
' Parameter 4 : (Boolean) False
'--------------------------------------------------

long3 = settingRepository1.GetAttr("AutoReverseTrack")
'--------------------------------------------------
' Parameter 1 : (String) "AutoReverseTrack"
' Returned value : (Variant) (Long) 0
'--------------------------------------------------

Dim bSTR5
bSTR5 = ""
Dim bSTR6
bSTR6 = ""
Dim boolean3
settingRepository1.GetAttrInfo "AutoReverseTrack", bSTR5, bSTR6, boolean3
'--------------------------------------------------
' Parameter 1 : (String) "AutoReverseTrack"
' Parameter 2 : (String) "Default value"
' Parameter 3 : (String) "Unlocked"
' Parameter 4 : (Boolean) False
'--------------------------------------------------

long4 = settingRepository1.GetAttr("HighlightMovObjOnSel")
'--------------------------------------------------
' Parameter 1 : (String) "HighlightMovObjOnSel"
' Returned value : (Variant) (Long) 0
'--------------------------------------------------

Dim bSTR7
bSTR7 = ""
Dim bSTR8
bSTR8 = ""
Dim boolean4
settingRepository1.GetAttrInfo "HighlightMovObjOnSel", bSTR7, bSTR8, boolean4
'--------------------------------------------------
' Parameter 1 : (String) "HighlightMovObjOnSel"
' Parameter 2 : (String) "Default value"
' Parameter 3 : (String) "Unlocked"
' Parameter 4 : (Boolean) False
'--------------------------------------------------

long5 = settingRepository1.GetAttr("HighlightMovObjOnSimu")
'--------------------------------------------------
' Parameter 1 : (String) "HighlightMovObjOnSimu"
' Returned value : (Variant) (Long) 0
'--------------------------------------------------

Dim bSTR9
bSTR9 = ""
Dim bSTR10
bSTR10 = ""
Dim boolean5
settingRepository1.GetAttrInfo "HighlightMovObjOnSimu", bSTR9, bSTR10, boolean5
'--------------------------------------------------
' Parameter 1 : (String) "HighlightMovObjOnSimu"
' Parameter 2 : (String) "Default value"
' Parameter 3 : (String) "Unlocked"
' Parameter 4 : (Boolean) False
'--------------------------------------------------

long6 = settingRepository1.GetAttr("SequenceGanttChoreoDisplay")
'--------------------------------------------------
' Parameter 1 : (String) "SequenceGanttChoreoDisplay"
' Returned value : (Variant) (Long) 0
'--------------------------------------------------

Dim bSTR11
bSTR11 = ""
Dim bSTR12
bSTR12 = ""
Dim boolean6
settingRepository1.GetAttrInfo "SequenceGanttChoreoDisplay", bSTR11, bSTR12, boolean6
'--------------------------------------------------
' Parameter 1 : (String) "SequenceGanttChoreoDisplay"
' Parameter 2 : (String) "Default value"
' Parameter 3 : (String) "Unlocked"
' Parameter 4 : (Boolean) False
'--------------------------------------------------

long7 = settingRepository1.GetAttr("TPointNameDisplay")
'--------------------------------------------------
' Parameter 1 : (String) "TPointNameDisplay"
' Returned value : (Variant) (Long) 0
'--------------------------------------------------

Dim bSTR13
bSTR13 = ""
Dim bSTR14
bSTR14 = ""
Dim boolean7
settingRepository1.GetAttrInfo "TPointNameDisplay", bSTR13, bSTR14, boolean7
'--------------------------------------------------
' Parameter 1 : (String) "TPointNameDisplay"
' Parameter 2 : (String) "Default value"
' Parameter 3 : (String) "Unlocked"
' Parameter 4 : (Boolean) False
'--------------------------------------------------

long8 = settingRepository1.GetAttr("TPointCoordDisplay")
'--------------------------------------------------
' Parameter 1 : (String) "TPointCoordDisplay"
' Returned value : (Variant) (Long) 0
'--------------------------------------------------

Dim bSTR15
bSTR15 = ""
Dim bSTR16
bSTR16 = ""
Dim boolean8
settingRepository1.GetAttrInfo "TPointCoordDisplay", bSTR15, bSTR16, boolean8
'--------------------------------------------------
' Parameter 1 : (String) "TPointCoordDisplay"
' Parameter 2 : (String) "Default value"
' Parameter 3 : (String) "Unlocked"
' Parameter 4 : (Boolean) False
'--------------------------------------------------

long9 = settingRepository1.GetAttr("TPointAxisPatternDisplay")
'--------------------------------------------------
' Parameter 1 : (String) "TPointAxisPatternDisplay"
' Returned value : (Variant) (Long) 0
'--------------------------------------------------

Dim bSTR17
bSTR17 = ""
Dim bSTR18
bSTR18 = ""
Dim boolean9
settingRepository1.GetAttrInfo "TPointAxisPatternDisplay", bSTR17, bSTR18, boolean9
'--------------------------------------------------
' Parameter 1 : (String) "TPointAxisPatternDisplay"
' Parameter 2 : (String) "Default value"
' Parameter 3 : (String) "Unlocked"
' Parameter 4 : (Boolean) False
'--------------------------------------------------

long10 = settingRepository1.GetAttr("AutomaticTPointInsertionWhileMoving")
'--------------------------------------------------
' Parameter 1 : (String) "AutomaticTPointInsertionWhileMoving"
' Returned value : (Variant) (Long) 0
'--------------------------------------------------

Dim bSTR19
bSTR19 = ""
Dim bSTR20
bSTR20 = ""
Dim boolean10
settingRepository1.GetAttrInfo "AutomaticTPointInsertionWhileMoving", bSTR19, bSTR20, boolean10
'--------------------------------------------------
' Parameter 1 : (String) "AutomaticTPointInsertionWhileMoving"
' Parameter 2 : (String) "Default value"
' Parameter 3 : (String) "Unlocked"
' Parameter 4 : (Boolean) False
'--------------------------------------------------

double1 = settingRepository1.GetAttr("AutomaticTPointInsertionDistanceSpinner")
'--------------------------------------------------
' Parameter 1 : (String) "AutomaticTPointInsertionDistanceSpinner"
' Returned value : (Variant) (Double) 0.020000
'--------------------------------------------------

Dim bSTR21
bSTR21 = ""
Dim bSTR22
bSTR22 = ""
Dim boolean11
settingRepository1.GetAttrInfo "AutomaticTPointInsertionDistanceSpinner", bSTR21, bSTR22, boolean11
'--------------------------------------------------
' Parameter 1 : (String) "AutomaticTPointInsertionDistanceSpinner"
' Parameter 2 : (String) "Default value"
' Parameter 3 : (String) "Unlocked"
' Parameter 4 : (Boolean) False
'--------------------------------------------------

double2 = settingRepository1.GetAttr("AutomaticTPointInsertionAngleSpinner")
'--------------------------------------------------
' Parameter 1 : (String) "AutomaticTPointInsertionAngleSpinner"
' Returned value : (Variant) (Double) 0.087266
'--------------------------------------------------

Dim bSTR23
bSTR23 = ""
Dim bSTR24
bSTR24 = ""
Dim boolean12
settingRepository1.GetAttrInfo "AutomaticTPointInsertionAngleSpinner", bSTR23, bSTR24, boolean12
'--------------------------------------------------
' Parameter 1 : (String) "AutomaticTPointInsertionAngleSpinner"
' Parameter 2 : (String) "Default value"
' Parameter 3 : (String) "Unlocked"
' Parameter 4 : (Boolean) False
'--------------------------------------------------

long11 = settingRepository1.GetAttr("TiltRestriction")
'--------------------------------------------------
' Parameter 1 : (String) "TiltRestriction"
' Returned value : (Variant) (Long) 0
'--------------------------------------------------

Dim bSTR25
bSTR25 = ""
Dim bSTR26
bSTR26 = ""
Dim boolean13
settingRepository1.GetAttrInfo "TiltRestriction", bSTR25, bSTR26, boolean13
'--------------------------------------------------
' Parameter 1 : (String) "TiltRestriction"
' Parameter 2 : (String) "Default value"
' Parameter 3 : (String) "Unlocked"
' Parameter 4 : (Boolean) False
'--------------------------------------------------

double3 = settingRepository1.GetAttr("SweptVolumeLinearAccuracySpinner")
'--------------------------------------------------
' Parameter 1 : (String) "SweptVolumeLinearAccuracySpinner"
' Returned value : (Variant) (Double) 0.000200
'--------------------------------------------------

Dim bSTR27
bSTR27 = ""
Dim bSTR28
bSTR28 = ""
Dim boolean14
settingRepository1.GetAttrInfo "SweptVolumeLinearAccuracySpinner", bSTR27, bSTR28, boolean14
'--------------------------------------------------
' Parameter 1 : (String) "SweptVolumeLinearAccuracySpinner"
' Parameter 2 : (String) "Default value"
' Parameter 3 : (String) "Unlocked"
' Parameter 4 : (Boolean) False
'--------------------------------------------------

double4 = settingRepository1.GetAttr("SweptVolumeAngularAccuracySpinner")
'--------------------------------------------------
' Parameter 1 : (String) "SweptVolumeAngularAccuracySpinner"
' Returned value : (Variant) (Double) 0.087266
'--------------------------------------------------

Dim bSTR29
bSTR29 = ""
Dim bSTR30
bSTR30 = ""
Dim boolean15
settingRepository1.GetAttrInfo "SweptVolumeAngularAccuracySpinner", bSTR29, bSTR30, boolean15
'--------------------------------------------------
' Parameter 1 : (String) "SweptVolumeAngularAccuracySpinner"
' Parameter 2 : (String) "Default value"
' Parameter 3 : (String) "Unlocked"
' Parameter 4 : (Boolean) False
'--------------------------------------------------

long12 = settingRepository1.GetAttr("DisplayDistanceForTPoint")
'--------------------------------------------------
' Parameter 1 : (String) "DisplayDistanceForTPoint"
' Returned value : (Variant) (Long) 0
'--------------------------------------------------

Dim bSTR31
bSTR31 = ""
Dim bSTR32
bSTR32 = ""
Dim boolean16
settingRepository1.GetAttrInfo "DisplayDistanceForTPoint", bSTR31, bSTR32, boolean16
'--------------------------------------------------
' Parameter 1 : (String) "DisplayDistanceForTPoint"
' Parameter 2 : (String) "Default value"
' Parameter 3 : (String) "Unlocked"
' Parameter 4 : (Boolean) False
'--------------------------------------------------

long13 = settingRepository1.GetAttr("TiltRestrictionVectorCombo")
'--------------------------------------------------
' Parameter 1 : (String) "TiltRestrictionVectorCombo"
' Returned value : (Variant) (Long) 0
'--------------------------------------------------

Dim bSTR33
bSTR33 = ""
Dim bSTR34
bSTR34 = ""
Dim boolean17
settingRepository1.GetAttrInfo "TiltRestrictionVectorCombo", bSTR33, bSTR34, boolean17
'--------------------------------------------------
' Parameter 1 : (String) "TiltRestrictionVectorCombo"
' Parameter 2 : (String) "Default value"
' Parameter 3 : (String) "Unlocked"
' Parameter 4 : (Boolean) False
'--------------------------------------------------

double5 = settingRepository1.GetAttr("TiltRestrictionAngleSpinner")
'--------------------------------------------------
' Parameter 1 : (String) "TiltRestrictionAngleSpinner"
' Returned value : (Variant) (Double) 0.087266
'--------------------------------------------------

Dim bSTR35
bSTR35 = ""
Dim bSTR36
bSTR36 = ""
Dim boolean18
settingRepository1.GetAttrInfo "TiltRestrictionAngleSpinner", bSTR35, bSTR36, boolean18
'--------------------------------------------------
' Parameter 1 : (String) "TiltRestrictionAngleSpinner"
' Parameter 2 : (String) "Default value"
' Parameter 3 : (String) "Unlocked"
' Parameter 4 : (Boolean) False
'--------------------------------------------------

End Sub
