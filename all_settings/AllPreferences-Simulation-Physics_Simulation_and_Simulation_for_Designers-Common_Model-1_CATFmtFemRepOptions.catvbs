Language="VBSCRIPT"

Sub CATMain()

Set settingControllers1 = CATIA.SettingControllers

Set settingRepository1 = settingControllers1.Item("CATFmtFemRepOptions")

long1 = settingRepository1.GetAttr("ScenarioResultSyncMask")
'--------------------------------------------------
' Parameter 1 : (String) "ScenarioResultSyncMask"
' Returned value : (Variant) (Long) 1
'--------------------------------------------------

Dim bSTR1
bSTR1 = ""
Dim bSTR2
bSTR2 = ""
Dim boolean1
settingRepository1.GetAttrInfo "ScenarioResultSyncMask", bSTR1, bSTR2, boolean1
'--------------------------------------------------
' Parameter 1 : (String) "ScenarioResultSyncMask"
' Parameter 2 : (String) "Default value"
' Parameter 3 : (String) "Unlocked"
' Parameter 4 : (Boolean) False
'--------------------------------------------------

long2 = settingRepository1.GetAttr("VisuMode")
'--------------------------------------------------
' Parameter 1 : (String) "VisuMode"
' Returned value : (Variant) (Long) 3
'--------------------------------------------------

Dim bSTR3
bSTR3 = ""
Dim bSTR4
bSTR4 = ""
Dim boolean2
settingRepository1.GetAttrInfo "VisuMode", bSTR3, bSTR4, boolean2
'--------------------------------------------------
' Parameter 1 : (String) "VisuMode"
' Parameter 2 : (String) "Default value"
' Parameter 3 : (String) "Unlocked"
' Parameter 4 : (Boolean) False
'--------------------------------------------------

long3 = settingRepository1.GetAttr("AutomaticNaming")
'--------------------------------------------------
' Parameter 1 : (String) "AutomaticNaming"
' Returned value : (Variant) (Long) 0
'--------------------------------------------------

Dim bSTR5
bSTR5 = ""
Dim bSTR6
bSTR6 = ""
Dim boolean3
settingRepository1.GetAttrInfo "AutomaticNaming", bSTR5, bSTR6, boolean3
'--------------------------------------------------
' Parameter 1 : (String) "AutomaticNaming"
' Parameter 2 : (String) "Default value"
' Parameter 3 : (String) "Unlocked"
' Parameter 4 : (Boolean) False
'--------------------------------------------------

long4 = settingRepository1.GetAttr("AutomaticNamingConnectionMesh")
'--------------------------------------------------
' Parameter 1 : (String) "AutomaticNamingConnectionMesh"
' Returned value : (Variant) (Long) 0
'--------------------------------------------------

Dim bSTR7
bSTR7 = ""
Dim bSTR8
bSTR8 = ""
Dim boolean4
settingRepository1.GetAttrInfo "AutomaticNamingConnectionMesh", bSTR7, bSTR8, boolean4
'--------------------------------------------------
' Parameter 1 : (String) "AutomaticNamingConnectionMesh"
' Parameter 2 : (String) "Default value"
' Parameter 3 : (String) "Unlocked"
' Parameter 4 : (Boolean) False
'--------------------------------------------------

End Sub
