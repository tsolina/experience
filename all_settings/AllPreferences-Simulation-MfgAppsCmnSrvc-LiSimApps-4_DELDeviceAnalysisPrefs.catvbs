Language="VBSCRIPT"

Sub CATMain()

Set settingControllers1 = CATIA.SettingControllers

Set settingRepository1 = settingControllers1.Item("DNBDeviceBase")

long1 = settingRepository1.GetAttr("TravelLimit")
'--------------------------------------------------
' Parameter 1 : (String) "TravelLimit"
' Returned value : (Variant) (Long) 0
'--------------------------------------------------

Dim bSTR1
bSTR1 = ""
Dim bSTR2
bSTR2 = ""
Dim boolean1
settingRepository1.GetAttrInfo "TravelLimit", bSTR1, bSTR2, boolean1
'--------------------------------------------------
' Parameter 1 : (String) "TravelLimit"
' Parameter 2 : (String) "Default value"
' Parameter 3 : (String) "Unlocked"
' Parameter 4 : (Boolean) False
'--------------------------------------------------

long2 = settingRepository1.GetAttr("SoftLimit")
'--------------------------------------------------
' Parameter 1 : (String) "SoftLimit"
' Returned value : (Variant) (Long) 0
'--------------------------------------------------

Dim bSTR3
bSTR3 = ""
Dim bSTR4
bSTR4 = ""
Dim boolean2
settingRepository1.GetAttrInfo "SoftLimit", bSTR3, bSTR4, boolean2
'--------------------------------------------------
' Parameter 1 : (String) "SoftLimit"
' Parameter 2 : (String) "Default value"
' Parameter 3 : (String) "Unlocked"
' Parameter 4 : (Boolean) False
'--------------------------------------------------

long3 = settingRepository1.GetAttr("VelocityLimit")
'--------------------------------------------------
' Parameter 1 : (String) "VelocityLimit"
' Returned value : (Variant) (Long) 0
'--------------------------------------------------

Dim bSTR5
bSTR5 = ""
Dim bSTR6
bSTR6 = ""
Dim boolean3
settingRepository1.GetAttrInfo "VelocityLimit", bSTR5, bSTR6, boolean3
'--------------------------------------------------
' Parameter 1 : (String) "VelocityLimit"
' Parameter 2 : (String) "Default value"
' Parameter 3 : (String) "Unlocked"
' Parameter 4 : (Boolean) False
'--------------------------------------------------

long4 = settingRepository1.GetAttr("CautionZone")
'--------------------------------------------------
' Parameter 1 : (String) "CautionZone"
' Returned value : (Variant) (Long) 0
'--------------------------------------------------

Dim bSTR7
bSTR7 = ""
Dim bSTR8
bSTR8 = ""
Dim boolean4
settingRepository1.GetAttrInfo "CautionZone", bSTR7, bSTR8, boolean4
'--------------------------------------------------
' Parameter 1 : (String) "CautionZone"
' Parameter 2 : (String) "Default value"
' Parameter 3 : (String) "Unlocked"
' Parameter 4 : (Boolean) False
'--------------------------------------------------

double1 = settingRepository1.GetAttr("CnvNetworkTolerance")
'--------------------------------------------------
' Parameter 1 : (String) "CnvNetworkTolerance"
' Returned value : (Variant) (Double) 0.000500
'--------------------------------------------------

Dim bSTR9
bSTR9 = ""
Dim bSTR10
bSTR10 = ""
Dim boolean5
settingRepository1.GetAttrInfo "CnvNetworkTolerance", bSTR9, bSTR10, boolean5
'--------------------------------------------------
' Parameter 1 : (String) "CnvNetworkTolerance"
' Parameter 2 : (String) "Default value"
' Parameter 3 : (String) "Unlocked"
' Parameter 4 : (Boolean) False
'--------------------------------------------------

bSTR11 = settingRepository1.GetAttr("KinTemplatePath")
'--------------------------------------------------
' Parameter 1 : (String) "KinTemplatePath"
' Returned value : (Variant) (String) ""
'--------------------------------------------------

Dim bSTR12
bSTR12 = ""
Dim bSTR13
bSTR13 = ""
Dim boolean6
settingRepository1.GetAttrInfo "KinTemplatePath", bSTR12, bSTR13, boolean6
'--------------------------------------------------
' Parameter 1 : (String) "KinTemplatePath"
' Parameter 2 : (String) "Default value"
' Parameter 3 : (String) "Unlocked"
' Parameter 4 : (Boolean) False
'--------------------------------------------------

End Sub
