Language="VBSCRIPT"

Sub CATMain()

Set settingControllers1 = CATIA.SettingControllers

Set settingRepository1 = settingControllers1.Item("CAT3DAppVNavSettings")

long1 = settingRepository1.GetAttr("NavigationMode")
'--------------------------------------------------
' Parameter 1 : (String) "NavigationMode"
' Returned value : (Variant) (Long) 1
'--------------------------------------------------

Dim bSTR1
bSTR1 = ""
Dim bSTR2
bSTR2 = ""
Dim boolean1
settingRepository1.GetAttrInfo "NavigationMode", bSTR1, bSTR2, boolean1
'--------------------------------------------------
' Parameter 1 : (String) "NavigationMode"
' Parameter 2 : (String) "Default value"
' Parameter 3 : (String) "Unlocked"
' Parameter 4 : (Boolean) False
'--------------------------------------------------

long2 = settingRepository1.GetAttr("SlidingMode")
'--------------------------------------------------
' Parameter 1 : (String) "SlidingMode"
' Returned value : (Variant) (Long) 0
'--------------------------------------------------

Dim bSTR3
bSTR3 = ""
Dim bSTR4
bSTR4 = ""
Dim boolean2
settingRepository1.GetAttrInfo "SlidingMode", bSTR3, bSTR4, boolean2
'--------------------------------------------------
' Parameter 1 : (String) "SlidingMode"
' Parameter 2 : (String) "Default value"
' Parameter 3 : (String) "Unlocked"
' Parameter 4 : (Boolean) False
'--------------------------------------------------

long3 = settingRepository1.GetAttr("RotationDuringZoom")
'--------------------------------------------------
' Parameter 1 : (String) "RotationDuringZoom"
' Returned value : (Variant) (Long) 1
'--------------------------------------------------

Dim bSTR5
bSTR5 = ""
Dim bSTR6
bSTR6 = ""
Dim boolean3
settingRepository1.GetAttrInfo "RotationDuringZoom", bSTR5, bSTR6, boolean3
'--------------------------------------------------
' Parameter 1 : (String) "RotationDuringZoom"
' Parameter 2 : (String) "Default value"
' Parameter 3 : (String) "Unlocked"
' Parameter 4 : (Boolean) False
'--------------------------------------------------

long4 = settingRepository1.GetAttr("AnimationTimeActive")
'--------------------------------------------------
' Parameter 1 : (String) "AnimationTimeActive"
' Returned value : (Variant) (Long) 1
'--------------------------------------------------

Dim bSTR7
bSTR7 = ""
Dim bSTR8
bSTR8 = ""
Dim boolean4
settingRepository1.GetAttrInfo "AnimationTimeActive", bSTR7, bSTR8, boolean4
'--------------------------------------------------
' Parameter 1 : (String) "AnimationTimeActive"
' Parameter 2 : (String) "Default value"
' Parameter 3 : (String) "Unlocked"
' Parameter 4 : (Boolean) False
'--------------------------------------------------

long5 = settingRepository1.GetAttr("AnimationTime")
'--------------------------------------------------
' Parameter 1 : (String) "AnimationTime"
' Returned value : (Variant) (Long) 10
'--------------------------------------------------

Dim bSTR9
bSTR9 = ""
Dim bSTR10
bSTR10 = ""
Dim boolean5
settingRepository1.GetAttrInfo "AnimationTime", bSTR9, bSTR10, boolean5
'--------------------------------------------------
' Parameter 1 : (String) "AnimationTime"
' Parameter 2 : (String) "Default value"
' Parameter 3 : (String) "Unlocked"
' Parameter 4 : (Boolean) False
'--------------------------------------------------

End Sub
