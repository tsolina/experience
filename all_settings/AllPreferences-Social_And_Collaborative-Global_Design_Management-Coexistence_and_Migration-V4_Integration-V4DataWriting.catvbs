Language="VBSCRIPT"

Sub CATMain()

Set settingControllers1 = CATIA.SettingControllers

Set settingRepository1 = settingControllers1.Item("V4Writing")

long1 = settingRepository1.GetAttr("Code_page_Dest")
'--------------------------------------------------
' Parameter 1 : (String) "Code_page_Dest"
' Returned value : (Variant) (Long) 11
'--------------------------------------------------

Dim bSTR1
bSTR1 = ""
Dim bSTR2
bSTR2 = ""
Dim boolean1
settingRepository1.GetAttrInfo "Code_page_Dest", bSTR1, bSTR2, boolean1
'--------------------------------------------------
' Parameter 1 : (String) "Code_page_Dest"
' Parameter 2 : (String) "Default value"
' Parameter 3 : (String) "Unlocked"
' Parameter 4 : (Boolean) False
'--------------------------------------------------

double1 = settingRepository1.GetAttr("Model_Dimension")
'--------------------------------------------------
' Parameter 1 : (String) "Model_Dimension"
' Returned value : (Variant) (Double) 10.000000
'--------------------------------------------------

Dim bSTR3
bSTR3 = ""
Dim bSTR4
bSTR4 = ""
Dim boolean2
settingRepository1.GetAttrInfo "Model_Dimension", bSTR3, bSTR4, boolean2
'--------------------------------------------------
' Parameter 1 : (String) "Model_Dimension"
' Parameter 2 : (String) "Default value"
' Parameter 3 : (String) "Unlocked"
' Parameter 4 : (Boolean) False
'--------------------------------------------------

long2 = settingRepository1.GetAttr("Model_Unit")
'--------------------------------------------------
' Parameter 1 : (String) "Model_Unit"
' Returned value : (Variant) (Long) 0
'--------------------------------------------------

Dim bSTR5
bSTR5 = ""
Dim bSTR6
bSTR6 = ""
Dim boolean3
settingRepository1.GetAttrInfo "Model_Unit", bSTR5, bSTR6, boolean3
'--------------------------------------------------
' Parameter 1 : (String) "Model_Unit"
' Parameter 2 : (String) "Default value"
' Parameter 3 : (String) "Unlocked"
' Parameter 4 : (Boolean) False
'--------------------------------------------------

bSTR7 = settingRepository1.GetAttr("StartUp_Model_File_Path")
'--------------------------------------------------
' Parameter 1 : (String) "StartUp_Model_File_Path"
' Returned value : (Variant) (String) ""
'--------------------------------------------------

Dim bSTR8
bSTR8 = ""
Dim bSTR9
bSTR9 = ""
Dim boolean4
settingRepository1.GetAttrInfo "StartUp_Model_File_Path", bSTR8, bSTR9, boolean4
'--------------------------------------------------
' Parameter 1 : (String) "StartUp_Model_File_Path"
' Parameter 2 : (String) "Default value"
' Parameter 3 : (String) "Unlocked"
' Parameter 4 : (Boolean) False
'--------------------------------------------------

bSTR10 = settingRepository1.GetAttr("ModeErrorDisplay")
'--------------------------------------------------
' Parameter 1 : (String) "ModeErrorDisplay"
' Returned value : (Variant) (String) "Refuse"
'--------------------------------------------------

Dim bSTR11
bSTR11 = ""
Dim bSTR12
bSTR12 = ""
Dim boolean5
settingRepository1.GetAttrInfo "ModeErrorDisplay", bSTR11, bSTR12, boolean5
'--------------------------------------------------
' Parameter 1 : (String) "ModeErrorDisplay"
' Parameter 2 : (String) "Default value"
' Parameter 3 : (String) "Unlocked"
' Parameter 4 : (Boolean) False
'--------------------------------------------------

bSTR13 = settingRepository1.GetAttr("ModeCreateDisplay")
'--------------------------------------------------
' Parameter 1 : (String) "ModeCreateDisplay"
' Returned value : (Variant) (String) "NeverCreate"
'--------------------------------------------------

Dim bSTR14
bSTR14 = ""
Dim bSTR15
bSTR15 = ""
Dim boolean6
settingRepository1.GetAttrInfo "ModeCreateDisplay", bSTR14, bSTR15, boolean6
'--------------------------------------------------
' Parameter 1 : (String) "ModeCreateDisplay"
' Parameter 2 : (String) "Default value"
' Parameter 3 : (String) "Unlocked"
' Parameter 4 : (Boolean) False
'--------------------------------------------------

bSTR16 = settingRepository1.GetAttr("Model_File_Name")
'--------------------------------------------------
' Parameter 1 : (String) "Model_File_Name"
' Returned value : (Variant) (String) "Normal"
'--------------------------------------------------

Dim bSTR17
bSTR17 = ""
Dim bSTR18
bSTR18 = ""
Dim boolean7
settingRepository1.GetAttrInfo "Model_File_Name", bSTR17, bSTR18, boolean7
'--------------------------------------------------
' Parameter 1 : (String) "Model_File_Name"
' Parameter 2 : (String) "Default value"
' Parameter 3 : (String) "Unlocked"
' Parameter 4 : (Boolean) False
'--------------------------------------------------

bSTR19 = settingRepository1.GetAttr("Model_File_NameCheckBox")
'--------------------------------------------------
' Parameter 1 : (String) "Model_File_NameCheckBox"
' Returned value : (Variant) (String) "Normal"
'--------------------------------------------------

Dim bSTR20
bSTR20 = ""
Dim bSTR21
bSTR21 = ""
Dim boolean8
settingRepository1.GetAttrInfo "Model_File_NameCheckBox", bSTR20, bSTR21, boolean8
'--------------------------------------------------
' Parameter 1 : (String) "Model_File_NameCheckBox"
' Parameter 2 : (String) "Default value"
' Parameter 3 : (String) "Unlocked"
' Parameter 4 : (Boolean) False
'--------------------------------------------------

long3 = settingRepository1.GetAttr("CleanTolButton")
'--------------------------------------------------
' Parameter 1 : (String) "CleanTolButton"
' Returned value : (Variant) (Long) 0
'--------------------------------------------------

Dim bSTR22
bSTR22 = ""
Dim bSTR23
bSTR23 = ""
Dim boolean9
settingRepository1.GetAttrInfo "CleanTolButton", bSTR22, bSTR23, boolean9
'--------------------------------------------------
' Parameter 1 : (String) "CleanTolButton"
' Parameter 2 : (String) "Default value"
' Parameter 3 : (String) "Unlocked"
' Parameter 4 : (Boolean) False
'--------------------------------------------------

double2 = settingRepository1.GetAttr("CleanTolEditor")
'--------------------------------------------------
' Parameter 1 : (String) "CleanTolEditor"
' Returned value : (Variant) (Double) 0.000000
'--------------------------------------------------

Dim bSTR24
bSTR24 = ""
Dim bSTR25
bSTR25 = ""
Dim boolean10
settingRepository1.GetAttrInfo "CleanTolEditor", bSTR24, bSTR25, boolean10
'--------------------------------------------------
' Parameter 1 : (String) "CleanTolEditor"
' Parameter 2 : (String) "Default value"
' Parameter 3 : (String) "Unlocked"
' Parameter 4 : (Boolean) False
'--------------------------------------------------

End Sub
