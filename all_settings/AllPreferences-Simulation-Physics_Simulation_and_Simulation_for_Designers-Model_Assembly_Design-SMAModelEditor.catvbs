Language="VBSCRIPT"

Sub CATMain()

Set settingControllers1 = CATIA.SettingControllers

Set settingRepository1 = settingControllers1.Item("SMAModelEditor")

boolean1 = settingRepository1.GetAttr("EnableGeneration")
'--------------------------------------------------
' Parameter 1 : (String) "EnableGeneration"
' Returned value : (Variant) (Boolean) True
'--------------------------------------------------

Dim bSTR1
bSTR1 = ""
Dim bSTR2
bSTR2 = ""
Dim boolean2
settingRepository1.GetAttrInfo "EnableGeneration", bSTR1, bSTR2, boolean2
'--------------------------------------------------
' Parameter 1 : (String) "EnableGeneration"
' Parameter 2 : (String) "Default value"
' Parameter 3 : (String) "Unlocked"
' Parameter 4 : (Boolean) False
'--------------------------------------------------

bSTR3 = settingRepository1.GetAttr("PatternChoice")
'--------------------------------------------------
' Parameter 1 : (String) "PatternChoice"
' Returned value : (Variant) (String) "with"
'--------------------------------------------------

Dim bSTR4
bSTR4 = ""
Dim bSTR5
bSTR5 = ""
Dim boolean3
settingRepository1.GetAttrInfo "PatternChoice", bSTR4, bSTR5, boolean3
'--------------------------------------------------
' Parameter 1 : (String) "PatternChoice"
' Parameter 2 : (String) "Default value"
' Parameter 3 : (String) "Unlocked"
' Parameter 4 : (Boolean) False
'--------------------------------------------------

bSTR6 = settingRepository1.GetAttr("Extension")
'--------------------------------------------------
' Parameter 1 : (String) "Extension"
' Returned value : (Variant) (String) "inp"
'--------------------------------------------------

Dim bSTR7
bSTR7 = ""
Dim bSTR8
bSTR8 = ""
Dim boolean4
settingRepository1.GetAttrInfo "Extension", bSTR7, bSTR8, boolean4
'--------------------------------------------------
' Parameter 1 : (String) "Extension"
' Parameter 2 : (String) "Default value"
' Parameter 3 : (String) "Unlocked"
' Parameter 4 : (Boolean) False
'--------------------------------------------------

bSTR9 = settingRepository1.GetAttr("WithoutRepNameText")
'--------------------------------------------------
' Parameter 1 : (String) "WithoutRepNameText"
' Returned value : (Variant) (String) ""
'--------------------------------------------------

Dim bSTR10
bSTR10 = ""
Dim bSTR11
bSTR11 = ""
Dim boolean5
settingRepository1.GetAttrInfo "WithoutRepNameText", bSTR10, bSTR11, boolean5
'--------------------------------------------------
' Parameter 1 : (String) "WithoutRepNameText"
' Parameter 2 : (String) "Default value"
' Parameter 3 : (String) "Unlocked"
' Parameter 4 : (Boolean) False
'--------------------------------------------------

bSTR12 = settingRepository1.GetAttr("WithRepNamePrefix")
'--------------------------------------------------
' Parameter 1 : (String) "WithRepNamePrefix"
' Returned value : (Variant) (String) ""
'--------------------------------------------------

Dim bSTR13
bSTR13 = ""
Dim bSTR14
bSTR14 = ""
Dim boolean6
settingRepository1.GetAttrInfo "WithRepNamePrefix", bSTR13, bSTR14, boolean6
'--------------------------------------------------
' Parameter 1 : (String) "WithRepNamePrefix"
' Parameter 2 : (String) "Default value"
' Parameter 3 : (String) "Unlocked"
' Parameter 4 : (Boolean) False
'--------------------------------------------------

bSTR15 = settingRepository1.GetAttr("WithRepNameSuffix")
'--------------------------------------------------
' Parameter 1 : (String) "WithRepNameSuffix"
' Returned value : (Variant) (String) ""
'--------------------------------------------------

Dim bSTR16
bSTR16 = ""
Dim bSTR17
bSTR17 = ""
Dim boolean7
settingRepository1.GetAttrInfo "WithRepNameSuffix", bSTR16, bSTR17, boolean7
'--------------------------------------------------
' Parameter 1 : (String) "WithRepNameSuffix"
' Parameter 2 : (String) "Default value"
' Parameter 3 : (String) "Unlocked"
' Parameter 4 : (Boolean) False
'--------------------------------------------------

End Sub
