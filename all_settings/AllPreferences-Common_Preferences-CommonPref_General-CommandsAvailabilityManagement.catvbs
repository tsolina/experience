Language="VBSCRIPT"

Sub CATMain()

Set settingControllers1 = CATIA.SettingControllers

Set settingRepository1 = settingControllers1.Item("AfrDeclUnavailableCommands")

long1 = settingRepository1.GetAttr("Lock")
'--------------------------------------------------
' Parameter 1 : (String) "Lock"
' Returned value : (Variant) (Long) 0
'--------------------------------------------------

Dim bSTR1
bSTR1 = ""
Dim bSTR2
bSTR2 = ""
Dim boolean1
settingRepository1.GetAttrInfo "Lock", bSTR1, bSTR2, boolean1
'--------------------------------------------------
' Parameter 1 : (String) "Lock"
' Parameter 2 : (String) "Default value"
' Parameter 3 : (String) "Unlocked"
' Parameter 4 : (Boolean) False
'--------------------------------------------------

long2 = settingRepository1.GetAttr("Lock")
'--------------------------------------------------
' Parameter 1 : (String) "Lock"
' Returned value : (Variant) (Long) 0
'--------------------------------------------------

Dim bSTR3
bSTR3 = ""
Dim bSTR4
bSTR4 = ""
Dim boolean2
settingRepository1.GetAttrInfo "Lock", bSTR3, bSTR4, boolean2
'--------------------------------------------------
' Parameter 1 : (String) "Lock"
' Parameter 2 : (String) "Default value"
' Parameter 3 : (String) "Unlocked"
' Parameter 4 : (Boolean) False
'--------------------------------------------------

End Sub
