Language="VBSCRIPT"

Sub CATMain()

Set settingControllers1 = CATIA.SettingControllers

Set settingRepository1 = settingControllers1.Item("VPMNavigator")

long1 = settingRepository1.GetAttr("DisplayThumbnailsExploreParents")
'--------------------------------------------------
' Parameter 1 : (String) "DisplayThumbnailsExploreParents"
' Returned value : (Variant) (Long) 1
'--------------------------------------------------

Dim bSTR1
bSTR1 = ""
Dim bSTR2
bSTR2 = ""
Dim boolean1
settingRepository1.GetAttrInfo "DisplayThumbnailsExploreParents", bSTR1, bSTR2, boolean1
'--------------------------------------------------
' Parameter 1 : (String) "DisplayThumbnailsExploreParents"
' Parameter 2 : (String) "Default value"
' Parameter 3 : (String) "Unlocked"
' Parameter 4 : (Boolean) False
'--------------------------------------------------

long2 = settingRepository1.GetAttr("DisplayTilesExploreParents")
'--------------------------------------------------
' Parameter 1 : (String) "DisplayTilesExploreParents"
' Returned value : (Variant) (Long) 1
'--------------------------------------------------

Dim bSTR3
bSTR3 = ""
Dim bSTR4
bSTR4 = ""
Dim boolean2
settingRepository1.GetAttrInfo "DisplayTilesExploreParents", bSTR3, bSTR4, boolean2
'--------------------------------------------------
' Parameter 1 : (String) "DisplayTilesExploreParents"
' Parameter 2 : (String) "Default value"
' Parameter 3 : (String) "Unlocked"
' Parameter 4 : (Boolean) False
'--------------------------------------------------

End Sub
