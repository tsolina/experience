Language="VBSCRIPT"

Sub CATMain()

Set settingControllers1 = CATIA.SettingControllers

Set settingRepository1 = settingControllers1.Item("CATKinMechanismWkb")

boolean1 = settingRepository1.GetAttr("MechanismManagementForMotion")
'--------------------------------------------------
' Parameter 1 : (String) "MechanismManagementForMotion"
' Returned value : (Variant) (Boolean) False
'--------------------------------------------------

Dim bSTR1
bSTR1 = ""
Dim bSTR2
bSTR2 = ""
Dim boolean2
settingRepository1.GetAttrInfo "MechanismManagementForMotion", bSTR1, bSTR2, boolean2
'--------------------------------------------------
' Parameter 1 : (String) "MechanismManagementForMotion"
' Parameter 2 : (String) "Default value"
' Parameter 3 : (String) "Unlocked"
' Parameter 4 : (Boolean) False
'--------------------------------------------------

boolean3 = settingRepository1.GetAttr("MechanismUpdation")
'--------------------------------------------------
' Parameter 1 : (String) "MechanismUpdation"
' Returned value : (Variant) (Boolean) False
'--------------------------------------------------

Dim bSTR3
bSTR3 = ""
Dim bSTR4
bSTR4 = ""
Dim boolean4
settingRepository1.GetAttrInfo "MechanismUpdation", bSTR3, bSTR4, boolean4
'--------------------------------------------------
' Parameter 1 : (String) "MechanismUpdation"
' Parameter 2 : (String) "Default value"
' Parameter 3 : (String) "Unlocked"
' Parameter 4 : (Boolean) False
'--------------------------------------------------

boolean5 = settingRepository1.GetAttr("MechanismUpdationNotif")
'--------------------------------------------------
' Parameter 1 : (String) "MechanismUpdationNotif"
' Returned value : (Variant) (Boolean) True
'--------------------------------------------------

Dim bSTR5
bSTR5 = ""
Dim bSTR6
bSTR6 = ""
Dim boolean6
settingRepository1.GetAttrInfo "MechanismUpdationNotif", bSTR5, bSTR6, boolean6
'--------------------------------------------------
' Parameter 1 : (String) "MechanismUpdationNotif"
' Parameter 2 : (String) "Default value"
' Parameter 3 : (String) "Unlocked"
' Parameter 4 : (Boolean) False
'--------------------------------------------------

End Sub
