Language="VBSCRIPT"

Sub CATMain()

Set settingControllers1 = CATIA.SettingControllers

Set settingRepository1 = settingControllers1.Item("DraftingOptions")

boolean1 = settingRepository1.GetAttr("DrwInsertDrawingInProductPart")
'--------------------------------------------------
' Parameter 1 : (String) "DrwInsertDrawingInProductPart"
' Returned value : (Variant) (Boolean) True
'--------------------------------------------------

Dim bSTR1
bSTR1 = ""
Dim bSTR2
bSTR2 = ""
Dim boolean2
settingRepository1.GetAttrInfo "DrwInsertDrawingInProductPart", bSTR1, bSTR2, boolean2
'--------------------------------------------------
' Parameter 1 : (String) "DrwInsertDrawingInProductPart"
' Parameter 2 : (String) "Default value"
' Parameter 3 : (String) "Unlocked"
' Parameter 4 : (Boolean) False
'--------------------------------------------------

boolean3 = settingRepository1.GetAttr("DrwMakeDrawingShareable")
'--------------------------------------------------
' Parameter 1 : (String) "DrwMakeDrawingShareable"
' Returned value : (Variant) (Boolean) True
'--------------------------------------------------

Dim bSTR3
bSTR3 = ""
Dim bSTR4
bSTR4 = ""
Dim boolean4
settingRepository1.GetAttrInfo "DrwMakeDrawingShareable", bSTR3, bSTR4, boolean4
'--------------------------------------------------
' Parameter 1 : (String) "DrwMakeDrawingShareable"
' Parameter 2 : (String) "Default value"
' Parameter 3 : (String) "Unlocked"
' Parameter 4 : (Boolean) False
'--------------------------------------------------

bSTR5 = settingRepository1.GetAttr("standard")
'--------------------------------------------------
' Parameter 1 : (String) "standard"
' Returned value : (Variant) (String) "ISO"
'--------------------------------------------------

Dim bSTR6
bSTR6 = ""
Dim bSTR7
bSTR7 = ""
Dim boolean5
settingRepository1.GetAttrInfo "standard", bSTR6, bSTR7, boolean5
'--------------------------------------------------
' Parameter 1 : (String) "standard"
' Parameter 2 : (String) "Default value"
' Parameter 3 : (String) "Unlocked"
' Parameter 4 : (Boolean) False
'--------------------------------------------------

bSTR8 = settingRepository1.GetAttr("FrameTemplate")
'--------------------------------------------------
' Parameter 1 : (String) "FrameTemplate"
' Returned value : (Variant) (String) ""
'--------------------------------------------------

Dim bSTR9
bSTR9 = ""
Dim bSTR10
bSTR10 = ""
Dim boolean6
settingRepository1.GetAttrInfo "FrameTemplate", bSTR9, bSTR10, boolean6
'--------------------------------------------------
' Parameter 1 : (String) "FrameTemplate"
' Parameter 2 : (String) "Default value"
' Parameter 3 : (String) "Unlocked"
' Parameter 4 : (Boolean) False
'--------------------------------------------------

uLong1 = settingRepository1.GetAttr("NumOfFrameTemplates")
'--------------------------------------------------
' Parameter 1 : (String) "NumOfFrameTemplates"
' Returned value : (Variant) (Unsigned Long) 0
'--------------------------------------------------

Dim bSTR11
bSTR11 = ""
Dim bSTR12
bSTR12 = ""
Dim boolean7
settingRepository1.GetAttrInfo "NumOfFrameTemplates", bSTR11, bSTR12, boolean7
'--------------------------------------------------
' Parameter 1 : (String) "NumOfFrameTemplates"
' Parameter 2 : (String) "Default value"
' Parameter 3 : (String) "Unlocked"
' Parameter 4 : (Boolean) False
'--------------------------------------------------

settingRepository1.GetAttrArray "FrameTemplates"
'--------------------------------------------------
' Parameter 1 : (String) "FrameTemplates"
'--------------------------------------------------

Dim bSTR13
bSTR13 = ""
Dim bSTR14
bSTR14 = ""
Dim boolean8
settingRepository1.GetAttrInfo "FrameTemplates", bSTR13, bSTR14, boolean8
'--------------------------------------------------
' Parameter 1 : (String) "FrameTemplates"
' Parameter 2 : (String) "Default value"
' Parameter 3 : (String) "Unlocked"
' Parameter 4 : (Boolean) False
'--------------------------------------------------

settingRepository1.GetAttrArray "FrameTemplateIDs"
'--------------------------------------------------
' Parameter 1 : (String) "FrameTemplateIDs"
'--------------------------------------------------

Dim bSTR15
bSTR15 = ""
Dim bSTR16
bSTR16 = ""
Dim boolean9
settingRepository1.GetAttrInfo "FrameTemplateIDs", bSTR15, bSTR16, boolean9
'--------------------------------------------------
' Parameter 1 : (String) "FrameTemplateIDs"
' Parameter 2 : (String) "Default value"
' Parameter 3 : (String) "Unlocked"
' Parameter 4 : (Boolean) False
'--------------------------------------------------

boolean10 = settingRepository1.GetAttr("FrameTemplateAdd")
'--------------------------------------------------
' Parameter 1 : (String) "FrameTemplateAdd"
' Returned value : (Variant) (Boolean) False
'--------------------------------------------------

Dim bSTR17
bSTR17 = ""
Dim bSTR18
bSTR18 = ""
Dim boolean11
settingRepository1.GetAttrInfo "FrameTemplateAdd", bSTR17, bSTR18, boolean11
'--------------------------------------------------
' Parameter 1 : (String) "FrameTemplateAdd"
' Parameter 2 : (String) "Default value"
' Parameter 3 : (String) "Unlocked"
' Parameter 4 : (Boolean) False
'--------------------------------------------------

boolean12 = settingRepository1.GetAttr("FrameTemplateRemove")
'--------------------------------------------------
' Parameter 1 : (String) "FrameTemplateRemove"
' Returned value : (Variant) (Boolean) False
'--------------------------------------------------

Dim bSTR19
bSTR19 = ""
Dim bSTR20
bSTR20 = ""
Dim boolean13
settingRepository1.GetAttrInfo "FrameTemplateRemove", bSTR19, bSTR20, boolean13
'--------------------------------------------------
' Parameter 1 : (String) "FrameTemplateRemove"
' Parameter 2 : (String) "Default value"
' Parameter 3 : (String) "Unlocked"
' Parameter 4 : (Boolean) False
'--------------------------------------------------

bSTR21 = settingRepository1.GetAttr("TitleBlockTemplate")
'--------------------------------------------------
' Parameter 1 : (String) "TitleBlockTemplate"
' Returned value : (Variant) (String) ""
'--------------------------------------------------

Dim bSTR22
bSTR22 = ""
Dim bSTR23
bSTR23 = ""
Dim boolean14
settingRepository1.GetAttrInfo "TitleBlockTemplate", bSTR22, bSTR23, boolean14
'--------------------------------------------------
' Parameter 1 : (String) "TitleBlockTemplate"
' Parameter 2 : (String) "Default value"
' Parameter 3 : (String) "Unlocked"
' Parameter 4 : (Boolean) False
'--------------------------------------------------

uLong2 = settingRepository1.GetAttr("NumOfTitleBlockTemplates")
'--------------------------------------------------
' Parameter 1 : (String) "NumOfTitleBlockTemplates"
' Returned value : (Variant) (Unsigned Long) 0
'--------------------------------------------------

Dim bSTR24
bSTR24 = ""
Dim bSTR25
bSTR25 = ""
Dim boolean15
settingRepository1.GetAttrInfo "NumOfTitleBlockTemplates", bSTR24, bSTR25, boolean15
'--------------------------------------------------
' Parameter 1 : (String) "NumOfTitleBlockTemplates"
' Parameter 2 : (String) "Default value"
' Parameter 3 : (String) "Unlocked"
' Parameter 4 : (Boolean) False
'--------------------------------------------------

settingRepository1.GetAttrArray "TitleBlockTemplates"
'--------------------------------------------------
' Parameter 1 : (String) "TitleBlockTemplates"
'--------------------------------------------------

Dim bSTR26
bSTR26 = ""
Dim bSTR27
bSTR27 = ""
Dim boolean16
settingRepository1.GetAttrInfo "TitleBlockTemplates", bSTR26, bSTR27, boolean16
'--------------------------------------------------
' Parameter 1 : (String) "TitleBlockTemplates"
' Parameter 2 : (String) "Default value"
' Parameter 3 : (String) "Unlocked"
' Parameter 4 : (Boolean) False
'--------------------------------------------------

settingRepository1.GetAttrArray "TitleBlockTemplateIDs"
'--------------------------------------------------
' Parameter 1 : (String) "TitleBlockTemplateIDs"
'--------------------------------------------------

Dim bSTR28
bSTR28 = ""
Dim bSTR29
bSTR29 = ""
Dim boolean17
settingRepository1.GetAttrInfo "TitleBlockTemplateIDs", bSTR28, bSTR29, boolean17
'--------------------------------------------------
' Parameter 1 : (String) "TitleBlockTemplateIDs"
' Parameter 2 : (String) "Default value"
' Parameter 3 : (String) "Unlocked"
' Parameter 4 : (Boolean) False
'--------------------------------------------------

boolean18 = settingRepository1.GetAttr("TitleBlockTemplateAdd")
'--------------------------------------------------
' Parameter 1 : (String) "TitleBlockTemplateAdd"
' Returned value : (Variant) (Boolean) False
'--------------------------------------------------

Dim bSTR30
bSTR30 = ""
Dim bSTR31
bSTR31 = ""
Dim boolean19
settingRepository1.GetAttrInfo "TitleBlockTemplateAdd", bSTR30, bSTR31, boolean19
'--------------------------------------------------
' Parameter 1 : (String) "TitleBlockTemplateAdd"
' Parameter 2 : (String) "Default value"
' Parameter 3 : (String) "Unlocked"
' Parameter 4 : (Boolean) False
'--------------------------------------------------

boolean20 = settingRepository1.GetAttr("TitleBlockTemplateRemove")
'--------------------------------------------------
' Parameter 1 : (String) "TitleBlockTemplateRemove"
' Returned value : (Variant) (Boolean) False
'--------------------------------------------------

Dim bSTR32
bSTR32 = ""
Dim bSTR33
bSTR33 = ""
Dim boolean21
settingRepository1.GetAttrInfo "TitleBlockTemplateRemove", bSTR32, bSTR33, boolean21
'--------------------------------------------------
' Parameter 1 : (String) "TitleBlockTemplateRemove"
' Parameter 2 : (String) "Default value"
' Parameter 3 : (String) "Unlocked"
' Parameter 4 : (Boolean) False
'--------------------------------------------------

bSTR34 = settingRepository1.GetAttr("RevisionTableTemplate")
'--------------------------------------------------
' Parameter 1 : (String) "RevisionTableTemplate"
' Returned value : (Variant) (String) ""
'--------------------------------------------------

Dim bSTR35
bSTR35 = ""
Dim bSTR36
bSTR36 = ""
Dim boolean22
settingRepository1.GetAttrInfo "RevisionTableTemplate", bSTR35, bSTR36, boolean22
'--------------------------------------------------
' Parameter 1 : (String) "RevisionTableTemplate"
' Parameter 2 : (String) "Default value"
' Parameter 3 : (String) "Unlocked"
' Parameter 4 : (Boolean) False
'--------------------------------------------------

uLong3 = settingRepository1.GetAttr("NumOfRevisionTableTemplates")
'--------------------------------------------------
' Parameter 1 : (String) "NumOfRevisionTableTemplates"
' Returned value : (Variant) (Unsigned Long) 0
'--------------------------------------------------

Dim bSTR37
bSTR37 = ""
Dim bSTR38
bSTR38 = ""
Dim boolean23
settingRepository1.GetAttrInfo "NumOfRevisionTableTemplates", bSTR37, bSTR38, boolean23
'--------------------------------------------------
' Parameter 1 : (String) "NumOfRevisionTableTemplates"
' Parameter 2 : (String) "Default value"
' Parameter 3 : (String) "Unlocked"
' Parameter 4 : (Boolean) False
'--------------------------------------------------

settingRepository1.GetAttrArray "RevisionTableTemplates"
'--------------------------------------------------
' Parameter 1 : (String) "RevisionTableTemplates"
'--------------------------------------------------

Dim bSTR39
bSTR39 = ""
Dim bSTR40
bSTR40 = ""
Dim boolean24
settingRepository1.GetAttrInfo "RevisionTableTemplates", bSTR39, bSTR40, boolean24
'--------------------------------------------------
' Parameter 1 : (String) "RevisionTableTemplates"
' Parameter 2 : (String) "Default value"
' Parameter 3 : (String) "Unlocked"
' Parameter 4 : (Boolean) False
'--------------------------------------------------

settingRepository1.GetAttrArray "RevisionTableTemplateIDs"
'--------------------------------------------------
' Parameter 1 : (String) "RevisionTableTemplateIDs"
'--------------------------------------------------

Dim bSTR41
bSTR41 = ""
Dim bSTR42
bSTR42 = ""
Dim boolean25
settingRepository1.GetAttrInfo "RevisionTableTemplateIDs", bSTR41, bSTR42, boolean25
'--------------------------------------------------
' Parameter 1 : (String) "RevisionTableTemplateIDs"
' Parameter 2 : (String) "Default value"
' Parameter 3 : (String) "Unlocked"
' Parameter 4 : (Boolean) False
'--------------------------------------------------

boolean26 = settingRepository1.GetAttr("RevisionTableTemplateAdd")
'--------------------------------------------------
' Parameter 1 : (String) "RevisionTableTemplateAdd"
' Returned value : (Variant) (Boolean) False
'--------------------------------------------------

Dim bSTR43
bSTR43 = ""
Dim bSTR44
bSTR44 = ""
Dim boolean27
settingRepository1.GetAttrInfo "RevisionTableTemplateAdd", bSTR43, bSTR44, boolean27
'--------------------------------------------------
' Parameter 1 : (String) "RevisionTableTemplateAdd"
' Parameter 2 : (String) "Default value"
' Parameter 3 : (String) "Unlocked"
' Parameter 4 : (Boolean) False
'--------------------------------------------------

boolean28 = settingRepository1.GetAttr("RevisionTableTemplateRemove")
'--------------------------------------------------
' Parameter 1 : (String) "RevisionTableTemplateRemove"
' Returned value : (Variant) (Boolean) False
'--------------------------------------------------

Dim bSTR45
bSTR45 = ""
Dim bSTR46
bSTR46 = ""
Dim boolean29
settingRepository1.GetAttrInfo "RevisionTableTemplateRemove", bSTR45, bSTR46, boolean29
'--------------------------------------------------
' Parameter 1 : (String) "RevisionTableTemplateRemove"
' Parameter 2 : (String) "Default value"
' Parameter 3 : (String) "Unlocked"
' Parameter 4 : (Boolean) False
'--------------------------------------------------

boolean30 = settingRepository1.GetAttr("DrwCalloutSize")
'--------------------------------------------------
' Parameter 1 : (String) "DrwCalloutSize"
' Returned value : (Variant) (Boolean) True
'--------------------------------------------------

Dim bSTR47
bSTR47 = ""
Dim bSTR48
bSTR48 = ""
Dim boolean31
settingRepository1.GetAttrInfo "DrwCalloutSize", bSTR47, bSTR48, boolean31
'--------------------------------------------------
' Parameter 1 : (String) "DrwCalloutSize"
' Parameter 2 : (String) "Default value"
' Parameter 3 : (String) "Unlocked"
' Parameter 4 : (Boolean) False
'--------------------------------------------------

Dim arrayOfVariantOfULong1
arrayOfVariantOfULong1 = settingRepository1.GetAttrArray("Drw_settings_ConstructEltsColor")
'--------------------------------------------------
' Parameter 1 : (String) "Drw_settings_ConstructEltsColor"
' Returned value : (Array) 
'    Array[0] : (Variant) (Unsigned Long) 140
'    Array[1] : (Variant) (Unsigned Long) 140
'    Array[2] : (Variant) (Unsigned Long) 140
'--------------------------------------------------

Dim bSTR49
bSTR49 = ""
Dim bSTR50
bSTR50 = ""
Dim boolean32
settingRepository1.GetAttrInfo "Drw_settings_ConstructEltsColor", bSTR49, bSTR50, boolean32
'--------------------------------------------------
' Parameter 1 : (String) "Drw_settings_ConstructEltsColor"
' Parameter 2 : (String) "Default value"
' Parameter 3 : (String) "Unlocked"
' Parameter 4 : (Boolean) False
'--------------------------------------------------

boolean33 = settingRepository1.GetAttr("DrwLineUpAutoFunnel")
'--------------------------------------------------
' Parameter 1 : (String) "DrwLineUpAutoFunnel"
' Returned value : (Variant) (Boolean) True
'--------------------------------------------------

Dim bSTR51
bSTR51 = ""
Dim bSTR52
bSTR52 = ""
Dim boolean34
settingRepository1.GetAttrInfo "DrwLineUpAutoFunnel", bSTR51, bSTR52, boolean34
'--------------------------------------------------
' Parameter 1 : (String) "DrwLineUpAutoFunnel"
' Parameter 2 : (String) "Default value"
' Parameter 3 : (String) "Unlocked"
' Parameter 4 : (Boolean) False
'--------------------------------------------------

boolean35 = settingRepository1.GetAttr("ViewName")
'--------------------------------------------------
' Parameter 1 : (String) "ViewName"
' Returned value : (Variant) (Boolean) True
'--------------------------------------------------

Dim bSTR53
bSTR53 = ""
Dim bSTR54
bSTR54 = ""
Dim boolean36
settingRepository1.GetAttrInfo "ViewName", bSTR53, bSTR54, boolean36
'--------------------------------------------------
' Parameter 1 : (String) "ViewName"
' Parameter 2 : (String) "Default value"
' Parameter 3 : (String) "Unlocked"
' Parameter 4 : (Boolean) False
'--------------------------------------------------

boolean37 = settingRepository1.GetAttr("ViewScale")
'--------------------------------------------------
' Parameter 1 : (String) "ViewScale"
' Returned value : (Variant) (Boolean) True
'--------------------------------------------------

Dim bSTR55
bSTR55 = ""
Dim bSTR56
bSTR56 = ""
Dim boolean38
settingRepository1.GetAttrInfo "ViewScale", bSTR55, bSTR56, boolean38
'--------------------------------------------------
' Parameter 1 : (String) "ViewScale"
' Parameter 2 : (String) "Default value"
' Parameter 3 : (String) "Unlocked"
' Parameter 4 : (Boolean) False
'--------------------------------------------------

Dim arrayOfVariantOfLong1
arrayOfVariantOfLong1 = settingRepository1.GetAttrArray("BackgroundColor")
'--------------------------------------------------
' Parameter 1 : (String) "BackgroundColor"
' Returned value : (Array) 
'    Array[0] : (Variant) (Long) 255
'    Array[1] : (Variant) (Long) 255
'    Array[2] : (Variant) (Long) 255
'--------------------------------------------------

Dim bSTR57
bSTR57 = ""
Dim bSTR58
bSTR58 = ""
Dim boolean39
settingRepository1.GetAttrInfo "BackgroundColor", bSTR57, bSTR58, boolean39
'--------------------------------------------------
' Parameter 1 : (String) "BackgroundColor"
' Parameter 2 : (String) "Default value"
' Parameter 3 : (String) "Unlocked"
' Parameter 4 : (Boolean) False
'--------------------------------------------------

boolean40 = settingRepository1.GetAttr("GraduatedColor")
'--------------------------------------------------
' Parameter 1 : (String) "GraduatedColor"
' Returned value : (Variant) (Boolean) False
'--------------------------------------------------

Dim bSTR59
bSTR59 = ""
Dim bSTR60
bSTR60 = ""
Dim boolean41
settingRepository1.GetAttrInfo "GraduatedColor", bSTR59, bSTR60, boolean41
'--------------------------------------------------
' Parameter 1 : (String) "GraduatedColor"
' Parameter 2 : (String) "Default value"
' Parameter 3 : (String) "Unlocked"
' Parameter 4 : (Boolean) False
'--------------------------------------------------

Dim arrayOfVariantOfLong2
arrayOfVariantOfLong2 = settingRepository1.GetAttrArray("BackgroundColorDitto")
'--------------------------------------------------
' Parameter 1 : (String) "BackgroundColorDitto"
' Returned value : (Array) 
'    Array[0] : (Variant) (Long) 255
'    Array[1] : (Variant) (Long) 255
'    Array[2] : (Variant) (Long) 255
'--------------------------------------------------

Dim bSTR61
bSTR61 = ""
Dim bSTR62
bSTR62 = ""
Dim boolean42
settingRepository1.GetAttrInfo "BackgroundColorDitto", bSTR61, bSTR62, boolean42
'--------------------------------------------------
' Parameter 1 : (String) "BackgroundColorDitto"
' Parameter 2 : (String) "Default value"
' Parameter 3 : (String) "Unlocked"
' Parameter 4 : (Boolean) False
'--------------------------------------------------

boolean43 = settingRepository1.GetAttr("GraduatedColorDitto")
'--------------------------------------------------
' Parameter 1 : (String) "GraduatedColorDitto"
' Returned value : (Variant) (Boolean) False
'--------------------------------------------------

Dim bSTR63
bSTR63 = ""
Dim bSTR64
bSTR64 = ""
Dim boolean44
settingRepository1.GetAttrInfo "GraduatedColorDitto", bSTR63, bSTR64, boolean44
'--------------------------------------------------
' Parameter 1 : (String) "GraduatedColorDitto"
' Parameter 2 : (String) "Default value"
' Parameter 3 : (String) "Unlocked"
' Parameter 4 : (Boolean) False
'--------------------------------------------------

End Sub
