Language="VBSCRIPT"

Sub CATMain()

Set settingControllers1 = CATIA.SettingControllers

Set settingRepository1 = settingControllers1.Item("WeightSettings")

double1 = settingRepository1.GetAttr("DefaultDensity")
'--------------------------------------------------
' Parameter 1 : (String) "DefaultDensity"
' Returned value : (Variant) (Double) 7770.000000
'--------------------------------------------------

Dim bSTR1
bSTR1 = ""
Dim bSTR2
bSTR2 = ""
Dim boolean1
settingRepository1.GetAttrInfo "DefaultDensity", bSTR1, bSTR2, boolean1
'--------------------------------------------------
' Parameter 1 : (String) "DefaultDensity"
' Parameter 2 : (String) "Default value"
' Parameter 3 : (String) "Unlocked"
' Parameter 4 : (Boolean) False
'--------------------------------------------------

double2 = settingRepository1.GetAttr("ComputedMargin")
'--------------------------------------------------
' Parameter 1 : (String) "ComputedMargin"
' Returned value : (Variant) (Double) 5.000000
'--------------------------------------------------

Dim bSTR3
bSTR3 = ""
Dim bSTR4
bSTR4 = ""
Dim boolean2
settingRepository1.GetAttrInfo "ComputedMargin", bSTR3, bSTR4, boolean2
'--------------------------------------------------
' Parameter 1 : (String) "ComputedMargin"
' Parameter 2 : (String) "Default value"
' Parameter 3 : (String) "Unlocked"
' Parameter 4 : (Boolean) False
'--------------------------------------------------

long1 = settingRepository1.GetAttr("ForceExact")
'--------------------------------------------------
' Parameter 1 : (String) "ForceExact"
' Returned value : (Variant) (Long) 0
'--------------------------------------------------

Dim bSTR5
bSTR5 = ""
Dim bSTR6
bSTR6 = ""
Dim boolean3
settingRepository1.GetAttrInfo "ForceExact", bSTR5, bSTR6, boolean3
'--------------------------------------------------
' Parameter 1 : (String) "ForceExact"
' Parameter 2 : (String) "Default value"
' Parameter 3 : (String) "Unlocked"
' Parameter 4 : (Boolean) False
'--------------------------------------------------

long2 = settingRepository1.GetAttr("OnlyMainBody")
'--------------------------------------------------
' Parameter 1 : (String) "OnlyMainBody"
' Returned value : (Variant) (Long) 0
'--------------------------------------------------

Dim bSTR7
bSTR7 = ""
Dim bSTR8
bSTR8 = ""
Dim boolean4
settingRepository1.GetAttrInfo "OnlyMainBody", bSTR7, bSTR8, boolean4
'--------------------------------------------------
' Parameter 1 : (String) "OnlyMainBody"
' Parameter 2 : (String) "Default value"
' Parameter 3 : (String) "Unlocked"
' Parameter 4 : (Boolean) False
'--------------------------------------------------

End Sub
