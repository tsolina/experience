Language="VBSCRIPT"

Sub CATMain()

Set settingControllers1 = CATIA.SettingControllers

Set settingRepository1 = settingControllers1.Item("CATTPSEditor")

long1 = settingRepository1.GetAttr("ManipTransparencySetting")
'--------------------------------------------------
' Parameter 1 : (String) "ManipTransparencySetting"
' Returned value : (Variant) (Long) 80
'--------------------------------------------------

Dim bSTR1
bSTR1 = ""
Dim bSTR2
bSTR2 = ""
Dim boolean1
settingRepository1.GetAttrInfo "ManipTransparencySetting", bSTR1, bSTR2, boolean1
'--------------------------------------------------
' Parameter 1 : (String) "ManipTransparencySetting"
' Parameter 2 : (String) "Default value"
' Parameter 3 : (String) "Unlocked"
' Parameter 4 : (Boolean) False
'--------------------------------------------------

double1 = settingRepository1.GetAttr("ManipRefSize")
'--------------------------------------------------
' Parameter 1 : (String) "ManipRefSize"
' Returned value : (Variant) (Double) 3.000000
'--------------------------------------------------

Dim bSTR3
bSTR3 = ""
Dim bSTR4
bSTR4 = ""
Dim boolean2
settingRepository1.GetAttrInfo "ManipRefSize", bSTR3, bSTR4, boolean2
'--------------------------------------------------
' Parameter 1 : (String) "ManipRefSize"
' Parameter 2 : (String) "Default value"
' Parameter 3 : (String) "Unlocked"
' Parameter 4 : (Boolean) False
'--------------------------------------------------

boolean3 = settingRepository1.GetAttr("ManipZoom")
'--------------------------------------------------
' Parameter 1 : (String) "ManipZoom"
' Returned value : (Variant) (Boolean) False
'--------------------------------------------------

Dim bSTR5
bSTR5 = ""
Dim bSTR6
bSTR6 = ""
Dim boolean4
settingRepository1.GetAttrInfo "ManipZoom", bSTR5, bSTR6, boolean4
'--------------------------------------------------
' Parameter 1 : (String) "ManipZoom"
' Parameter 2 : (String) "Default value"
' Parameter 3 : (String) "Unlocked"
' Parameter 4 : (Boolean) False
'--------------------------------------------------

boolean5 = settingRepository1.GetAttr("SnapToPaperGridSetting")
'--------------------------------------------------
' Parameter 1 : (String) "SnapToPaperGridSetting"
' Returned value : (Variant) (Boolean) True
'--------------------------------------------------

Dim bSTR7
bSTR7 = ""
Dim bSTR8
bSTR8 = ""
Dim boolean6
settingRepository1.GetAttrInfo "SnapToPaperGridSetting", bSTR7, bSTR8, boolean6
'--------------------------------------------------
' Parameter 1 : (String) "SnapToPaperGridSetting"
' Parameter 2 : (String) "Default value"
' Parameter 3 : (String) "Unlocked"
' Parameter 4 : (Boolean) False
'--------------------------------------------------

boolean7 = settingRepository1.GetAttr("RotSnapAuto")
'--------------------------------------------------
' Parameter 1 : (String) "RotSnapAuto"
' Returned value : (Variant) (Boolean) True
'--------------------------------------------------

Dim bSTR9
bSTR9 = ""
Dim bSTR10
bSTR10 = ""
Dim boolean8
settingRepository1.GetAttrInfo "RotSnapAuto", bSTR9, bSTR10, boolean8
'--------------------------------------------------
' Parameter 1 : (String) "RotSnapAuto"
' Parameter 2 : (String) "Default value"
' Parameter 3 : (String) "Unlocked"
' Parameter 4 : (Boolean) False
'--------------------------------------------------

boolean9 = settingRepository1.GetAttr("SnapOnDirectionSetting")
'--------------------------------------------------
' Parameter 1 : (String) "SnapOnDirectionSetting"
' Returned value : (Variant) (Boolean) True
'--------------------------------------------------

Dim bSTR11
bSTR11 = ""
Dim bSTR12
bSTR12 = ""
Dim boolean10
settingRepository1.GetAttrInfo "SnapOnDirectionSetting", bSTR11, bSTR12, boolean10
'--------------------------------------------------
' Parameter 1 : (String) "SnapOnDirectionSetting"
' Parameter 2 : (String) "Default value"
' Parameter 3 : (String) "Unlocked"
' Parameter 4 : (Boolean) False
'--------------------------------------------------

boolean11 = settingRepository1.GetAttr("MoveLeaderFreelySetting")
'--------------------------------------------------
' Parameter 1 : (String) "MoveLeaderFreelySetting"
' Returned value : (Variant) (Boolean) False
'--------------------------------------------------

Dim bSTR13
bSTR13 = ""
Dim bSTR14
bSTR14 = ""
Dim boolean12
settingRepository1.GetAttrInfo "MoveLeaderFreelySetting", bSTR13, bSTR14, boolean12
'--------------------------------------------------
' Parameter 1 : (String) "MoveLeaderFreelySetting"
' Parameter 2 : (String) "Default value"
' Parameter 3 : (String) "Unlocked"
' Parameter 4 : (Boolean) False
'--------------------------------------------------

double2 = settingRepository1.GetAttr("PaperGridSpacingSetting")
'--------------------------------------------------
' Parameter 1 : (String) "PaperGridSpacingSetting"
' Returned value : (Variant) (Double) 1.000000
'--------------------------------------------------

Dim bSTR15
bSTR15 = ""
Dim bSTR16
bSTR16 = ""
Dim boolean13
settingRepository1.GetAttrInfo "PaperGridSpacingSetting", bSTR15, bSTR16, boolean13
'--------------------------------------------------
' Parameter 1 : (String) "PaperGridSpacingSetting"
' Parameter 2 : (String) "Default value"
' Parameter 3 : (String) "Unlocked"
' Parameter 4 : (Boolean) False
'--------------------------------------------------

double3 = settingRepository1.GetAttr("RotSnapAngle")
'--------------------------------------------------
' Parameter 1 : (String) "RotSnapAngle"
' Returned value : (Variant) (Double) 90.000000
'--------------------------------------------------

Dim bSTR17
bSTR17 = ""
Dim bSTR18
bSTR18 = ""
Dim boolean14
settingRepository1.GetAttrInfo "RotSnapAngle", bSTR17, bSTR18, boolean14
'--------------------------------------------------
' Parameter 1 : (String) "RotSnapAngle"
' Parameter 2 : (String) "Default value"
' Parameter 3 : (String) "Unlocked"
' Parameter 4 : (Boolean) False
'--------------------------------------------------

boolean15 = settingRepository1.GetAttr("ManipRotateAnnotCre")
'--------------------------------------------------
' Parameter 1 : (String) "ManipRotateAnnotCre"
' Returned value : (Variant) (Boolean) True
'--------------------------------------------------

Dim bSTR19
bSTR19 = ""
Dim bSTR20
bSTR20 = ""
Dim boolean16
settingRepository1.GetAttrInfo "ManipRotateAnnotCre", bSTR19, bSTR20, boolean16
'--------------------------------------------------
' Parameter 1 : (String) "ManipRotateAnnotCre"
' Parameter 2 : (String) "Default value"
' Parameter 3 : (String) "Unlocked"
' Parameter 4 : (Boolean) False
'--------------------------------------------------

boolean17 = settingRepository1.GetAttr("ManipRotateAnnotMod")
'--------------------------------------------------
' Parameter 1 : (String) "ManipRotateAnnotMod"
' Returned value : (Variant) (Boolean) True
'--------------------------------------------------

Dim bSTR21
bSTR21 = ""
Dim bSTR22
bSTR22 = ""
Dim boolean18
settingRepository1.GetAttrInfo "ManipRotateAnnotMod", bSTR21, bSTR22, boolean18
'--------------------------------------------------
' Parameter 1 : (String) "ManipRotateAnnotMod"
' Parameter 2 : (String) "Default value"
' Parameter 3 : (String) "Unlocked"
' Parameter 4 : (Boolean) False
'--------------------------------------------------

boolean19 = settingRepository1.GetAttr("ManipTranslationAnnotCre")
'--------------------------------------------------
' Parameter 1 : (String) "ManipTranslationAnnotCre"
' Returned value : (Variant) (Boolean) True
'--------------------------------------------------

Dim bSTR23
bSTR23 = ""
Dim bSTR24
bSTR24 = ""
Dim boolean20
settingRepository1.GetAttrInfo "ManipTranslationAnnotCre", bSTR23, bSTR24, boolean20
'--------------------------------------------------
' Parameter 1 : (String) "ManipTranslationAnnotCre"
' Parameter 2 : (String) "Default value"
' Parameter 3 : (String) "Unlocked"
' Parameter 4 : (Boolean) False
'--------------------------------------------------

boolean21 = settingRepository1.GetAttr("ManipTranslationAnnotMod")
'--------------------------------------------------
' Parameter 1 : (String) "ManipTranslationAnnotMod"
' Returned value : (Variant) (Boolean) True
'--------------------------------------------------

Dim bSTR25
bSTR25 = ""
Dim bSTR26
bSTR26 = ""
Dim boolean22
settingRepository1.GetAttrInfo "ManipTranslationAnnotMod", bSTR25, bSTR26, boolean22
'--------------------------------------------------
' Parameter 1 : (String) "ManipTranslationAnnotMod"
' Parameter 2 : (String) "Default value"
' Parameter 3 : (String) "Unlocked"
' Parameter 4 : (Boolean) False
'--------------------------------------------------

boolean23 = settingRepository1.GetAttr("ManipResizeAnnotCre")
'--------------------------------------------------
' Parameter 1 : (String) "ManipResizeAnnotCre"
' Returned value : (Variant) (Boolean) True
'--------------------------------------------------

Dim bSTR27
bSTR27 = ""
Dim bSTR28
bSTR28 = ""
Dim boolean24
settingRepository1.GetAttrInfo "ManipResizeAnnotCre", bSTR27, bSTR28, boolean24
'--------------------------------------------------
' Parameter 1 : (String) "ManipResizeAnnotCre"
' Parameter 2 : (String) "Default value"
' Parameter 3 : (String) "Unlocked"
' Parameter 4 : (Boolean) False
'--------------------------------------------------

boolean25 = settingRepository1.GetAttr("ManipResizeAnnotMod")
'--------------------------------------------------
' Parameter 1 : (String) "ManipResizeAnnotMod"
' Returned value : (Variant) (Boolean) True
'--------------------------------------------------

Dim bSTR29
bSTR29 = ""
Dim bSTR30
bSTR30 = ""
Dim boolean26
settingRepository1.GetAttrInfo "ManipResizeAnnotMod", bSTR29, bSTR30, boolean26
'--------------------------------------------------
' Parameter 1 : (String) "ManipResizeAnnotMod"
' Parameter 2 : (String) "Default value"
' Parameter 3 : (String) "Unlocked"
' Parameter 4 : (Boolean) False
'--------------------------------------------------

boolean27 = settingRepository1.GetAttr("ManipMoveValueAnnotCre")
'--------------------------------------------------
' Parameter 1 : (String) "ManipMoveValueAnnotCre"
' Returned value : (Variant) (Boolean) True
'--------------------------------------------------

Dim bSTR31
bSTR31 = ""
Dim bSTR32
bSTR32 = ""
Dim boolean28
settingRepository1.GetAttrInfo "ManipMoveValueAnnotCre", bSTR31, bSTR32, boolean28
'--------------------------------------------------
' Parameter 1 : (String) "ManipMoveValueAnnotCre"
' Parameter 2 : (String) "Default value"
' Parameter 3 : (String) "Unlocked"
' Parameter 4 : (Boolean) False
'--------------------------------------------------

boolean29 = settingRepository1.GetAttr("ManipMoveValueAnnotMod")
'--------------------------------------------------
' Parameter 1 : (String) "ManipMoveValueAnnotMod"
' Returned value : (Variant) (Boolean) False
'--------------------------------------------------

Dim bSTR33
bSTR33 = ""
Dim bSTR34
bSTR34 = ""
Dim boolean30
settingRepository1.GetAttrInfo "ManipMoveValueAnnotMod", bSTR33, bSTR34, boolean30
'--------------------------------------------------
' Parameter 1 : (String) "ManipMoveValueAnnotMod"
' Parameter 2 : (String) "Default value"
' Parameter 3 : (String) "Unlocked"
' Parameter 4 : (Boolean) False
'--------------------------------------------------

boolean31 = settingRepository1.GetAttr("ManipTranslationLeaderCre")
'--------------------------------------------------
' Parameter 1 : (String) "ManipTranslationLeaderCre"
' Returned value : (Variant) (Boolean) True
'--------------------------------------------------

Dim bSTR35
bSTR35 = ""
Dim bSTR36
bSTR36 = ""
Dim boolean32
settingRepository1.GetAttrInfo "ManipTranslationLeaderCre", bSTR35, bSTR36, boolean32
'--------------------------------------------------
' Parameter 1 : (String) "ManipTranslationLeaderCre"
' Parameter 2 : (String) "Default value"
' Parameter 3 : (String) "Unlocked"
' Parameter 4 : (Boolean) False
'--------------------------------------------------

boolean33 = settingRepository1.GetAttr("ManipTranslationLeaderMod")
'--------------------------------------------------
' Parameter 1 : (String) "ManipTranslationLeaderMod"
' Returned value : (Variant) (Boolean) False
'--------------------------------------------------

Dim bSTR37
bSTR37 = ""
Dim bSTR38
bSTR38 = ""
Dim boolean34
settingRepository1.GetAttrInfo "ManipTranslationLeaderMod", bSTR37, bSTR38, boolean34
'--------------------------------------------------
' Parameter 1 : (String) "ManipTranslationLeaderMod"
' Parameter 2 : (String) "Default value"
' Parameter 3 : (String) "Unlocked"
' Parameter 4 : (Boolean) False
'--------------------------------------------------

boolean35 = settingRepository1.GetAttr("ManipMoveLeaderAnchorCre")
'--------------------------------------------------
' Parameter 1 : (String) "ManipMoveLeaderAnchorCre"
' Returned value : (Variant) (Boolean) True
'--------------------------------------------------

Dim bSTR39
bSTR39 = ""
Dim bSTR40
bSTR40 = ""
Dim boolean36
settingRepository1.GetAttrInfo "ManipMoveLeaderAnchorCre", bSTR39, bSTR40, boolean36
'--------------------------------------------------
' Parameter 1 : (String) "ManipMoveLeaderAnchorCre"
' Parameter 2 : (String) "Default value"
' Parameter 3 : (String) "Unlocked"
' Parameter 4 : (Boolean) False
'--------------------------------------------------

boolean37 = settingRepository1.GetAttr("ManipMoveLeaderAnchorMod")
'--------------------------------------------------
' Parameter 1 : (String) "ManipMoveLeaderAnchorMod"
' Returned value : (Variant) (Boolean) False
'--------------------------------------------------

Dim bSTR41
bSTR41 = ""
Dim bSTR42
bSTR42 = ""
Dim boolean38
settingRepository1.GetAttrInfo "ManipMoveLeaderAnchorMod", bSTR41, bSTR42, boolean38
'--------------------------------------------------
' Parameter 1 : (String) "ManipMoveLeaderAnchorMod"
' Parameter 2 : (String) "Default value"
' Parameter 3 : (String) "Unlocked"
' Parameter 4 : (Boolean) False
'--------------------------------------------------

boolean39 = settingRepository1.GetAttr("ManipMoveLeaderCre")
'--------------------------------------------------
' Parameter 1 : (String) "ManipMoveLeaderCre"
' Returned value : (Variant) (Boolean) True
'--------------------------------------------------

Dim bSTR43
bSTR43 = ""
Dim bSTR44
bSTR44 = ""
Dim boolean40
settingRepository1.GetAttrInfo "ManipMoveLeaderCre", bSTR43, bSTR44, boolean40
'--------------------------------------------------
' Parameter 1 : (String) "ManipMoveLeaderCre"
' Parameter 2 : (String) "Default value"
' Parameter 3 : (String) "Unlocked"
' Parameter 4 : (Boolean) False
'--------------------------------------------------

boolean41 = settingRepository1.GetAttr("ManipMoveLeaderMod")
'--------------------------------------------------
' Parameter 1 : (String) "ManipMoveLeaderMod"
' Returned value : (Variant) (Boolean) False
'--------------------------------------------------

Dim bSTR45
bSTR45 = ""
Dim bSTR46
bSTR46 = ""
Dim boolean42
settingRepository1.GetAttrInfo "ManipMoveLeaderMod", bSTR45, bSTR46, boolean42
'--------------------------------------------------
' Parameter 1 : (String) "ManipMoveLeaderMod"
' Parameter 2 : (String) "Default value"
' Parameter 3 : (String) "Unlocked"
' Parameter 4 : (Boolean) False
'--------------------------------------------------

End Sub
