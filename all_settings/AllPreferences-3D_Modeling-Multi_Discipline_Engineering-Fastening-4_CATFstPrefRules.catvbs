Language="VBSCRIPT"

Sub CATMain()

Set settingControllers1 = CATIA.SettingControllers

Set settingRepository1 = settingControllers1.Item("FstRules")

boolean1 = settingRepository1.GetAttr("FstFBECompass")
'--------------------------------------------------
' Parameter 1 : (String) "FstFBECompass"
' Returned value : (Variant) (Boolean) False
'--------------------------------------------------

Dim bSTR1
bSTR1 = ""
Dim bSTR2
bSTR2 = ""
Dim boolean2
settingRepository1.GetAttrInfo "FstFBECompass", bSTR1, bSTR2, boolean2
'--------------------------------------------------
' Parameter 1 : (String) "FstFBECompass"
' Parameter 2 : (String) "Default value"
' Parameter 3 : (String) "Unlocked"
' Parameter 4 : (Boolean) False
'--------------------------------------------------

bSTR3 = settingRepository1.GetAttr("FstFBECompassCriticality")
'--------------------------------------------------
' Parameter 1 : (String) "FstFBECompassCriticality"
' Returned value : (Variant) (String) "Medium"
'--------------------------------------------------

Dim bSTR4
bSTR4 = ""
Dim bSTR5
bSTR5 = ""
Dim boolean3
settingRepository1.GetAttrInfo "FstFBECompassCriticality", bSTR4, bSTR5, boolean3
'--------------------------------------------------
' Parameter 1 : (String) "FstFBECompassCriticality"
' Parameter 2 : (String) "Default value"
' Parameter 3 : (String) "Unlocked"
' Parameter 4 : (Boolean) False
'--------------------------------------------------

boolean4 = settingRepository1.GetAttr("FstFCECompass")
'--------------------------------------------------
' Parameter 1 : (String) "FstFCECompass"
' Returned value : (Variant) (Boolean) False
'--------------------------------------------------

Dim bSTR6
bSTR6 = ""
Dim bSTR7
bSTR7 = ""
Dim boolean5
settingRepository1.GetAttrInfo "FstFCECompass", bSTR6, bSTR7, boolean5
'--------------------------------------------------
' Parameter 1 : (String) "FstFCECompass"
' Parameter 2 : (String) "Default value"
' Parameter 3 : (String) "Unlocked"
' Parameter 4 : (Boolean) False
'--------------------------------------------------

bSTR8 = settingRepository1.GetAttr("FstFCECompassCriticality")
'--------------------------------------------------
' Parameter 1 : (String) "FstFCECompassCriticality"
' Returned value : (Variant) (String) "Medium"
'--------------------------------------------------

Dim bSTR9
bSTR9 = ""
Dim bSTR10
bSTR10 = ""
Dim boolean6
settingRepository1.GetAttrInfo "FstFCECompassCriticality", bSTR9, bSTR10, boolean6
'--------------------------------------------------
' Parameter 1 : (String) "FstFCECompassCriticality"
' Parameter 2 : (String) "Default value"
' Parameter 3 : (String) "Unlocked"
' Parameter 4 : (Boolean) False
'--------------------------------------------------

boolean7 = settingRepository1.GetAttr("FstFCLSCompass")
'--------------------------------------------------
' Parameter 1 : (String) "FstFCLSCompass"
' Returned value : (Variant) (Boolean) False
'--------------------------------------------------

Dim bSTR11
bSTR11 = ""
Dim bSTR12
bSTR12 = ""
Dim boolean8
settingRepository1.GetAttrInfo "FstFCLSCompass", bSTR11, bSTR12, boolean8
'--------------------------------------------------
' Parameter 1 : (String) "FstFCLSCompass"
' Parameter 2 : (String) "Default value"
' Parameter 3 : (String) "Unlocked"
' Parameter 4 : (Boolean) False
'--------------------------------------------------

bSTR13 = settingRepository1.GetAttr("FstFCLSCompassCriticality")
'--------------------------------------------------
' Parameter 1 : (String) "FstFCLSCompassCriticality"
' Returned value : (Variant) (String) "High"
'--------------------------------------------------

Dim bSTR14
bSTR14 = ""
Dim bSTR15
bSTR15 = ""
Dim boolean9
settingRepository1.GetAttrInfo "FstFCLSCompassCriticality", bSTR14, bSTR15, boolean9
'--------------------------------------------------
' Parameter 1 : (String) "FstFCLSCompassCriticality"
' Parameter 2 : (String) "Default value"
' Parameter 3 : (String) "Unlocked"
' Parameter 4 : (Boolean) False
'--------------------------------------------------

boolean10 = settingRepository1.GetAttr("FstFFLCCompass")
'--------------------------------------------------
' Parameter 1 : (String) "FstFFLCCompass"
' Returned value : (Variant) (Boolean) False
'--------------------------------------------------

Dim bSTR16
bSTR16 = ""
Dim bSTR17
bSTR17 = ""
Dim boolean11
settingRepository1.GetAttrInfo "FstFFLCCompass", bSTR16, bSTR17, boolean11
'--------------------------------------------------
' Parameter 1 : (String) "FstFFLCCompass"
' Parameter 2 : (String) "Default value"
' Parameter 3 : (String) "Unlocked"
' Parameter 4 : (Boolean) False
'--------------------------------------------------

bSTR18 = settingRepository1.GetAttr("FstFFLCCompassCriticality")
'--------------------------------------------------
' Parameter 1 : (String) "FstFFLCCompassCriticality"
' Returned value : (Variant) (String) "High"
'--------------------------------------------------

Dim bSTR19
bSTR19 = ""
Dim bSTR20
bSTR20 = ""
Dim boolean12
settingRepository1.GetAttrInfo "FstFFLCCompassCriticality", bSTR19, bSTR20, boolean12
'--------------------------------------------------
' Parameter 1 : (String) "FstFFLCCompassCriticality"
' Parameter 2 : (String) "Default value"
' Parameter 3 : (String) "Unlocked"
' Parameter 4 : (Boolean) False
'--------------------------------------------------

boolean13 = settingRepository1.GetAttr("FstFPCNCompass")
'--------------------------------------------------
' Parameter 1 : (String) "FstFPCNCompass"
' Returned value : (Variant) (Boolean) False
'--------------------------------------------------

Dim bSTR21
bSTR21 = ""
Dim bSTR22
bSTR22 = ""
Dim boolean14
settingRepository1.GetAttrInfo "FstFPCNCompass", bSTR21, bSTR22, boolean14
'--------------------------------------------------
' Parameter 1 : (String) "FstFPCNCompass"
' Parameter 2 : (String) "Default value"
' Parameter 3 : (String) "Unlocked"
' Parameter 4 : (Boolean) False
'--------------------------------------------------

bSTR23 = settingRepository1.GetAttr("FstFPCNCompassCriticality")
'--------------------------------------------------
' Parameter 1 : (String) "FstFPCNCompassCriticality"
' Returned value : (Variant) (String) "Medium"
'--------------------------------------------------

Dim bSTR24
bSTR24 = ""
Dim bSTR25
bSTR25 = ""
Dim boolean15
settingRepository1.GetAttrInfo "FstFPCNCompassCriticality", bSTR24, bSTR25, boolean15
'--------------------------------------------------
' Parameter 1 : (String) "FstFPCNCompassCriticality"
' Parameter 2 : (String) "Default value"
' Parameter 3 : (String) "Unlocked"
' Parameter 4 : (Boolean) False
'--------------------------------------------------

boolean16 = settingRepository1.GetAttr("FstMSPCompass")
'--------------------------------------------------
' Parameter 1 : (String) "FstMSPCompass"
' Returned value : (Variant) (Boolean) False
'--------------------------------------------------

Dim bSTR26
bSTR26 = ""
Dim bSTR27
bSTR27 = ""
Dim boolean17
settingRepository1.GetAttrInfo "FstMSPCompass", bSTR26, bSTR27, boolean17
'--------------------------------------------------
' Parameter 1 : (String) "FstMSPCompass"
' Parameter 2 : (String) "Default value"
' Parameter 3 : (String) "Unlocked"
' Parameter 4 : (Boolean) False
'--------------------------------------------------

bSTR28 = settingRepository1.GetAttr("FstMSPCompassCriticality")
'--------------------------------------------------
' Parameter 1 : (String) "FstMSPCompassCriticality"
' Returned value : (Variant) (String) "Low"
'--------------------------------------------------

Dim bSTR29
bSTR29 = ""
Dim bSTR30
bSTR30 = ""
Dim boolean18
settingRepository1.GetAttrInfo "FstMSPCompassCriticality", bSTR29, bSTR30, boolean18
'--------------------------------------------------
' Parameter 1 : (String) "FstMSPCompassCriticality"
' Parameter 2 : (String) "Default value"
' Parameter 3 : (String) "Unlocked"
' Parameter 4 : (Boolean) False
'--------------------------------------------------

boolean19 = settingRepository1.GetAttr("FstNCPPCompass")
'--------------------------------------------------
' Parameter 1 : (String) "FstNCPPCompass"
' Returned value : (Variant) (Boolean) False
'--------------------------------------------------

Dim bSTR31
bSTR31 = ""
Dim bSTR32
bSTR32 = ""
Dim boolean20
settingRepository1.GetAttrInfo "FstNCPPCompass", bSTR31, bSTR32, boolean20
'--------------------------------------------------
' Parameter 1 : (String) "FstNCPPCompass"
' Parameter 2 : (String) "Default value"
' Parameter 3 : (String) "Unlocked"
' Parameter 4 : (Boolean) False
'--------------------------------------------------

bSTR33 = settingRepository1.GetAttr("FstNCPPCompassCriticality")
'--------------------------------------------------
' Parameter 1 : (String) "FstNCPPCompassCriticality"
' Returned value : (Variant) (String) "High"
'--------------------------------------------------

Dim bSTR34
bSTR34 = ""
Dim bSTR35
bSTR35 = ""
Dim boolean21
settingRepository1.GetAttrInfo "FstNCPPCompassCriticality", bSTR34, bSTR35, boolean21
'--------------------------------------------------
' Parameter 1 : (String) "FstNCPPCompassCriticality"
' Parameter 2 : (String) "Default value"
' Parameter 3 : (String) "Unlocked"
' Parameter 4 : (Boolean) False
'--------------------------------------------------

boolean22 = settingRepository1.GetAttr("FstSTKCompass")
'--------------------------------------------------
' Parameter 1 : (String) "FstSTKCompass"
' Returned value : (Variant) (Boolean) False
'--------------------------------------------------

Dim bSTR36
bSTR36 = ""
Dim bSTR37
bSTR37 = ""
Dim boolean23
settingRepository1.GetAttrInfo "FstSTKCompass", bSTR36, bSTR37, boolean23
'--------------------------------------------------
' Parameter 1 : (String) "FstSTKCompass"
' Parameter 2 : (String) "Default value"
' Parameter 3 : (String) "Unlocked"
' Parameter 4 : (Boolean) False
'--------------------------------------------------

bSTR38 = settingRepository1.GetAttr("FstSTKCompassCriticality")
'--------------------------------------------------
' Parameter 1 : (String) "FstSTKCompassCriticality"
' Returned value : (Variant) (String) "High"
'--------------------------------------------------

Dim bSTR39
bSTR39 = ""
Dim bSTR40
bSTR40 = ""
Dim boolean24
settingRepository1.GetAttrInfo "FstSTKCompassCriticality", bSTR39, bSTR40, boolean24
'--------------------------------------------------
' Parameter 1 : (String) "FstSTKCompassCriticality"
' Parameter 2 : (String) "Default value"
' Parameter 3 : (String) "Unlocked"
' Parameter 4 : (Boolean) False
'--------------------------------------------------

long1 = settingRepository1.GetAttr("FstSTKSuppositionMode")
'--------------------------------------------------
' Parameter 1 : (String) "FstSTKSuppositionMode"
' Returned value : (Variant) (Long) 1
'--------------------------------------------------

Dim bSTR41
bSTR41 = ""
Dim bSTR42
bSTR42 = ""
Dim boolean25
settingRepository1.GetAttrInfo "FstSTKSuppositionMode", bSTR41, bSTR42, boolean25
'--------------------------------------------------
' Parameter 1 : (String) "FstSTKSuppositionMode"
' Parameter 2 : (String) "Default value"
' Parameter 3 : (String) "Unlocked"
' Parameter 4 : (Boolean) False
'--------------------------------------------------

End Sub
