Language="VBSCRIPT"

Sub CATMain()

Set settingControllers1 = CATIA.SettingControllers

Set settingRepository1 = settingControllers1.Item("Tree")

boolean1 = settingRepository1.GetAttr("AutoScroll")
'--------------------------------------------------
' Parameter 1 : (String) "AutoScroll"
' Returned value : (Variant) (Boolean) True
'--------------------------------------------------

Dim bSTR1
bSTR1 = ""
Dim bSTR2
bSTR2 = ""
Dim boolean2
settingRepository1.GetAttrInfo "AutoScroll", bSTR1, bSTR2, boolean2
'--------------------------------------------------
' Parameter 1 : (String) "AutoScroll"
' Parameter 2 : (String) "Default value"
' Parameter 3 : (String) "Unlocked"
' Parameter 4 : (Boolean) False
'--------------------------------------------------

boolean3 = settingRepository1.GetAttr("DisplayGeometry")
'--------------------------------------------------
' Parameter 1 : (String) "DisplayGeometry"
' Returned value : (Variant) (Boolean) True
'--------------------------------------------------

Dim bSTR3
bSTR3 = ""
Dim bSTR4
bSTR4 = ""
Dim boolean4
settingRepository1.GetAttrInfo "DisplayGeometry", bSTR3, bSTR4, boolean4
'--------------------------------------------------
' Parameter 1 : (String) "DisplayGeometry"
' Parameter 2 : (String) "Default value"
' Parameter 3 : (String) "Unlocked"
' Parameter 4 : (Boolean) False
'--------------------------------------------------

boolean5 = settingRepository1.GetAttr("AutoExpand")
'--------------------------------------------------
' Parameter 1 : (String) "AutoExpand"
' Returned value : (Variant) (Boolean) False
'--------------------------------------------------

Dim bSTR5
bSTR5 = ""
Dim bSTR6
bSTR6 = ""
Dim boolean6
settingRepository1.GetAttrInfo "AutoExpand", bSTR5, bSTR6, boolean6
'--------------------------------------------------
' Parameter 1 : (String) "AutoExpand"
' Parameter 2 : (String) "Default value"
' Parameter 3 : (String) "Unlocked"
' Parameter 4 : (Boolean) False
'--------------------------------------------------

boolean7 = settingRepository1.GetAttr("ArcSelection")
'--------------------------------------------------
' Parameter 1 : (String) "ArcSelection"
' Returned value : (Variant) (Boolean) True
'--------------------------------------------------

Dim bSTR7
bSTR7 = ""
Dim bSTR8
bSTR8 = ""
Dim boolean8
settingRepository1.GetAttrInfo "ArcSelection", bSTR7, bSTR8, boolean8
'--------------------------------------------------
' Parameter 1 : (String) "ArcSelection"
' Parameter 2 : (String) "Default value"
' Parameter 3 : (String) "Unlocked"
' Parameter 4 : (Boolean) False
'--------------------------------------------------

End Sub
