Language="VBSCRIPT"

Sub CATMain()

Set settingControllers1 = CATIA.SettingControllers

Set settingRepository1 = settingControllers1.Item("WidgetLayoutRepository")

long1 = settingRepository1.GetAttr("OpenInNewTP")
'--------------------------------------------------
' Parameter 1 : (String) "OpenInNewTP"
' Returned value : (Variant) (Long) 1
'--------------------------------------------------

Dim bSTR1
bSTR1 = ""
Dim bSTR2
bSTR2 = ""
Dim boolean1
settingRepository1.GetAttrInfo "OpenInNewTP", bSTR1, bSTR2, boolean1
'--------------------------------------------------
' Parameter 1 : (String) "OpenInNewTP"
' Parameter 2 : (String) "Default value"
' Parameter 3 : (String) "Unlocked"
' Parameter 4 : (Boolean) False
'--------------------------------------------------

long2 = settingRepository1.GetAttr("CreateInMaxState")
'--------------------------------------------------
' Parameter 1 : (String) "CreateInMaxState"
' Returned value : (Variant) (Long) 1
'--------------------------------------------------

Dim bSTR3
bSTR3 = ""
Dim bSTR4
bSTR4 = ""
Dim boolean2
settingRepository1.GetAttrInfo "CreateInMaxState", bSTR3, bSTR4, boolean2
'--------------------------------------------------
' Parameter 1 : (String) "CreateInMaxState"
' Parameter 2 : (String) "Default value"
' Parameter 3 : (String) "Unlocked"
' Parameter 4 : (Boolean) False
'--------------------------------------------------

long3 = settingRepository1.GetAttr("ExtractedAB")
'--------------------------------------------------
' Parameter 1 : (String) "ExtractedAB"
' Returned value : (Variant) (Long) 0
'--------------------------------------------------

Dim bSTR5
bSTR5 = ""
Dim bSTR6
bSTR6 = ""
Dim boolean3
settingRepository1.GetAttrInfo "ExtractedAB", bSTR5, bSTR6, boolean3
'--------------------------------------------------
' Parameter 1 : (String) "ExtractedAB"
' Parameter 2 : (String) "Default value"
' Parameter 3 : (String) "Unlocked"
' Parameter 4 : (Boolean) False
'--------------------------------------------------

End Sub
