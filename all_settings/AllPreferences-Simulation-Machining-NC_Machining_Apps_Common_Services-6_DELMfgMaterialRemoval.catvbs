Language="VBSCRIPT"

Sub CATMain()

Set settingControllers1 = CATIA.SettingControllers

Set settingRepository1 = settingControllers1.Item("NCMfgSimulation")

boolean1 = settingRepository1.GetAttr("TouchIsCollision")
'--------------------------------------------------
' Parameter 1 : (String) "TouchIsCollision"
' Returned value : (Variant) (Boolean) True
'--------------------------------------------------

Dim bSTR1
bSTR1 = ""
Dim bSTR2
bSTR2 = ""
Dim boolean2
settingRepository1.GetAttrInfo "TouchIsCollision", bSTR1, bSTR2, boolean2
'--------------------------------------------------
' Parameter 1 : (String) "TouchIsCollision"
' Parameter 2 : (String) "Default value"
' Parameter 3 : (String) "Unlocked"
' Parameter 4 : (Boolean) False
'--------------------------------------------------

boolean3 = settingRepository1.GetAttr("CollisionDetectionLimitEnable")
'--------------------------------------------------
' Parameter 1 : (String) "CollisionDetectionLimitEnable"
' Returned value : (Variant) (Boolean) False
'--------------------------------------------------

Dim bSTR3
bSTR3 = ""
Dim bSTR4
bSTR4 = ""
Dim boolean4
settingRepository1.GetAttrInfo "CollisionDetectionLimitEnable", bSTR3, bSTR4, boolean4
'--------------------------------------------------
' Parameter 1 : (String) "CollisionDetectionLimitEnable"
' Parameter 2 : (String) "Default value"
' Parameter 3 : (String) "Unlocked"
' Parameter 4 : (Boolean) False
'--------------------------------------------------

long1 = settingRepository1.GetAttr("CollisionDetectionLimitValue")
'--------------------------------------------------
' Parameter 1 : (String) "CollisionDetectionLimitValue"
' Returned value : (Variant) (Long) 100
'--------------------------------------------------

Dim bSTR5
bSTR5 = ""
Dim bSTR6
bSTR6 = ""
Dim boolean5
settingRepository1.GetAttrInfo "CollisionDetectionLimitValue", bSTR5, bSTR6, boolean5
'--------------------------------------------------
' Parameter 1 : (String) "CollisionDetectionLimitValue"
' Parameter 2 : (String) "Default value"
' Parameter 3 : (String) "Unlocked"
' Parameter 4 : (Boolean) False
'--------------------------------------------------

long2 = settingRepository1.GetAttr("MillingAccuracyType")
'--------------------------------------------------
' Parameter 1 : (String) "MillingAccuracyType"
' Returned value : (Variant) (Long) 0
'--------------------------------------------------

Dim bSTR7
bSTR7 = ""
Dim bSTR8
bSTR8 = ""
Dim boolean6
settingRepository1.GetAttrInfo "MillingAccuracyType", bSTR7, bSTR8, boolean6
'--------------------------------------------------
' Parameter 1 : (String) "MillingAccuracyType"
' Parameter 2 : (String) "Default value"
' Parameter 3 : (String) "Unlocked"
' Parameter 4 : (Boolean) False
'--------------------------------------------------

float1 = settingRepository1.GetAttr("ManualMillingAccuVal")
'--------------------------------------------------
' Parameter 1 : (String) "ManualMillingAccuVal"
' Returned value : (Variant) (Float) 0.000050
'--------------------------------------------------

Dim bSTR9
bSTR9 = ""
Dim bSTR10
bSTR10 = ""
Dim boolean7
settingRepository1.GetAttrInfo "ManualMillingAccuVal", bSTR9, bSTR10, boolean7
'--------------------------------------------------
' Parameter 1 : (String) "ManualMillingAccuVal"
' Parameter 2 : (String) "Default value"
' Parameter 3 : (String) "Unlocked"
' Parameter 4 : (Boolean) False
'--------------------------------------------------

long3 = settingRepository1.GetAttr("LatheAccuracyFacets")
'--------------------------------------------------
' Parameter 1 : (String) "LatheAccuracyFacets"
' Returned value : (Variant) (Long) 48
'--------------------------------------------------

Dim bSTR11
bSTR11 = ""
Dim bSTR12
bSTR12 = ""
Dim boolean8
settingRepository1.GetAttrInfo "LatheAccuracyFacets", bSTR11, bSTR12, boolean8
'--------------------------------------------------
' Parameter 1 : (String) "LatheAccuracyFacets"
' Parameter 2 : (String) "Default value"
' Parameter 3 : (String) "Unlocked"
' Parameter 4 : (Boolean) False
'--------------------------------------------------

float2 = settingRepository1.GetAttr("InterpolAngle")
'--------------------------------------------------
' Parameter 1 : (String) "InterpolAngle"
' Returned value : (Variant) (Float) 1.000000
'--------------------------------------------------

Dim bSTR13
bSTR13 = ""
Dim bSTR14
bSTR14 = ""
Dim boolean9
settingRepository1.GetAttrInfo "InterpolAngle", bSTR13, bSTR14, boolean9
'--------------------------------------------------
' Parameter 1 : (String) "InterpolAngle"
' Parameter 2 : (String) "Default value"
' Parameter 3 : (String) "Unlocked"
' Parameter 4 : (Boolean) False
'--------------------------------------------------

long4 = settingRepository1.GetAttr("DisconnectToolCoreDiameter")
'--------------------------------------------------
' Parameter 1 : (String) "DisconnectToolCoreDiameter"
' Returned value : (Variant) (Long) 0
'--------------------------------------------------

Dim bSTR15
bSTR15 = ""
Dim bSTR16
bSTR16 = ""
Dim boolean10
settingRepository1.GetAttrInfo "DisconnectToolCoreDiameter", bSTR15, bSTR16, boolean10
'--------------------------------------------------
' Parameter 1 : (String) "DisconnectToolCoreDiameter"
' Parameter 2 : (String) "Default value"
' Parameter 3 : (String) "Unlocked"
' Parameter 4 : (Boolean) False
'--------------------------------------------------

long5 = settingRepository1.GetAttr("ToolorFeedColor")
'--------------------------------------------------
' Parameter 1 : (String) "ToolorFeedColor"
' Returned value : (Variant) (Long) 0
'--------------------------------------------------

Dim bSTR17
bSTR17 = ""
Dim bSTR18
bSTR18 = ""
Dim boolean11
settingRepository1.GetAttrInfo "ToolorFeedColor", bSTR17, bSTR18, boolean11
'--------------------------------------------------
' Parameter 1 : (String) "ToolorFeedColor"
' Parameter 2 : (String) "Default value"
' Parameter 3 : (String) "Unlocked"
' Parameter 4 : (Boolean) False
'--------------------------------------------------

Dim arrayOfVariantOfULong1
arrayOfVariantOfULong1 = settingRepository1.GetAttrArray("VideoPartColor")
'--------------------------------------------------
' Parameter 1 : (String) "VideoPartColor"
' Returned value : (Array) 
'    Array[0] : (Variant) (Unsigned Long) 255
'    Array[1] : (Variant) (Unsigned Long) 255
'    Array[2] : (Variant) (Unsigned Long) 255
'--------------------------------------------------

Dim bSTR19
bSTR19 = ""
Dim bSTR20
bSTR20 = ""
Dim boolean12
settingRepository1.GetAttrInfo "VideoPartColor", bSTR19, bSTR20, boolean12
'--------------------------------------------------
' Parameter 1 : (String) "VideoPartColor"
' Parameter 2 : (String) "Default value"
' Parameter 3 : (String) "Unlocked"
' Parameter 4 : (Boolean) False
'--------------------------------------------------

float3 = settingRepository1.GetAttr("TransitionMaxAngle")
'--------------------------------------------------
' Parameter 1 : (String) "TransitionMaxAngle"
' Returned value : (Variant) (Float) 1.000000
'--------------------------------------------------

Dim bSTR21
bSTR21 = ""
Dim bSTR22
bSTR22 = ""
Dim boolean13
settingRepository1.GetAttrInfo "TransitionMaxAngle", bSTR21, bSTR22, boolean13
'--------------------------------------------------
' Parameter 1 : (String) "TransitionMaxAngle"
' Parameter 2 : (String) "Default value"
' Parameter 3 : (String) "Unlocked"
' Parameter 4 : (Boolean) False
'--------------------------------------------------

long6 = settingRepository1.GetAttr("FacetType")
'--------------------------------------------------
' Parameter 1 : (String) "FacetType"
' Returned value : (Variant) (Long) 2
'--------------------------------------------------

Dim bSTR23
bSTR23 = ""
Dim bSTR24
bSTR24 = ""
Dim boolean14
settingRepository1.GetAttrInfo "FacetType", bSTR23, bSTR24, boolean14
'--------------------------------------------------
' Parameter 1 : (String) "FacetType"
' Parameter 2 : (String) "Default value"
' Parameter 3 : (String) "Unlocked"
' Parameter 4 : (Boolean) False
'--------------------------------------------------

long7 = settingRepository1.GetAttr("ToolColor")
'--------------------------------------------------
' Parameter 1 : (String) "ToolColor"
' Returned value : (Variant) (Long) 2
'--------------------------------------------------

Dim bSTR25
bSTR25 = ""
Dim bSTR26
bSTR26 = ""
Dim boolean15
settingRepository1.GetAttrInfo "ToolColor", bSTR25, bSTR26, boolean15
'--------------------------------------------------
' Parameter 1 : (String) "ToolColor"
' Parameter 2 : (String) "Default value"
' Parameter 3 : (String) "Unlocked"
' Parameter 4 : (Boolean) False
'--------------------------------------------------

uLong1 = settingRepository1.GetAttr("ToolNumber")
'--------------------------------------------------
' Parameter 1 : (String) "ToolNumber"
' Returned value : (Variant) (Unsigned Long) 1
'--------------------------------------------------

Dim bSTR27
bSTR27 = ""
Dim bSTR28
bSTR28 = ""
Dim boolean16
settingRepository1.GetAttrInfo "ToolNumber", bSTR27, bSTR28, boolean16
'--------------------------------------------------
' Parameter 1 : (String) "ToolNumber"
' Parameter 2 : (String) "Default value"
' Parameter 3 : (String) "Unlocked"
' Parameter 4 : (Boolean) False
'--------------------------------------------------

Dim arrayOfVariantOfULong2
arrayOfVariantOfULong2 = settingRepository1.GetAttrArray("ToolColorValue1")
'--------------------------------------------------
' Parameter 1 : (String) "ToolColorValue1"
' Returned value : (Array) 
'    Array[0] : (Variant) (Unsigned Long) 29
'    Array[1] : (Variant) (Unsigned Long) 209
'    Array[2] : (Variant) (Unsigned Long) 29
'--------------------------------------------------

Dim bSTR29
bSTR29 = ""
Dim bSTR30
bSTR30 = ""
Dim boolean17
settingRepository1.GetAttrInfo "ToolColorValue1", bSTR29, bSTR30, boolean17
'--------------------------------------------------
' Parameter 1 : (String) "ToolColorValue1"
' Parameter 2 : (String) "Default value"
' Parameter 3 : (String) "Unlocked"
' Parameter 4 : (Boolean) False
'--------------------------------------------------

Dim arrayOfVariantOfULong3
arrayOfVariantOfULong3 = settingRepository1.GetAttrArray("ToolColorValue2")
'--------------------------------------------------
' Parameter 1 : (String) "ToolColorValue2"
' Returned value : (Array) 
'    Array[0] : (Variant) (Unsigned Long) 0
'    Array[1] : (Variant) (Unsigned Long) 108
'    Array[2] : (Variant) (Unsigned Long) 209
'--------------------------------------------------

Dim bSTR31
bSTR31 = ""
Dim bSTR32
bSTR32 = ""
Dim boolean18
settingRepository1.GetAttrInfo "ToolColorValue2", bSTR31, bSTR32, boolean18
'--------------------------------------------------
' Parameter 1 : (String) "ToolColorValue2"
' Parameter 2 : (String) "Default value"
' Parameter 3 : (String) "Unlocked"
' Parameter 4 : (Boolean) False
'--------------------------------------------------

Dim arrayOfVariantOfULong4
arrayOfVariantOfULong4 = settingRepository1.GetAttrArray("ToolColorValue3")
'--------------------------------------------------
' Parameter 1 : (String) "ToolColorValue3"
' Returned value : (Array) 
'    Array[0] : (Variant) (Unsigned Long) 210
'    Array[1] : (Variant) (Unsigned Long) 210
'    Array[2] : (Variant) (Unsigned Long) 0
'--------------------------------------------------

Dim bSTR33
bSTR33 = ""
Dim bSTR34
bSTR34 = ""
Dim boolean19
settingRepository1.GetAttrInfo "ToolColorValue3", bSTR33, bSTR34, boolean19
'--------------------------------------------------
' Parameter 1 : (String) "ToolColorValue3"
' Parameter 2 : (String) "Default value"
' Parameter 3 : (String) "Unlocked"
' Parameter 4 : (Boolean) False
'--------------------------------------------------

Dim arrayOfVariantOfULong5
arrayOfVariantOfULong5 = settingRepository1.GetAttrArray("ToolColorValue4")
'--------------------------------------------------
' Parameter 1 : (String) "ToolColorValue4"
' Returned value : (Array) 
'    Array[0] : (Variant) (Unsigned Long) 210
'    Array[1] : (Variant) (Unsigned Long) 0
'    Array[2] : (Variant) (Unsigned Long) 210
'--------------------------------------------------

Dim bSTR35
bSTR35 = ""
Dim bSTR36
bSTR36 = ""
Dim boolean20
settingRepository1.GetAttrInfo "ToolColorValue4", bSTR35, bSTR36, boolean20
'--------------------------------------------------
' Parameter 1 : (String) "ToolColorValue4"
' Parameter 2 : (String) "Default value"
' Parameter 3 : (String) "Unlocked"
' Parameter 4 : (Boolean) False
'--------------------------------------------------

Dim arrayOfVariantOfULong6
arrayOfVariantOfULong6 = settingRepository1.GetAttrArray("ToolColorValue5")
'--------------------------------------------------
' Parameter 1 : (String) "ToolColorValue5"
' Returned value : (Array) 
'    Array[0] : (Variant) (Unsigned Long) 255
'    Array[1] : (Variant) (Unsigned Long) 165
'    Array[2] : (Variant) (Unsigned Long) 0
'--------------------------------------------------

Dim bSTR37
bSTR37 = ""
Dim bSTR38
bSTR38 = ""
Dim boolean21
settingRepository1.GetAttrInfo "ToolColorValue5", bSTR37, bSTR38, boolean21
'--------------------------------------------------
' Parameter 1 : (String) "ToolColorValue5"
' Parameter 2 : (String) "Default value"
' Parameter 3 : (String) "Unlocked"
' Parameter 4 : (Boolean) False
'--------------------------------------------------

Dim arrayOfVariantOfULong7
arrayOfVariantOfULong7 = settingRepository1.GetAttrArray("ToolColorValue6")
'--------------------------------------------------
' Parameter 1 : (String) "ToolColorValue6"
' Returned value : (Array) 
'    Array[0] : (Variant) (Unsigned Long) 0
'    Array[1] : (Variant) (Unsigned Long) 210
'    Array[2] : (Variant) (Unsigned Long) 210
'--------------------------------------------------

Dim bSTR39
bSTR39 = ""
Dim bSTR40
bSTR40 = ""
Dim boolean22
settingRepository1.GetAttrInfo "ToolColorValue6", bSTR39, bSTR40, boolean22
'--------------------------------------------------
' Parameter 1 : (String) "ToolColorValue6"
' Parameter 2 : (String) "Default value"
' Parameter 3 : (String) "Unlocked"
' Parameter 4 : (Boolean) False
'--------------------------------------------------

Dim arrayOfVariantOfULong8
arrayOfVariantOfULong8 = settingRepository1.GetAttrArray("ToolColorValue7")
'--------------------------------------------------
' Parameter 1 : (String) "ToolColorValue7"
' Returned value : (Array) 
'    Array[0] : (Variant) (Unsigned Long) 220
'    Array[1] : (Variant) (Unsigned Long) 110
'    Array[2] : (Variant) (Unsigned Long) 215
'--------------------------------------------------

Dim bSTR41
bSTR41 = ""
Dim bSTR42
bSTR42 = ""
Dim boolean23
settingRepository1.GetAttrInfo "ToolColorValue7", bSTR41, bSTR42, boolean23
'--------------------------------------------------
' Parameter 1 : (String) "ToolColorValue7"
' Parameter 2 : (String) "Default value"
' Parameter 3 : (String) "Unlocked"
' Parameter 4 : (Boolean) False
'--------------------------------------------------

Dim arrayOfVariantOfULong9
arrayOfVariantOfULong9 = settingRepository1.GetAttrArray("ToolColorValue8")
'--------------------------------------------------
' Parameter 1 : (String) "ToolColorValue8"
' Returned value : (Array) 
'    Array[0] : (Variant) (Unsigned Long) 152
'    Array[1] : (Variant) (Unsigned Long) 83
'    Array[2] : (Variant) (Unsigned Long) 150
'--------------------------------------------------

Dim bSTR43
bSTR43 = ""
Dim bSTR44
bSTR44 = ""
Dim boolean24
settingRepository1.GetAttrInfo "ToolColorValue8", bSTR43, bSTR44, boolean24
'--------------------------------------------------
' Parameter 1 : (String) "ToolColorValue8"
' Parameter 2 : (String) "Default value"
' Parameter 3 : (String) "Unlocked"
' Parameter 4 : (Boolean) False
'--------------------------------------------------

Dim arrayOfVariantOfULong10
arrayOfVariantOfULong10 = settingRepository1.GetAttrArray("ToolColorValue9")
'--------------------------------------------------
' Parameter 1 : (String) "ToolColorValue9"
' Returned value : (Array) 
'    Array[0] : (Variant) (Unsigned Long) 85
'    Array[1] : (Variant) (Unsigned Long) 110
'    Array[2] : (Variant) (Unsigned Long) 45
'--------------------------------------------------

Dim bSTR45
bSTR45 = ""
Dim bSTR46
bSTR46 = ""
Dim boolean25
settingRepository1.GetAttrInfo "ToolColorValue9", bSTR45, bSTR46, boolean25
'--------------------------------------------------
' Parameter 1 : (String) "ToolColorValue9"
' Parameter 2 : (String) "Default value"
' Parameter 3 : (String) "Unlocked"
' Parameter 4 : (Boolean) False
'--------------------------------------------------

Dim arrayOfVariantOfULong11
arrayOfVariantOfULong11 = settingRepository1.GetAttrArray("ToolColorValue10")
'--------------------------------------------------
' Parameter 1 : (String) "ToolColorValue10"
' Returned value : (Array) 
'    Array[0] : (Variant) (Unsigned Long) 148
'    Array[1] : (Variant) (Unsigned Long) 0
'    Array[2] : (Variant) (Unsigned Long) 210
'--------------------------------------------------

Dim bSTR47
bSTR47 = ""
Dim bSTR48
bSTR48 = ""
Dim boolean26
settingRepository1.GetAttrInfo "ToolColorValue10", bSTR47, bSTR48, boolean26
'--------------------------------------------------
' Parameter 1 : (String) "ToolColorValue10"
' Parameter 2 : (String) "Default value"
' Parameter 3 : (String) "Unlocked"
' Parameter 4 : (Boolean) False
'--------------------------------------------------

Dim arrayOfVariantOfULong12
arrayOfVariantOfULong12 = settingRepository1.GetAttrArray("ToolColorValue11")
'--------------------------------------------------
' Parameter 1 : (String) "ToolColorValue11"
' Returned value : (Array) 
'    Array[0] : (Variant) (Unsigned Long) 41
'    Array[1] : (Variant) (Unsigned Long) 125
'    Array[2] : (Variant) (Unsigned Long) 209
'--------------------------------------------------

Dim bSTR49
bSTR49 = ""
Dim bSTR50
bSTR50 = ""
Dim boolean27
settingRepository1.GetAttrInfo "ToolColorValue11", bSTR49, bSTR50, boolean27
'--------------------------------------------------
' Parameter 1 : (String) "ToolColorValue11"
' Parameter 2 : (String) "Default value"
' Parameter 3 : (String) "Unlocked"
' Parameter 4 : (Boolean) False
'--------------------------------------------------

Dim arrayOfVariantOfULong13
arrayOfVariantOfULong13 = settingRepository1.GetAttrArray("ToolColorValue12")
'--------------------------------------------------
' Parameter 1 : (String) "ToolColorValue12"
' Returned value : (Array) 
'    Array[0] : (Variant) (Unsigned Long) 146
'    Array[1] : (Variant) (Unsigned Long) 209
'    Array[2] : (Variant) (Unsigned Long) 37
'--------------------------------------------------

Dim bSTR51
bSTR51 = ""
Dim bSTR52
bSTR52 = ""
Dim boolean28
settingRepository1.GetAttrInfo "ToolColorValue12", bSTR51, bSTR52, boolean28
'--------------------------------------------------
' Parameter 1 : (String) "ToolColorValue12"
' Parameter 2 : (String) "Default value"
' Parameter 3 : (String) "Unlocked"
' Parameter 4 : (Boolean) False
'--------------------------------------------------

Dim arrayOfVariantOfULong14
arrayOfVariantOfULong14 = settingRepository1.GetAttrArray("ToolColorValue13")
'--------------------------------------------------
' Parameter 1 : (String) "ToolColorValue13"
' Returned value : (Array) 
'    Array[0] : (Variant) (Unsigned Long) 190
'    Array[1] : (Variant) (Unsigned Long) 111
'    Array[2] : (Variant) (Unsigned Long) 0
'--------------------------------------------------

Dim bSTR53
bSTR53 = ""
Dim bSTR54
bSTR54 = ""
Dim boolean29
settingRepository1.GetAttrInfo "ToolColorValue13", bSTR53, bSTR54, boolean29
'--------------------------------------------------
' Parameter 1 : (String) "ToolColorValue13"
' Parameter 2 : (String) "Default value"
' Parameter 3 : (String) "Unlocked"
' Parameter 4 : (Boolean) False
'--------------------------------------------------

Dim arrayOfVariantOfULong15
arrayOfVariantOfULong15 = settingRepository1.GetAttrArray("ToolColorValue14")
'--------------------------------------------------
' Parameter 1 : (String) "ToolColorValue14"
' Returned value : (Array) 
'    Array[0] : (Variant) (Unsigned Long) 95
'    Array[1] : (Variant) (Unsigned Long) 160
'    Array[2] : (Variant) (Unsigned Long) 155
'--------------------------------------------------

Dim bSTR55
bSTR55 = ""
Dim bSTR56
bSTR56 = ""
Dim boolean30
settingRepository1.GetAttrInfo "ToolColorValue14", bSTR55, bSTR56, boolean30
'--------------------------------------------------
' Parameter 1 : (String) "ToolColorValue14"
' Parameter 2 : (String) "Default value"
' Parameter 3 : (String) "Unlocked"
' Parameter 4 : (Boolean) False
'--------------------------------------------------

Dim arrayOfVariantOfULong16
arrayOfVariantOfULong16 = settingRepository1.GetAttrArray("ToolColorValue15")
'--------------------------------------------------
' Parameter 1 : (String) "ToolColorValue15"
' Returned value : (Array) 
'    Array[0] : (Variant) (Unsigned Long) 210
'    Array[1] : (Variant) (Unsigned Long) 239
'    Array[2] : (Variant) (Unsigned Long) 219
'--------------------------------------------------

Dim bSTR57
bSTR57 = ""
Dim bSTR58
bSTR58 = ""
Dim boolean31
settingRepository1.GetAttrInfo "ToolColorValue15", bSTR57, bSTR58, boolean31
'--------------------------------------------------
' Parameter 1 : (String) "ToolColorValue15"
' Parameter 2 : (String) "Default value"
' Parameter 3 : (String) "Unlocked"
' Parameter 4 : (Boolean) False
'--------------------------------------------------

Dim arrayOfVariantOfULong17
arrayOfVariantOfULong17 = settingRepository1.GetAttrArray("ToolColorValue16")
'--------------------------------------------------
' Parameter 1 : (String) "ToolColorValue16"
' Returned value : (Array) 
'    Array[0] : (Variant) (Unsigned Long) 140
'    Array[1] : (Variant) (Unsigned Long) 70
'    Array[2] : (Variant) (Unsigned Long) 20
'--------------------------------------------------

Dim bSTR59
bSTR59 = ""
Dim bSTR60
bSTR60 = ""
Dim boolean32
settingRepository1.GetAttrInfo "ToolColorValue16", bSTR59, bSTR60, boolean32
'--------------------------------------------------
' Parameter 1 : (String) "ToolColorValue16"
' Parameter 2 : (String) "Default value"
' Parameter 3 : (String) "Unlocked"
' Parameter 4 : (Boolean) False
'--------------------------------------------------

Dim arrayOfVariantOfULong18
arrayOfVariantOfULong18 = settingRepository1.GetAttrArray("ToolColorValue17")
'--------------------------------------------------
' Parameter 1 : (String) "ToolColorValue17"
' Returned value : (Array) 
'    Array[0] : (Variant) (Unsigned Long) 70
'    Array[1] : (Variant) (Unsigned Long) 130
'    Array[2] : (Variant) (Unsigned Long) 180
'--------------------------------------------------

Dim bSTR61
bSTR61 = ""
Dim bSTR62
bSTR62 = ""
Dim boolean33
settingRepository1.GetAttrInfo "ToolColorValue17", bSTR61, bSTR62, boolean33
'--------------------------------------------------
' Parameter 1 : (String) "ToolColorValue17"
' Parameter 2 : (String) "Default value"
' Parameter 3 : (String) "Unlocked"
' Parameter 4 : (Boolean) False
'--------------------------------------------------

Dim arrayOfVariantOfULong19
arrayOfVariantOfULong19 = settingRepository1.GetAttrArray("ToolColorValue18")
'--------------------------------------------------
' Parameter 1 : (String) "ToolColorValue18"
' Returned value : (Array) 
'    Array[0] : (Variant) (Unsigned Long) 209
'    Array[1] : (Variant) (Unsigned Long) 187
'    Array[2] : (Variant) (Unsigned Long) 154
'--------------------------------------------------

Dim bSTR63
bSTR63 = ""
Dim bSTR64
bSTR64 = ""
Dim boolean34
settingRepository1.GetAttrInfo "ToolColorValue18", bSTR63, bSTR64, boolean34
'--------------------------------------------------
' Parameter 1 : (String) "ToolColorValue18"
' Parameter 2 : (String) "Default value"
' Parameter 3 : (String) "Unlocked"
' Parameter 4 : (Boolean) False
'--------------------------------------------------

Dim arrayOfVariantOfULong20
arrayOfVariantOfULong20 = settingRepository1.GetAttrArray("ToolColorValue19")
'--------------------------------------------------
' Parameter 1 : (String) "ToolColorValue19"
' Returned value : (Array) 
'    Array[0] : (Variant) (Unsigned Long) 110
'    Array[1] : (Variant) (Unsigned Long) 130
'    Array[2] : (Variant) (Unsigned Long) 140
'--------------------------------------------------

Dim bSTR65
bSTR65 = ""
Dim bSTR66
bSTR66 = ""
Dim boolean35
settingRepository1.GetAttrInfo "ToolColorValue19", bSTR65, bSTR66, boolean35
'--------------------------------------------------
' Parameter 1 : (String) "ToolColorValue19"
' Parameter 2 : (String) "Default value"
' Parameter 3 : (String) "Unlocked"
' Parameter 4 : (Boolean) False
'--------------------------------------------------

Dim arrayOfVariantOfULong21
arrayOfVariantOfULong21 = settingRepository1.GetAttrArray("ToolColorValue20")
'--------------------------------------------------
' Parameter 1 : (String) "ToolColorValue20"
' Returned value : (Array) 
'    Array[0] : (Variant) (Unsigned Long) 179
'    Array[1] : (Variant) (Unsigned Long) 142
'    Array[2] : (Variant) (Unsigned Long) 80
'--------------------------------------------------

Dim bSTR67
bSTR67 = ""
Dim bSTR68
bSTR68 = ""
Dim boolean36
settingRepository1.GetAttrInfo "ToolColorValue20", bSTR67, bSTR68, boolean36
'--------------------------------------------------
' Parameter 1 : (String) "ToolColorValue20"
' Parameter 2 : (String) "Default value"
' Parameter 3 : (String) "Unlocked"
' Parameter 4 : (Boolean) False
'--------------------------------------------------

Dim arrayOfVariantOfULong22
arrayOfVariantOfULong22 = settingRepository1.GetAttrArray("ToolColorValue21")
'--------------------------------------------------
' Parameter 1 : (String) "ToolColorValue21"
' Returned value : (Array) 
'    Array[0] : (Variant) (Unsigned Long) 0
'    Array[1] : (Variant) (Unsigned Long) 75
'    Array[2] : (Variant) (Unsigned Long) 205
'--------------------------------------------------

Dim bSTR69
bSTR69 = ""
Dim bSTR70
bSTR70 = ""
Dim boolean37
settingRepository1.GetAttrInfo "ToolColorValue21", bSTR69, bSTR70, boolean37
'--------------------------------------------------
' Parameter 1 : (String) "ToolColorValue21"
' Parameter 2 : (String) "Default value"
' Parameter 3 : (String) "Unlocked"
' Parameter 4 : (Boolean) False
'--------------------------------------------------

Dim arrayOfVariantOfULong23
arrayOfVariantOfULong23 = settingRepository1.GetAttrArray("ToolColorValue22")
'--------------------------------------------------
' Parameter 1 : (String) "ToolColorValue22"
' Returned value : (Array) 
'    Array[0] : (Variant) (Unsigned Long) 215
'    Array[1] : (Variant) (Unsigned Long) 155
'    Array[2] : (Variant) (Unsigned Long) 90
'--------------------------------------------------

Dim bSTR71
bSTR71 = ""
Dim bSTR72
bSTR72 = ""
Dim boolean38
settingRepository1.GetAttrInfo "ToolColorValue22", bSTR71, bSTR72, boolean38
'--------------------------------------------------
' Parameter 1 : (String) "ToolColorValue22"
' Parameter 2 : (String) "Default value"
' Parameter 3 : (String) "Unlocked"
' Parameter 4 : (Boolean) False
'--------------------------------------------------

Dim arrayOfVariantOfULong24
arrayOfVariantOfULong24 = settingRepository1.GetAttrArray("ToolColorValue23")
'--------------------------------------------------
' Parameter 1 : (String) "ToolColorValue23"
' Returned value : (Array) 
'    Array[0] : (Variant) (Unsigned Long) 210
'    Array[1] : (Variant) (Unsigned Long) 210
'    Array[2] : (Variant) (Unsigned Long) 210
'--------------------------------------------------

Dim bSTR73
bSTR73 = ""
Dim bSTR74
bSTR74 = ""
Dim boolean39
settingRepository1.GetAttrInfo "ToolColorValue23", bSTR73, bSTR74, boolean39
'--------------------------------------------------
' Parameter 1 : (String) "ToolColorValue23"
' Parameter 2 : (String) "Default value"
' Parameter 3 : (String) "Unlocked"
' Parameter 4 : (Boolean) False
'--------------------------------------------------

Dim arrayOfVariantOfULong25
arrayOfVariantOfULong25 = settingRepository1.GetAttrArray("ToolColorValue24")
'--------------------------------------------------
' Parameter 1 : (String) "ToolColorValue24"
' Returned value : (Array) 
'    Array[0] : (Variant) (Unsigned Long) 0
'    Array[1] : (Variant) (Unsigned Long) 0
'    Array[2] : (Variant) (Unsigned Long) 210
'--------------------------------------------------

Dim bSTR75
bSTR75 = ""
Dim bSTR76
bSTR76 = ""
Dim boolean40
settingRepository1.GetAttrInfo "ToolColorValue24", bSTR75, bSTR76, boolean40
'--------------------------------------------------
' Parameter 1 : (String) "ToolColorValue24"
' Parameter 2 : (String) "Default value"
' Parameter 3 : (String) "Unlocked"
' Parameter 4 : (Boolean) False
'--------------------------------------------------

Dim arrayOfVariantOfULong26
arrayOfVariantOfULong26 = settingRepository1.GetAttrArray("ToolColorValue25")
'--------------------------------------------------
' Parameter 1 : (String) "ToolColorValue25"
' Returned value : (Array) 
'    Array[0] : (Variant) (Unsigned Long) 178
'    Array[1] : (Variant) (Unsigned Long) 177
'    Array[2] : (Variant) (Unsigned Long) 165
'--------------------------------------------------

Dim bSTR77
bSTR77 = ""
Dim bSTR78
bSTR78 = ""
Dim boolean41
settingRepository1.GetAttrInfo "ToolColorValue25", bSTR77, bSTR78, boolean41
'--------------------------------------------------
' Parameter 1 : (String) "ToolColorValue25"
' Parameter 2 : (String) "Default value"
' Parameter 3 : (String) "Unlocked"
' Parameter 4 : (Boolean) False
'--------------------------------------------------

Dim arrayOfVariantOfULong27
arrayOfVariantOfULong27 = settingRepository1.GetAttrArray("ToolColorValue26")
'--------------------------------------------------
' Parameter 1 : (String) "ToolColorValue26"
' Returned value : (Array) 
'    Array[0] : (Variant) (Unsigned Long) 85
'    Array[1] : (Variant) (Unsigned Long) 107
'    Array[2] : (Variant) (Unsigned Long) 47
'--------------------------------------------------

Dim bSTR79
bSTR79 = ""
Dim bSTR80
bSTR80 = ""
Dim boolean42
settingRepository1.GetAttrInfo "ToolColorValue26", bSTR79, bSTR80, boolean42
'--------------------------------------------------
' Parameter 1 : (String) "ToolColorValue26"
' Parameter 2 : (String) "Default value"
' Parameter 3 : (String) "Unlocked"
' Parameter 4 : (Boolean) False
'--------------------------------------------------

Dim arrayOfVariantOfULong28
arrayOfVariantOfULong28 = settingRepository1.GetAttrArray("ToolColorValue27")
'--------------------------------------------------
' Parameter 1 : (String) "ToolColorValue27"
' Returned value : (Array) 
'    Array[0] : (Variant) (Unsigned Long) 173
'    Array[1] : (Variant) (Unsigned Long) 216
'    Array[2] : (Variant) (Unsigned Long) 230
'--------------------------------------------------

Dim bSTR81
bSTR81 = ""
Dim bSTR82
bSTR82 = ""
Dim boolean43
settingRepository1.GetAttrInfo "ToolColorValue27", bSTR81, bSTR82, boolean43
'--------------------------------------------------
' Parameter 1 : (String) "ToolColorValue27"
' Parameter 2 : (String) "Default value"
' Parameter 3 : (String) "Unlocked"
' Parameter 4 : (Boolean) False
'--------------------------------------------------

Dim arrayOfVariantOfULong29
arrayOfVariantOfULong29 = settingRepository1.GetAttrArray("ToolColorValue28")
'--------------------------------------------------
' Parameter 1 : (String) "ToolColorValue28"
' Returned value : (Array) 
'    Array[0] : (Variant) (Unsigned Long) 255
'    Array[1] : (Variant) (Unsigned Long) 239
'    Array[2] : (Variant) (Unsigned Long) 0
'--------------------------------------------------

Dim bSTR83
bSTR83 = ""
Dim bSTR84
bSTR84 = ""
Dim boolean44
settingRepository1.GetAttrInfo "ToolColorValue28", bSTR83, bSTR84, boolean44
'--------------------------------------------------
' Parameter 1 : (String) "ToolColorValue28"
' Parameter 2 : (String) "Default value"
' Parameter 3 : (String) "Unlocked"
' Parameter 4 : (Boolean) False
'--------------------------------------------------

Dim arrayOfVariantOfULong30
arrayOfVariantOfULong30 = settingRepository1.GetAttrArray("ToolColorValue29")
'--------------------------------------------------
' Parameter 1 : (String) "ToolColorValue29"
' Returned value : (Array) 
'    Array[0] : (Variant) (Unsigned Long) 255
'    Array[1] : (Variant) (Unsigned Long) 0
'    Array[2] : (Variant) (Unsigned Long) 255
'--------------------------------------------------

Dim bSTR85
bSTR85 = ""
Dim bSTR86
bSTR86 = ""
Dim boolean45
settingRepository1.GetAttrInfo "ToolColorValue29", bSTR85, bSTR86, boolean45
'--------------------------------------------------
' Parameter 1 : (String) "ToolColorValue29"
' Parameter 2 : (String) "Default value"
' Parameter 3 : (String) "Unlocked"
' Parameter 4 : (Boolean) False
'--------------------------------------------------

Dim arrayOfVariantOfULong31
arrayOfVariantOfULong31 = settingRepository1.GetAttrArray("ToolColorValue30")
'--------------------------------------------------
' Parameter 1 : (String) "ToolColorValue30"
' Returned value : (Array) 
'    Array[0] : (Variant) (Unsigned Long) 219
'    Array[1] : (Variant) (Unsigned Long) 223
'    Array[2] : (Variant) (Unsigned Long) 195
'--------------------------------------------------

Dim bSTR87
bSTR87 = ""
Dim bSTR88
bSTR88 = ""
Dim boolean46
settingRepository1.GetAttrInfo "ToolColorValue30", bSTR87, bSTR88, boolean46
'--------------------------------------------------
' Parameter 1 : (String) "ToolColorValue30"
' Parameter 2 : (String) "Default value"
' Parameter 3 : (String) "Unlocked"
' Parameter 4 : (Boolean) False
'--------------------------------------------------

Dim arrayOfVariantOfULong32
arrayOfVariantOfULong32 = settingRepository1.GetAttrArray("ToolColorValue31")
'--------------------------------------------------
' Parameter 1 : (String) "ToolColorValue31"
' Returned value : (Array) 
'    Array[0] : (Variant) (Unsigned Long) 255
'    Array[1] : (Variant) (Unsigned Long) 200
'    Array[2] : (Variant) (Unsigned Long) 0
'--------------------------------------------------

Dim bSTR89
bSTR89 = ""
Dim bSTR90
bSTR90 = ""
Dim boolean47
settingRepository1.GetAttrInfo "ToolColorValue31", bSTR89, bSTR90, boolean47
'--------------------------------------------------
' Parameter 1 : (String) "ToolColorValue31"
' Parameter 2 : (String) "Default value"
' Parameter 3 : (String) "Unlocked"
' Parameter 4 : (Boolean) False
'--------------------------------------------------

Dim arrayOfVariantOfULong33
arrayOfVariantOfULong33 = settingRepository1.GetAttrArray("ToolColorValue32")
'--------------------------------------------------
' Parameter 1 : (String) "ToolColorValue32"
' Returned value : (Array) 
'    Array[0] : (Variant) (Unsigned Long) 0
'    Array[1] : (Variant) (Unsigned Long) 255
'    Array[2] : (Variant) (Unsigned Long) 255
'--------------------------------------------------

Dim bSTR91
bSTR91 = ""
Dim bSTR92
bSTR92 = ""
Dim boolean48
settingRepository1.GetAttrInfo "ToolColorValue32", bSTR91, bSTR92, boolean48
'--------------------------------------------------
' Parameter 1 : (String) "ToolColorValue32"
' Parameter 2 : (String) "Default value"
' Parameter 3 : (String) "Unlocked"
' Parameter 4 : (Boolean) False
'--------------------------------------------------

Dim arrayOfVariantOfULong34
arrayOfVariantOfULong34 = settingRepository1.GetAttrArray("ToolColorValue33")
'--------------------------------------------------
' Parameter 1 : (String) "ToolColorValue33"
' Returned value : (Array) 
'    Array[0] : (Variant) (Unsigned Long) 50
'    Array[1] : (Variant) (Unsigned Long) 150
'    Array[2] : (Variant) (Unsigned Long) 255
'--------------------------------------------------

Dim bSTR93
bSTR93 = ""
Dim bSTR94
bSTR94 = ""
Dim boolean49
settingRepository1.GetAttrInfo "ToolColorValue33", bSTR93, bSTR94, boolean49
'--------------------------------------------------
' Parameter 1 : (String) "ToolColorValue33"
' Parameter 2 : (String) "Default value"
' Parameter 3 : (String) "Unlocked"
' Parameter 4 : (Boolean) False
'--------------------------------------------------

Dim arrayOfVariantOfULong35
arrayOfVariantOfULong35 = settingRepository1.GetAttrArray("ToolColorValue34")
'--------------------------------------------------
' Parameter 1 : (String) "ToolColorValue34"
' Returned value : (Array) 
'    Array[0] : (Variant) (Unsigned Long) 164
'    Array[1] : (Variant) (Unsigned Long) 196
'    Array[2] : (Variant) (Unsigned Long) 0
'--------------------------------------------------

Dim bSTR95
bSTR95 = ""
Dim bSTR96
bSTR96 = ""
Dim boolean50
settingRepository1.GetAttrInfo "ToolColorValue34", bSTR95, bSTR96, boolean50
'--------------------------------------------------
' Parameter 1 : (String) "ToolColorValue34"
' Parameter 2 : (String) "Default value"
' Parameter 3 : (String) "Unlocked"
' Parameter 4 : (Boolean) False
'--------------------------------------------------

Dim arrayOfVariantOfULong36
arrayOfVariantOfULong36 = settingRepository1.GetAttrArray("ToolColorValue35")
'--------------------------------------------------
' Parameter 1 : (String) "ToolColorValue35"
' Returned value : (Array) 
'    Array[0] : (Variant) (Unsigned Long) 199
'    Array[1] : (Variant) (Unsigned Long) 134
'    Array[2] : (Variant) (Unsigned Long) 207
'--------------------------------------------------

Dim bSTR97
bSTR97 = ""
Dim bSTR98
bSTR98 = ""
Dim boolean51
settingRepository1.GetAttrInfo "ToolColorValue35", bSTR97, bSTR98, boolean51
'--------------------------------------------------
' Parameter 1 : (String) "ToolColorValue35"
' Parameter 2 : (String) "Default value"
' Parameter 3 : (String) "Unlocked"
' Parameter 4 : (Boolean) False
'--------------------------------------------------

Dim arrayOfVariantOfULong37
arrayOfVariantOfULong37 = settingRepository1.GetAttrArray("ToolColorValue36")
'--------------------------------------------------
' Parameter 1 : (String) "ToolColorValue36"
' Returned value : (Array) 
'    Array[0] : (Variant) (Unsigned Long) 87
'    Array[1] : (Variant) (Unsigned Long) 44
'    Array[2] : (Variant) (Unsigned Long) 41
'--------------------------------------------------

Dim bSTR99
bSTR99 = ""
Dim bSTR100
bSTR100 = ""
Dim boolean52
settingRepository1.GetAttrInfo "ToolColorValue36", bSTR99, bSTR100, boolean52
'--------------------------------------------------
' Parameter 1 : (String) "ToolColorValue36"
' Parameter 2 : (String) "Default value"
' Parameter 3 : (String) "Unlocked"
' Parameter 4 : (Boolean) False
'--------------------------------------------------

Dim arrayOfVariantOfULong38
arrayOfVariantOfULong38 = settingRepository1.GetAttrArray("ToolColorValue37")
'--------------------------------------------------
' Parameter 1 : (String) "ToolColorValue37"
' Returned value : (Array) 
'    Array[0] : (Variant) (Unsigned Long) 250
'    Array[1] : (Variant) (Unsigned Long) 207
'    Array[2] : (Variant) (Unsigned Long) 99
'--------------------------------------------------

Dim bSTR101
bSTR101 = ""
Dim bSTR102
bSTR102 = ""
Dim boolean53
settingRepository1.GetAttrInfo "ToolColorValue37", bSTR101, bSTR102, boolean53
'--------------------------------------------------
' Parameter 1 : (String) "ToolColorValue37"
' Parameter 2 : (String) "Default value"
' Parameter 3 : (String) "Unlocked"
' Parameter 4 : (Boolean) False
'--------------------------------------------------

Dim arrayOfVariantOfULong39
arrayOfVariantOfULong39 = settingRepository1.GetAttrArray("ToolColorValue38")
'--------------------------------------------------
' Parameter 1 : (String) "ToolColorValue38"
' Returned value : (Array) 
'    Array[0] : (Variant) (Unsigned Long) 174
'    Array[1] : (Variant) (Unsigned Long) 209
'    Array[2] : (Variant) (Unsigned Long) 233
'--------------------------------------------------

Dim bSTR103
bSTR103 = ""
Dim bSTR104
bSTR104 = ""
Dim boolean54
settingRepository1.GetAttrInfo "ToolColorValue38", bSTR103, bSTR104, boolean54
'--------------------------------------------------
' Parameter 1 : (String) "ToolColorValue38"
' Parameter 2 : (String) "Default value"
' Parameter 3 : (String) "Unlocked"
' Parameter 4 : (Boolean) False
'--------------------------------------------------

Dim arrayOfVariantOfULong40
arrayOfVariantOfULong40 = settingRepository1.GetAttrArray("ToolColorValue39")
'--------------------------------------------------
' Parameter 1 : (String) "ToolColorValue39"
' Returned value : (Array) 
'    Array[0] : (Variant) (Unsigned Long) 246
'    Array[1] : (Variant) (Unsigned Long) 139
'    Array[2] : (Variant) (Unsigned Long) 105
'--------------------------------------------------

Dim bSTR105
bSTR105 = ""
Dim bSTR106
bSTR106 = ""
Dim boolean55
settingRepository1.GetAttrInfo "ToolColorValue39", bSTR105, bSTR106, boolean55
'--------------------------------------------------
' Parameter 1 : (String) "ToolColorValue39"
' Parameter 2 : (String) "Default value"
' Parameter 3 : (String) "Unlocked"
' Parameter 4 : (Boolean) False
'--------------------------------------------------

Dim arrayOfVariantOfULong41
arrayOfVariantOfULong41 = settingRepository1.GetAttrArray("ToolColorValue40")
'--------------------------------------------------
' Parameter 1 : (String) "ToolColorValue40"
' Returned value : (Array) 
'    Array[0] : (Variant) (Unsigned Long) 161
'    Array[1] : (Variant) (Unsigned Long) 206
'    Array[2] : (Variant) (Unsigned Long) 94
'--------------------------------------------------

Dim bSTR107
bSTR107 = ""
Dim bSTR108
bSTR108 = ""
Dim boolean56
settingRepository1.GetAttrInfo "ToolColorValue40", bSTR107, bSTR108, boolean56
'--------------------------------------------------
' Parameter 1 : (String) "ToolColorValue40"
' Parameter 2 : (String) "Default value"
' Parameter 3 : (String) "Unlocked"
' Parameter 4 : (Boolean) False
'--------------------------------------------------

Dim arrayOfVariantOfULong42
arrayOfVariantOfULong42 = settingRepository1.GetAttrArray("ToolColorValue41")
'--------------------------------------------------
' Parameter 1 : (String) "ToolColorValue41"
' Returned value : (Array) 
'    Array[0] : (Variant) (Unsigned Long) 128
'    Array[1] : (Variant) (Unsigned Long) 84
'    Array[2] : (Variant) (Unsigned Long) 98
'--------------------------------------------------

Dim bSTR109
bSTR109 = ""
Dim bSTR110
bSTR110 = ""
Dim boolean57
settingRepository1.GetAttrInfo "ToolColorValue41", bSTR109, bSTR110, boolean57
'--------------------------------------------------
' Parameter 1 : (String) "ToolColorValue41"
' Parameter 2 : (String) "Default value"
' Parameter 3 : (String) "Unlocked"
' Parameter 4 : (Boolean) False
'--------------------------------------------------

Dim arrayOfVariantOfULong43
arrayOfVariantOfULong43 = settingRepository1.GetAttrArray("ToolColorValue42")
'--------------------------------------------------
' Parameter 1 : (String) "ToolColorValue42"
' Returned value : (Array) 
'    Array[0] : (Variant) (Unsigned Long) 162
'    Array[1] : (Variant) (Unsigned Long) 208
'    Array[2] : (Variant) (Unsigned Long) 207
'--------------------------------------------------

Dim bSTR111
bSTR111 = ""
Dim bSTR112
bSTR112 = ""
Dim boolean58
settingRepository1.GetAttrInfo "ToolColorValue42", bSTR111, bSTR112, boolean58
'--------------------------------------------------
' Parameter 1 : (String) "ToolColorValue42"
' Parameter 2 : (String) "Default value"
' Parameter 3 : (String) "Unlocked"
' Parameter 4 : (Boolean) False
'--------------------------------------------------

Dim arrayOfVariantOfULong44
arrayOfVariantOfULong44 = settingRepository1.GetAttrArray("ToolColorValue43")
'--------------------------------------------------
' Parameter 1 : (String) "ToolColorValue43"
' Returned value : (Array) 
'    Array[0] : (Variant) (Unsigned Long) 251
'    Array[1] : (Variant) (Unsigned Long) 175
'    Array[2] : (Variant) (Unsigned Long) 95
'--------------------------------------------------

Dim bSTR113
bSTR113 = ""
Dim bSTR114
bSTR114 = ""
Dim boolean59
settingRepository1.GetAttrInfo "ToolColorValue43", bSTR113, bSTR114, boolean59
'--------------------------------------------------
' Parameter 1 : (String) "ToolColorValue43"
' Parameter 2 : (String) "Default value"
' Parameter 3 : (String) "Unlocked"
' Parameter 4 : (Boolean) False
'--------------------------------------------------

Dim arrayOfVariantOfULong45
arrayOfVariantOfULong45 = settingRepository1.GetAttrArray("ToolColorValue44")
'--------------------------------------------------
' Parameter 1 : (String) "ToolColorValue44"
' Returned value : (Array) 
'    Array[0] : (Variant) (Unsigned Long) 227
'    Array[1] : (Variant) (Unsigned Long) 223
'    Array[2] : (Variant) (Unsigned Long) 214
'--------------------------------------------------

Dim bSTR115
bSTR115 = ""
Dim bSTR116
bSTR116 = ""
Dim boolean60
settingRepository1.GetAttrInfo "ToolColorValue44", bSTR115, bSTR116, boolean60
'--------------------------------------------------
' Parameter 1 : (String) "ToolColorValue44"
' Parameter 2 : (String) "Default value"
' Parameter 3 : (String) "Unlocked"
' Parameter 4 : (Boolean) False
'--------------------------------------------------

Dim arrayOfVariantOfULong46
arrayOfVariantOfULong46 = settingRepository1.GetAttrArray("ToolColorValue45")
'--------------------------------------------------
' Parameter 1 : (String) "ToolColorValue45"
' Returned value : (Array) 
'    Array[0] : (Variant) (Unsigned Long) 200
'    Array[1] : (Variant) (Unsigned Long) 201
'    Array[2] : (Variant) (Unsigned Long) 208
'--------------------------------------------------

Dim bSTR117
bSTR117 = ""
Dim bSTR118
bSTR118 = ""
Dim boolean61
settingRepository1.GetAttrInfo "ToolColorValue45", bSTR117, bSTR118, boolean61
'--------------------------------------------------
' Parameter 1 : (String) "ToolColorValue45"
' Parameter 2 : (String) "Default value"
' Parameter 3 : (String) "Unlocked"
' Parameter 4 : (Boolean) False
'--------------------------------------------------

Dim arrayOfVariantOfULong47
arrayOfVariantOfULong47 = settingRepository1.GetAttrArray("ToolColorValue46")
'--------------------------------------------------
' Parameter 1 : (String) "ToolColorValue46"
' Returned value : (Array) 
'    Array[0] : (Variant) (Unsigned Long) 0
'    Array[1] : (Variant) (Unsigned Long) 145
'    Array[2] : (Variant) (Unsigned Long) 156
'--------------------------------------------------

Dim bSTR119
bSTR119 = ""
Dim bSTR120
bSTR120 = ""
Dim boolean62
settingRepository1.GetAttrInfo "ToolColorValue46", bSTR119, bSTR120, boolean62
'--------------------------------------------------
' Parameter 1 : (String) "ToolColorValue46"
' Parameter 2 : (String) "Default value"
' Parameter 3 : (String) "Unlocked"
' Parameter 4 : (Boolean) False
'--------------------------------------------------

Dim arrayOfVariantOfULong48
arrayOfVariantOfULong48 = settingRepository1.GetAttrArray("ToolColorValue47")
'--------------------------------------------------
' Parameter 1 : (String) "ToolColorValue47"
' Returned value : (Array) 
'    Array[0] : (Variant) (Unsigned Long) 206
'    Array[1] : (Variant) (Unsigned Long) 215
'    Array[2] : (Variant) (Unsigned Long) 92
'--------------------------------------------------

Dim bSTR121
bSTR121 = ""
Dim bSTR122
bSTR122 = ""
Dim boolean63
settingRepository1.GetAttrInfo "ToolColorValue47", bSTR121, bSTR122, boolean63
'--------------------------------------------------
' Parameter 1 : (String) "ToolColorValue47"
' Parameter 2 : (String) "Default value"
' Parameter 3 : (String) "Unlocked"
' Parameter 4 : (Boolean) False
'--------------------------------------------------

Dim arrayOfVariantOfULong49
arrayOfVariantOfULong49 = settingRepository1.GetAttrArray("ToolColorValue48")
'--------------------------------------------------
' Parameter 1 : (String) "ToolColorValue48"
' Returned value : (Array) 
'    Array[0] : (Variant) (Unsigned Long) 255
'    Array[1] : (Variant) (Unsigned Long) 242
'    Array[2] : (Variant) (Unsigned Long) 236
'--------------------------------------------------

Dim bSTR123
bSTR123 = ""
Dim bSTR124
bSTR124 = ""
Dim boolean64
settingRepository1.GetAttrInfo "ToolColorValue48", bSTR123, bSTR124, boolean64
'--------------------------------------------------
' Parameter 1 : (String) "ToolColorValue48"
' Parameter 2 : (String) "Default value"
' Parameter 3 : (String) "Unlocked"
' Parameter 4 : (Boolean) False
'--------------------------------------------------

Dim arrayOfVariantOfULong50
arrayOfVariantOfULong50 = settingRepository1.GetAttrArray("ToolColorValue49")
'--------------------------------------------------
' Parameter 1 : (String) "ToolColorValue49"
' Returned value : (Array) 
'    Array[0] : (Variant) (Unsigned Long) 0
'    Array[1] : (Variant) (Unsigned Long) 101
'    Array[2] : (Variant) (Unsigned Long) 169
'--------------------------------------------------

Dim bSTR125
bSTR125 = ""
Dim bSTR126
bSTR126 = ""
Dim boolean65
settingRepository1.GetAttrInfo "ToolColorValue49", bSTR125, bSTR126, boolean65
'--------------------------------------------------
' Parameter 1 : (String) "ToolColorValue49"
' Parameter 2 : (String) "Default value"
' Parameter 3 : (String) "Unlocked"
' Parameter 4 : (Boolean) False
'--------------------------------------------------

Dim arrayOfVariantOfULong51
arrayOfVariantOfULong51 = settingRepository1.GetAttrArray("ToolColorValue50")
'--------------------------------------------------
' Parameter 1 : (String) "ToolColorValue50"
' Returned value : (Array) 
'    Array[0] : (Variant) (Unsigned Long) 255
'    Array[1] : (Variant) (Unsigned Long) 226
'    Array[2] : (Variant) (Unsigned Long) 147
'--------------------------------------------------

Dim bSTR127
bSTR127 = ""
Dim bSTR128
bSTR128 = ""
Dim boolean66
settingRepository1.GetAttrInfo "ToolColorValue50", bSTR127, bSTR128, boolean66
'--------------------------------------------------
' Parameter 1 : (String) "ToolColorValue50"
' Parameter 2 : (String) "Default value"
' Parameter 3 : (String) "Unlocked"
' Parameter 4 : (Boolean) False
'--------------------------------------------------

Dim arrayOfVariantOfULong52
arrayOfVariantOfULong52 = settingRepository1.GetAttrArray("FeedColorValue1")
'--------------------------------------------------
' Parameter 1 : (String) "FeedColorValue1"
' Returned value : (Array) 
'    Array[0] : (Variant) (Unsigned Long) 29
'    Array[1] : (Variant) (Unsigned Long) 210
'    Array[2] : (Variant) (Unsigned Long) 29
'--------------------------------------------------

Dim bSTR129
bSTR129 = ""
Dim bSTR130
bSTR130 = ""
Dim boolean67
settingRepository1.GetAttrInfo "FeedColorValue1", bSTR129, bSTR130, boolean67
'--------------------------------------------------
' Parameter 1 : (String) "FeedColorValue1"
' Parameter 2 : (String) "Default value"
' Parameter 3 : (String) "Unlocked"
' Parameter 4 : (Boolean) False
'--------------------------------------------------

float4 = settingRepository1.GetAttr("FeedValue1")
'--------------------------------------------------
' Parameter 1 : (String) "FeedValue1"
' Returned value : (Variant) (Float) 100.000000
'--------------------------------------------------

Dim bSTR131
bSTR131 = ""
Dim bSTR132
bSTR132 = ""
Dim boolean68
settingRepository1.GetAttrInfo "FeedValue1", bSTR131, bSTR132, boolean68
'--------------------------------------------------
' Parameter 1 : (String) "FeedValue1"
' Parameter 2 : (String) "Default value"
' Parameter 3 : (String) "Unlocked"
' Parameter 4 : (Boolean) False
'--------------------------------------------------

Dim arrayOfVariantOfULong53
arrayOfVariantOfULong53 = settingRepository1.GetAttrArray("FeedColorValue2")
'--------------------------------------------------
' Parameter 1 : (String) "FeedColorValue2"
' Returned value : (Array) 
'    Array[0] : (Variant) (Unsigned Long) 210
'    Array[1] : (Variant) (Unsigned Long) 210
'    Array[2] : (Variant) (Unsigned Long) 0
'--------------------------------------------------

Dim bSTR133
bSTR133 = ""
Dim bSTR134
bSTR134 = ""
Dim boolean69
settingRepository1.GetAttrInfo "FeedColorValue2", bSTR133, bSTR134, boolean69
'--------------------------------------------------
' Parameter 1 : (String) "FeedColorValue2"
' Parameter 2 : (String) "Default value"
' Parameter 3 : (String) "Unlocked"
' Parameter 4 : (Boolean) False
'--------------------------------------------------

float5 = settingRepository1.GetAttr("FeedValue2")
'--------------------------------------------------
' Parameter 1 : (String) "FeedValue2"
' Returned value : (Variant) (Float) 500.000000
'--------------------------------------------------

Dim bSTR135
bSTR135 = ""
Dim bSTR136
bSTR136 = ""
Dim boolean70
settingRepository1.GetAttrInfo "FeedValue2", bSTR135, bSTR136, boolean70
'--------------------------------------------------
' Parameter 1 : (String) "FeedValue2"
' Parameter 2 : (String) "Default value"
' Parameter 3 : (String) "Unlocked"
' Parameter 4 : (Boolean) False
'--------------------------------------------------

Dim arrayOfVariantOfULong54
arrayOfVariantOfULong54 = settingRepository1.GetAttrArray("FeedColorValue3")
'--------------------------------------------------
' Parameter 1 : (String) "FeedColorValue3"
' Returned value : (Array) 
'    Array[0] : (Variant) (Unsigned Long) 0
'    Array[1] : (Variant) (Unsigned Long) 108
'    Array[2] : (Variant) (Unsigned Long) 209
'--------------------------------------------------

Dim bSTR137
bSTR137 = ""
Dim bSTR138
bSTR138 = ""
Dim boolean71
settingRepository1.GetAttrInfo "FeedColorValue3", bSTR137, bSTR138, boolean71
'--------------------------------------------------
' Parameter 1 : (String) "FeedColorValue3"
' Parameter 2 : (String) "Default value"
' Parameter 3 : (String) "Unlocked"
' Parameter 4 : (Boolean) False
'--------------------------------------------------

float6 = settingRepository1.GetAttr("FeedValue3")
'--------------------------------------------------
' Parameter 1 : (String) "FeedValue3"
' Returned value : (Variant) (Float) 1000.000000
'--------------------------------------------------

Dim bSTR139
bSTR139 = ""
Dim bSTR140
bSTR140 = ""
Dim boolean72
settingRepository1.GetAttrInfo "FeedValue3", bSTR139, bSTR140, boolean72
'--------------------------------------------------
' Parameter 1 : (String) "FeedValue3"
' Parameter 2 : (String) "Default value"
' Parameter 3 : (String) "Unlocked"
' Parameter 4 : (Boolean) False
'--------------------------------------------------

Dim arrayOfVariantOfULong55
arrayOfVariantOfULong55 = settingRepository1.GetAttrArray("FeedColorValue4")
'--------------------------------------------------
' Parameter 1 : (String) "FeedColorValue4"
' Returned value : (Array) 
'    Array[0] : (Variant) (Unsigned Long) 0
'    Array[1] : (Variant) (Unsigned Long) 0
'    Array[2] : (Variant) (Unsigned Long) 210
'--------------------------------------------------

Dim bSTR141
bSTR141 = ""
Dim bSTR142
bSTR142 = ""
Dim boolean73
settingRepository1.GetAttrInfo "FeedColorValue4", bSTR141, bSTR142, boolean73
'--------------------------------------------------
' Parameter 1 : (String) "FeedColorValue4"
' Parameter 2 : (String) "Default value"
' Parameter 3 : (String) "Unlocked"
' Parameter 4 : (Boolean) False
'--------------------------------------------------

float7 = settingRepository1.GetAttr("FeedValue4")
'--------------------------------------------------
' Parameter 1 : (String) "FeedValue4"
' Returned value : (Variant) (Float) 5000.000000
'--------------------------------------------------

Dim bSTR143
bSTR143 = ""
Dim bSTR144
bSTR144 = ""
Dim boolean74
settingRepository1.GetAttrInfo "FeedValue4", bSTR143, bSTR144, boolean74
'--------------------------------------------------
' Parameter 1 : (String) "FeedValue4"
' Parameter 2 : (String) "Default value"
' Parameter 3 : (String) "Unlocked"
' Parameter 4 : (Boolean) False
'--------------------------------------------------

Dim arrayOfVariantOfULong56
arrayOfVariantOfULong56 = settingRepository1.GetAttrArray("FeedColorValue5")
'--------------------------------------------------
' Parameter 1 : (String) "FeedColorValue5"
' Returned value : (Array) 
'    Array[0] : (Variant) (Unsigned Long) 210
'    Array[1] : (Variant) (Unsigned Long) 0
'    Array[2] : (Variant) (Unsigned Long) 210
'--------------------------------------------------

Dim bSTR145
bSTR145 = ""
Dim bSTR146
bSTR146 = ""
Dim boolean75
settingRepository1.GetAttrInfo "FeedColorValue5", bSTR145, bSTR146, boolean75
'--------------------------------------------------
' Parameter 1 : (String) "FeedColorValue5"
' Parameter 2 : (String) "Default value"
' Parameter 3 : (String) "Unlocked"
' Parameter 4 : (Boolean) False
'--------------------------------------------------

float8 = settingRepository1.GetAttr("FeedValue5")
'--------------------------------------------------
' Parameter 1 : (String) "FeedValue5"
' Returned value : (Variant) (Float) 10000.000000
'--------------------------------------------------

Dim bSTR147
bSTR147 = ""
Dim bSTR148
bSTR148 = ""
Dim boolean76
settingRepository1.GetAttrInfo "FeedValue5", bSTR147, bSTR148, boolean76
'--------------------------------------------------
' Parameter 1 : (String) "FeedValue5"
' Parameter 2 : (String) "Default value"
' Parameter 3 : (String) "Unlocked"
' Parameter 4 : (Boolean) False
'--------------------------------------------------

Dim arrayOfVariantOfULong57
arrayOfVariantOfULong57 = settingRepository1.GetAttrArray("FeedColorValue6")
'--------------------------------------------------
' Parameter 1 : (String) "FeedColorValue6"
' Returned value : (Array) 
'    Array[0] : (Variant) (Unsigned Long) 148
'    Array[1] : (Variant) (Unsigned Long) 0
'    Array[2] : (Variant) (Unsigned Long) 210
'--------------------------------------------------

Dim bSTR149
bSTR149 = ""
Dim bSTR150
bSTR150 = ""
Dim boolean77
settingRepository1.GetAttrInfo "FeedColorValue6", bSTR149, bSTR150, boolean77
'--------------------------------------------------
' Parameter 1 : (String) "FeedColorValue6"
' Parameter 2 : (String) "Default value"
' Parameter 3 : (String) "Unlocked"
' Parameter 4 : (Boolean) False
'--------------------------------------------------

float9 = settingRepository1.GetAttr("FeedValue6")
'--------------------------------------------------
' Parameter 1 : (String) "FeedValue6"
' Returned value : (Variant) (Float) 50000.000000
'--------------------------------------------------

Dim bSTR151
bSTR151 = ""
Dim bSTR152
bSTR152 = ""
Dim boolean78
settingRepository1.GetAttrInfo "FeedValue6", bSTR151, bSTR152, boolean78
'--------------------------------------------------
' Parameter 1 : (String) "FeedValue6"
' Parameter 2 : (String) "Default value"
' Parameter 3 : (String) "Unlocked"
' Parameter 4 : (Boolean) False
'--------------------------------------------------

Dim arrayOfVariantOfULong58
arrayOfVariantOfULong58 = settingRepository1.GetAttrArray("FeedColorValue7")
'--------------------------------------------------
' Parameter 1 : (String) "FeedColorValue7"
' Returned value : (Array) 
'    Array[0] : (Variant) (Unsigned Long) 255
'    Array[1] : (Variant) (Unsigned Long) 165
'    Array[2] : (Variant) (Unsigned Long) 0
'--------------------------------------------------

Dim bSTR153
bSTR153 = ""
Dim bSTR154
bSTR154 = ""
Dim boolean79
settingRepository1.GetAttrInfo "FeedColorValue7", bSTR153, bSTR154, boolean79
'--------------------------------------------------
' Parameter 1 : (String) "FeedColorValue7"
' Parameter 2 : (String) "Default value"
' Parameter 3 : (String) "Unlocked"
' Parameter 4 : (Boolean) False
'--------------------------------------------------

End Sub
