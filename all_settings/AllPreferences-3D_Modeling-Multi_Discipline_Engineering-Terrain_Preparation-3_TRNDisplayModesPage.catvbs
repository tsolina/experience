Language="VBSCRIPT"

Sub CATMain()

Set settingControllers1 = CATIA.SettingControllers

Set settingRepository1 = settingControllers1.Item("CATTerrainPreferenceSettings")

boolean1 = settingRepository1.GetAttr("TrnPrep_ApplyTextOnOpen_ChkBox")
'--------------------------------------------------
' Parameter 1 : (String) "TrnPrep_ApplyTextOnOpen_ChkBox"
' Returned value : (Variant) (Boolean) False
'--------------------------------------------------

Dim bSTR1
bSTR1 = ""
Dim bSTR2
bSTR2 = ""
Dim boolean2
settingRepository1.GetAttrInfo "TrnPrep_ApplyTextOnOpen_ChkBox", bSTR1, bSTR2, boolean2
'--------------------------------------------------
' Parameter 1 : (String) "TrnPrep_ApplyTextOnOpen_ChkBox"
' Parameter 2 : (String) "Default value"
' Parameter 3 : (String) "Unlocked"
' Parameter 4 : (Boolean) False
'--------------------------------------------------

boolean3 = settingRepository1.GetAttr("TrnPrep_ApplyLandCover_ChkBox")
'--------------------------------------------------
' Parameter 1 : (String) "TrnPrep_ApplyLandCover_ChkBox"
' Returned value : (Variant) (Boolean) False
'--------------------------------------------------

Dim bSTR3
bSTR3 = ""
Dim bSTR4
bSTR4 = ""
Dim boolean4
settingRepository1.GetAttrInfo "TrnPrep_ApplyLandCover_ChkBox", bSTR3, bSTR4, boolean4
'--------------------------------------------------
' Parameter 1 : (String) "TrnPrep_ApplyLandCover_ChkBox"
' Parameter 2 : (String) "Default value"
' Parameter 3 : (String) "Unlocked"
' Parameter 4 : (Boolean) False
'--------------------------------------------------

End Sub
