Language="VBSCRIPT"

Sub CATMain()

Set settingControllers1 = CATIA.SettingControllers

Set settingRepository1 = settingControllers1.Item("CATPpxOptionData_Rendering")

long1 = settingRepository1.GetAttr("ConeOpaqueValue")
'--------------------------------------------------
' Parameter 1 : (String) "ConeOpaqueValue"
' Returned value : (Variant) (Long) 50
'--------------------------------------------------

Dim bSTR1
bSTR1 = ""
Dim bSTR2
bSTR2 = ""
Dim boolean1
settingRepository1.GetAttrInfo "ConeOpaqueValue", bSTR1, bSTR2, boolean1
'--------------------------------------------------
' Parameter 1 : (String) "ConeOpaqueValue"
' Parameter 2 : (String) "Default value"
' Parameter 3 : (String) "Unlocked"
' Parameter 4 : (Boolean) False
'--------------------------------------------------

End Sub
