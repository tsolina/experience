Language="VBSCRIPT"

Sub CATMain()

Set settingControllers1 = CATIA.SettingControllers

Set settingRepository1 = settingControllers1.Item("LatticeDesign")

boolean1 = settingRepository1.GetAttr("Enable_Standard_Values")
'--------------------------------------------------
' Parameter 1 : (String) "Enable_Standard_Values"
' Returned value : (Variant) (Boolean) False
'--------------------------------------------------

Dim bSTR1
bSTR1 = ""
Dim bSTR2
bSTR2 = ""
Dim boolean2
settingRepository1.GetAttrInfo "Enable_Standard_Values", bSTR1, bSTR2, boolean2
'--------------------------------------------------
' Parameter 1 : (String) "Enable_Standard_Values"
' Parameter 2 : (String) "Default value"
' Parameter 3 : (String) "Unlocked"
' Parameter 4 : (Boolean) False
'--------------------------------------------------

boolean3 = settingRepository1.GetAttr("Deactivate_GPGPU_Computation")
'--------------------------------------------------
' Parameter 1 : (String) "Deactivate_GPGPU_Computation"
' Returned value : (Variant) (Boolean) False
'--------------------------------------------------

Dim bSTR3
bSTR3 = ""
Dim bSTR4
bSTR4 = ""
Dim boolean4
settingRepository1.GetAttrInfo "Deactivate_GPGPU_Computation", bSTR3, bSTR4, boolean4
'--------------------------------------------------
' Parameter 1 : (String) "Deactivate_GPGPU_Computation"
' Parameter 2 : (String) "Default value"
' Parameter 3 : (String) "Unlocked"
' Parameter 4 : (Boolean) False
'--------------------------------------------------

End Sub
