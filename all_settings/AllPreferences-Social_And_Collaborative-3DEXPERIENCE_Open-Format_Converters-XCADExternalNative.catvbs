Language="VBSCRIPT"

Sub CATMain()

Set settingControllers1 = CATIA.SettingControllers

Set settingRepository1 = settingControllers1.Item("MultiCAD")

short1 = settingRepository1.GetAttr("ImportProfileMode")
'--------------------------------------------------
' Parameter 1 : (String) "ImportProfileMode"
' Returned value : (Variant) (Short) 1
'--------------------------------------------------

Dim bSTR1
bSTR1 = ""
Dim bSTR2
bSTR2 = ""
Dim boolean1
settingRepository1.GetAttrInfo "ImportProfileMode", bSTR1, bSTR2, boolean1
'--------------------------------------------------
' Parameter 1 : (String) "ImportProfileMode"
' Parameter 2 : (String) "Default value"
' Parameter 3 : (String) "Unlocked"
' Parameter 4 : (Boolean) False
'--------------------------------------------------

long1 = settingRepository1.GetAttr("ImportLinkedFiles")
'--------------------------------------------------
' Parameter 1 : (String) "ImportLinkedFiles"
' Returned value : (Variant) (Long) 0
'--------------------------------------------------

Dim bSTR3
bSTR3 = ""
Dim bSTR4
bSTR4 = ""
Dim boolean2
settingRepository1.GetAttrInfo "ImportLinkedFiles", bSTR3, bSTR4, boolean2
'--------------------------------------------------
' Parameter 1 : (String) "ImportLinkedFiles"
' Parameter 2 : (String) "Default value"
' Parameter 3 : (String) "Unlocked"
' Parameter 4 : (Boolean) False
'--------------------------------------------------

End Sub
