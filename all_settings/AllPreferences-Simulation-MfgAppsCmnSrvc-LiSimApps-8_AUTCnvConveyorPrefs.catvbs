Language="VBSCRIPT"

Sub CATMain()

Set settingControllers1 = CATIA.SettingControllers

Set settingRepository1 = settingControllers1.Item("AUTCnvConveyor")

short1 = settingRepository1.GetAttr("PreciseWorkpiece")
'--------------------------------------------------
' Parameter 1 : (String) "PreciseWorkpiece"
' Returned value : (Variant) (Short) 0
'--------------------------------------------------

Dim bSTR1
bSTR1 = ""
Dim bSTR2
bSTR2 = ""
Dim boolean1
settingRepository1.GetAttrInfo "PreciseWorkpiece", bSTR1, bSTR2, boolean1
'--------------------------------------------------
' Parameter 1 : (String) "PreciseWorkpiece"
' Parameter 2 : (String) "Default value"
' Parameter 3 : (String) "Unlocked"
' Parameter 4 : (Boolean) False
'--------------------------------------------------

uLong1 = settingRepository1.GetAttr("RemoveLegacyIO")
'--------------------------------------------------
' Parameter 1 : (String) "RemoveLegacyIO"
' Returned value : (Variant) (Unsigned Long) 0
'--------------------------------------------------

Dim bSTR3
bSTR3 = ""
Dim bSTR4
bSTR4 = ""
Dim boolean2
settingRepository1.GetAttrInfo "RemoveLegacyIO", bSTR3, bSTR4, boolean2
'--------------------------------------------------
' Parameter 1 : (String) "RemoveLegacyIO"
' Parameter 2 : (String) "Default value"
' Parameter 3 : (String) "Unlocked"
' Parameter 4 : (Boolean) False
'--------------------------------------------------

End Sub
