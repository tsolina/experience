Language="VBSCRIPT"

Sub CATMain()

Set settingControllers1 = CATIA.SettingControllers

Set settingRepository1 = settingControllers1.Item("Interference")

long1 = settingRepository1.GetAttr("PreferredInterface")
'--------------------------------------------------
' Parameter 1 : (String) "PreferredInterface"
' Returned value : (Variant) (Long) 0
'--------------------------------------------------

Dim bSTR1
bSTR1 = ""
Dim bSTR2
bSTR2 = ""
Dim boolean1
settingRepository1.GetAttrInfo "PreferredInterface", bSTR1, bSTR2, boolean1
'--------------------------------------------------
' Parameter 1 : (String) "PreferredInterface"
' Parameter 2 : (String) "Default value"
' Parameter 3 : (String) "Unlocked"
' Parameter 4 : (Boolean) False
'--------------------------------------------------

long2 = settingRepository1.GetAttr("AutomaticMetricDisplay")
'--------------------------------------------------
' Parameter 1 : (String) "AutomaticMetricDisplay"
' Returned value : (Variant) (Long) 1
'--------------------------------------------------

Dim bSTR3
bSTR3 = ""
Dim bSTR4
bSTR4 = ""
Dim boolean2
settingRepository1.GetAttrInfo "AutomaticMetricDisplay", bSTR3, bSTR4, boolean2
'--------------------------------------------------
' Parameter 1 : (String) "AutomaticMetricDisplay"
' Parameter 2 : (String) "Default value"
' Parameter 3 : (String) "Unlocked"
' Parameter 4 : (Boolean) False
'--------------------------------------------------

long3 = settingRepository1.GetAttr("DisplayItfStoredResult")
'--------------------------------------------------
' Parameter 1 : (String) "DisplayItfStoredResult"
' Returned value : (Variant) (Long) 0
'--------------------------------------------------

Dim bSTR5
bSTR5 = ""
Dim bSTR6
bSTR6 = ""
Dim boolean3
settingRepository1.GetAttrInfo "DisplayItfStoredResult", bSTR5, bSTR6, boolean3
'--------------------------------------------------
' Parameter 1 : (String) "DisplayItfStoredResult"
' Parameter 2 : (String) "Default value"
' Parameter 3 : (String) "Unlocked"
' Parameter 4 : (Boolean) False
'--------------------------------------------------

long4 = settingRepository1.GetAttr("DisplayItfQuantifierClash")
'--------------------------------------------------
' Parameter 1 : (String) "DisplayItfQuantifierClash"
' Returned value : (Variant) (Long) 1
'--------------------------------------------------

Dim bSTR7
bSTR7 = ""
Dim bSTR8
bSTR8 = ""
Dim boolean4
settingRepository1.GetAttrInfo "DisplayItfQuantifierClash", bSTR7, bSTR8, boolean4
'--------------------------------------------------
' Parameter 1 : (String) "DisplayItfQuantifierClash"
' Parameter 2 : (String) "Default value"
' Parameter 3 : (String) "Unlocked"
' Parameter 4 : (Boolean) False
'--------------------------------------------------

long5 = settingRepository1.GetAttr("DisplayItfQuantifierClearance")
'--------------------------------------------------
' Parameter 1 : (String) "DisplayItfQuantifierClearance"
' Returned value : (Variant) (Long) 1
'--------------------------------------------------

Dim bSTR9
bSTR9 = ""
Dim bSTR10
bSTR10 = ""
Dim boolean5
settingRepository1.GetAttrInfo "DisplayItfQuantifierClearance", bSTR9, bSTR10, boolean5
'--------------------------------------------------
' Parameter 1 : (String) "DisplayItfQuantifierClearance"
' Parameter 2 : (String) "Default value"
' Parameter 3 : (String) "Unlocked"
' Parameter 4 : (Boolean) False
'--------------------------------------------------

long6 = settingRepository1.GetAttr("DisplayItfGeometryMode")
'--------------------------------------------------
' Parameter 1 : (String) "DisplayItfGeometryMode"
' Returned value : (Variant) (Long) 1
'--------------------------------------------------

Dim bSTR11
bSTR11 = ""
Dim bSTR12
bSTR12 = ""
Dim boolean6
settingRepository1.GetAttrInfo "DisplayItfGeometryMode", bSTR11, bSTR12, boolean6
'--------------------------------------------------
' Parameter 1 : (String) "DisplayItfGeometryMode"
' Parameter 2 : (String) "Default value"
' Parameter 3 : (String) "Unlocked"
' Parameter 4 : (Boolean) False
'--------------------------------------------------

long7 = settingRepository1.GetAttr("ColorITFParts")
'--------------------------------------------------
' Parameter 1 : (String) "ColorITFParts"
' Returned value : (Variant) (Long) 0
'--------------------------------------------------

Dim bSTR13
bSTR13 = ""
Dim bSTR14
bSTR14 = ""
Dim boolean7
settingRepository1.GetAttrInfo "ColorITFParts", bSTR13, bSTR14, boolean7
'--------------------------------------------------
' Parameter 1 : (String) "ColorITFParts"
' Parameter 2 : (String) "Default value"
' Parameter 3 : (String) "Unlocked"
' Parameter 4 : (Boolean) False
'--------------------------------------------------

Dim arrayOfVariantOfULong1
arrayOfVariantOfULong1 = settingRepository1.GetAttrArray("ColorInterferrringPart1")
'--------------------------------------------------
' Parameter 1 : (String) "ColorInterferrringPart1"
' Returned value : (Array) 
'    Array[0] : (Variant) (Unsigned Long) 0
'    Array[1] : (Variant) (Unsigned Long) 0
'    Array[2] : (Variant) (Unsigned Long) 255
'--------------------------------------------------

Dim bSTR15
bSTR15 = ""
Dim bSTR16
bSTR16 = ""
Dim boolean8
settingRepository1.GetAttrInfo "ColorInterferrringPart1", bSTR15, bSTR16, boolean8
'--------------------------------------------------
' Parameter 1 : (String) "ColorInterferrringPart1"
' Parameter 2 : (String) "Default value"
' Parameter 3 : (String) "Unlocked"
' Parameter 4 : (Boolean) False
'--------------------------------------------------

Dim arrayOfVariantOfULong2
arrayOfVariantOfULong2 = settingRepository1.GetAttrArray("ColorInterferrringPart2")
'--------------------------------------------------
' Parameter 1 : (String) "ColorInterferrringPart2"
' Returned value : (Array) 
'    Array[0] : (Variant) (Unsigned Long) 255
'    Array[1] : (Variant) (Unsigned Long) 255
'    Array[2] : (Variant) (Unsigned Long) 0
'--------------------------------------------------

Dim bSTR17
bSTR17 = ""
Dim bSTR18
bSTR18 = ""
Dim boolean9
settingRepository1.GetAttrInfo "ColorInterferrringPart2", bSTR17, bSTR18, boolean9
'--------------------------------------------------
' Parameter 1 : (String) "ColorInterferrringPart2"
' Parameter 2 : (String) "Default value"
' Parameter 3 : (String) "Unlocked"
' Parameter 4 : (Boolean) False
'--------------------------------------------------

Dim arrayOfVariantOfULong3
arrayOfVariantOfULong3 = settingRepository1.GetAttrArray("ColorInterferrringPartClash")
'--------------------------------------------------
' Parameter 1 : (String) "ColorInterferrringPartClash"
' Returned value : (Array) 
'    Array[0] : (Variant) (Unsigned Long) 255
'    Array[1] : (Variant) (Unsigned Long) 0
'    Array[2] : (Variant) (Unsigned Long) 0
'--------------------------------------------------

Dim bSTR19
bSTR19 = ""
Dim bSTR20
bSTR20 = ""
Dim boolean10
settingRepository1.GetAttrInfo "ColorInterferrringPartClash", bSTR19, bSTR20, boolean10
'--------------------------------------------------
' Parameter 1 : (String) "ColorInterferrringPartClash"
' Parameter 2 : (String) "Default value"
' Parameter 3 : (String) "Unlocked"
' Parameter 4 : (Boolean) False
'--------------------------------------------------

Dim arrayOfVariantOfULong4
arrayOfVariantOfULong4 = settingRepository1.GetAttrArray("ColorInterferrringPartContact")
'--------------------------------------------------
' Parameter 1 : (String) "ColorInterferrringPartContact"
' Returned value : (Array) 
'    Array[0] : (Variant) (Unsigned Long) 255
'    Array[1] : (Variant) (Unsigned Long) 165
'    Array[2] : (Variant) (Unsigned Long) 0
'--------------------------------------------------

Dim bSTR21
bSTR21 = ""
Dim bSTR22
bSTR22 = ""
Dim boolean11
settingRepository1.GetAttrInfo "ColorInterferrringPartContact", bSTR21, bSTR22, boolean11
'--------------------------------------------------
' Parameter 1 : (String) "ColorInterferrringPartContact"
' Parameter 2 : (String) "Default value"
' Parameter 3 : (String) "Unlocked"
' Parameter 4 : (Boolean) False
'--------------------------------------------------

Dim arrayOfVariantOfULong5
arrayOfVariantOfULong5 = settingRepository1.GetAttrArray("ColorInterferrringPartClear")
'--------------------------------------------------
' Parameter 1 : (String) "ColorInterferrringPartClear"
' Returned value : (Array) 
'    Array[0] : (Variant) (Unsigned Long) 0
'    Array[1] : (Variant) (Unsigned Long) 255
'    Array[2] : (Variant) (Unsigned Long) 0
'--------------------------------------------------

Dim bSTR23
bSTR23 = ""
Dim bSTR24
bSTR24 = ""
Dim boolean12
settingRepository1.GetAttrInfo "ColorInterferrringPartClear", bSTR23, bSTR24, boolean12
'--------------------------------------------------
' Parameter 1 : (String) "ColorInterferrringPartClear"
' Parameter 2 : (String) "Default value"
' Parameter 3 : (String) "Unlocked"
' Parameter 4 : (Boolean) False
'--------------------------------------------------

long8 = settingRepository1.GetAttr("ItfIcon")
'--------------------------------------------------
' Parameter 1 : (String) "ItfIcon"
' Returned value : (Variant) (Long) 0
'--------------------------------------------------

Dim bSTR25
bSTR25 = ""
Dim bSTR26
bSTR26 = ""
Dim boolean13
settingRepository1.GetAttrInfo "ItfIcon", bSTR25, bSTR26, boolean13
'--------------------------------------------------
' Parameter 1 : (String) "ItfIcon"
' Parameter 2 : (String) "Default value"
' Parameter 3 : (String) "Unlocked"
' Parameter 4 : (Boolean) False
'--------------------------------------------------

long9 = settingRepository1.GetAttr("CustomizeDisplay")
'--------------------------------------------------
' Parameter 1 : (String) "CustomizeDisplay"
' Returned value : (Variant) (Long) 0
'--------------------------------------------------

Dim bSTR27
bSTR27 = ""
Dim bSTR28
bSTR28 = ""
Dim boolean14
settingRepository1.GetAttrInfo "CustomizeDisplay", bSTR27, bSTR28, boolean14
'--------------------------------------------------
' Parameter 1 : (String) "CustomizeDisplay"
' Parameter 2 : (String) "Default value"
' Parameter 3 : (String) "Unlocked"
' Parameter 4 : (Boolean) False
'--------------------------------------------------

long10 = settingRepository1.GetAttr("ToolTip")
'--------------------------------------------------
' Parameter 1 : (String) "ToolTip"
' Returned value : (Variant) (Long) 0
'--------------------------------------------------

Dim bSTR29
bSTR29 = ""
Dim bSTR30
bSTR30 = ""
Dim boolean15
settingRepository1.GetAttrInfo "ToolTip", bSTR29, bSTR30, boolean15
'--------------------------------------------------
' Parameter 1 : (String) "ToolTip"
' Parameter 2 : (String) "Default value"
' Parameter 3 : (String) "Unlocked"
' Parameter 4 : (Boolean) False
'--------------------------------------------------

long11 = settingRepository1.GetAttr("DisplayItfGeometryClash")
'--------------------------------------------------
' Parameter 1 : (String) "DisplayItfGeometryClash"
' Returned value : (Variant) (Long) 1
'--------------------------------------------------

Dim bSTR31
bSTR31 = ""
Dim bSTR32
bSTR32 = ""
Dim boolean16
settingRepository1.GetAttrInfo "DisplayItfGeometryClash", bSTR31, bSTR32, boolean16
'--------------------------------------------------
' Parameter 1 : (String) "DisplayItfGeometryClash"
' Parameter 2 : (String) "Default value"
' Parameter 3 : (String) "Unlocked"
' Parameter 4 : (Boolean) False
'--------------------------------------------------

long12 = settingRepository1.GetAttr("DisplayItfGeometryContact")
'--------------------------------------------------
' Parameter 1 : (String) "DisplayItfGeometryContact"
' Returned value : (Variant) (Long) 1
'--------------------------------------------------

Dim bSTR33
bSTR33 = ""
Dim bSTR34
bSTR34 = ""
Dim boolean17
settingRepository1.GetAttrInfo "DisplayItfGeometryContact", bSTR33, bSTR34, boolean17
'--------------------------------------------------
' Parameter 1 : (String) "DisplayItfGeometryContact"
' Parameter 2 : (String) "Default value"
' Parameter 3 : (String) "Unlocked"
' Parameter 4 : (Boolean) False
'--------------------------------------------------

long13 = settingRepository1.GetAttr("DisplayItfGeometryClearance")
'--------------------------------------------------
' Parameter 1 : (String) "DisplayItfGeometryClearance"
' Returned value : (Variant) (Long) 1
'--------------------------------------------------

Dim bSTR35
bSTR35 = ""
Dim bSTR36
bSTR36 = ""
Dim boolean18
settingRepository1.GetAttrInfo "DisplayItfGeometryClearance", bSTR35, bSTR36, boolean18
'--------------------------------------------------
' Parameter 1 : (String) "DisplayItfGeometryClearance"
' Parameter 2 : (String) "Default value"
' Parameter 3 : (String) "Unlocked"
' Parameter 4 : (Boolean) False
'--------------------------------------------------

double1 = settingRepository1.GetAttr("ClearanceAreaRediscretization")
'--------------------------------------------------
' Parameter 1 : (String) "ClearanceAreaRediscretization"
' Returned value : (Variant) (Double) 10.000000
'--------------------------------------------------

Dim bSTR37
bSTR37 = ""
Dim bSTR38
bSTR38 = ""
Dim boolean19
settingRepository1.GetAttrInfo "ClearanceAreaRediscretization", bSTR37, bSTR38, boolean19
'--------------------------------------------------
' Parameter 1 : (String) "ClearanceAreaRediscretization"
' Parameter 2 : (String) "Default value"
' Parameter 3 : (String) "Unlocked"
' Parameter 4 : (Boolean) False
'--------------------------------------------------

long14 = settingRepository1.GetAttr("ItfPartsTransparency")
'--------------------------------------------------
' Parameter 1 : (String) "ItfPartsTransparency"
' Returned value : (Variant) (Long) 128
'--------------------------------------------------

Dim bSTR39
bSTR39 = ""
Dim bSTR40
bSTR40 = ""
Dim boolean20
settingRepository1.GetAttrInfo "ItfPartsTransparency", bSTR39, bSTR40, boolean20
'--------------------------------------------------
' Parameter 1 : (String) "ItfPartsTransparency"
' Parameter 2 : (String) "Default value"
' Parameter 3 : (String) "Unlocked"
' Parameter 4 : (Boolean) False
'--------------------------------------------------

End Sub
