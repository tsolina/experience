Language="VBSCRIPT"

Sub CATMain()

Set settingControllers1 = CATIA.SettingControllers

Set settingRepository1 = settingControllers1.Item("VPMNavigator")

long1 = settingRepository1.GetAttr("UwpActivation")
'--------------------------------------------------
' Parameter 1 : (String) "UwpActivation"
' Returned value : (Variant) (Long) 0
'--------------------------------------------------

Dim bSTR1
bSTR1 = ""
Dim bSTR2
bSTR2 = ""
Dim boolean1
settingRepository1.GetAttrInfo "UwpActivation", bSTR1, bSTR2, boolean1
'--------------------------------------------------
' Parameter 1 : (String) "UwpActivation"
' Parameter 2 : (String) "Default value"
' Parameter 3 : (String) "Unlocked"
' Parameter 4 : (Boolean) False
'--------------------------------------------------

long2 = settingRepository1.GetAttr("FastenerInUWPLoading")
'--------------------------------------------------
' Parameter 1 : (String) "FastenerInUWPLoading"
' Returned value : (Variant) (Long) 0
'--------------------------------------------------

Dim bSTR3
bSTR3 = ""
Dim bSTR4
bSTR4 = ""
Dim boolean2
settingRepository1.GetAttrInfo "FastenerInUWPLoading", bSTR3, bSTR4, boolean2
'--------------------------------------------------
' Parameter 1 : (String) "FastenerInUWPLoading"
' Parameter 2 : (String) "Default value"
' Parameter 3 : (String) "Unlocked"
' Parameter 4 : (Boolean) False
'--------------------------------------------------

long3 = settingRepository1.GetAttr("LoadThumbnailsWithFilteredExpandInUWP")
'--------------------------------------------------
' Parameter 1 : (String) "LoadThumbnailsWithFilteredExpandInUWP"
' Returned value : (Variant) (Long) 0
'--------------------------------------------------

Dim bSTR5
bSTR5 = ""
Dim bSTR6
bSTR6 = ""
Dim boolean3
settingRepository1.GetAttrInfo "LoadThumbnailsWithFilteredExpandInUWP", bSTR5, bSTR6, boolean3
'--------------------------------------------------
' Parameter 1 : (String) "LoadThumbnailsWithFilteredExpandInUWP"
' Parameter 2 : (String) "Default value"
' Parameter 3 : (String) "Unlocked"
' Parameter 4 : (Boolean) False
'--------------------------------------------------

End Sub
