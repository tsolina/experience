Language="VBSCRIPT"

Sub CATMain()

Set settingControllers1 = CATIA.SettingControllers

Set settingRepository1 = settingControllers1.Item("RenderingOptionsSettings")

boolean1 = settingRepository1.GetAttr("ViewpointModeActivated")
'--------------------------------------------------
' Parameter 1 : (String) "ViewpointModeActivated"
' Returned value : (Variant) (Boolean) False
'--------------------------------------------------

Dim bSTR1
bSTR1 = ""
Dim bSTR2
bSTR2 = ""
Dim boolean2
settingRepository1.GetAttrInfo "ViewpointModeActivated", bSTR1, bSTR2, boolean2
'--------------------------------------------------
' Parameter 1 : (String) "ViewpointModeActivated"
' Parameter 2 : (String) "Default value"
' Parameter 3 : (String) "Unlocked"
' Parameter 4 : (Boolean) False
'--------------------------------------------------

boolean3 = settingRepository1.GetAttr("MaterialViewMode")
'--------------------------------------------------
' Parameter 1 : (String) "MaterialViewMode"
' Returned value : (Variant) (Boolean) False
'--------------------------------------------------

Dim bSTR3
bSTR3 = ""
Dim bSTR4
bSTR4 = ""
Dim boolean4
settingRepository1.GetAttrInfo "MaterialViewMode", bSTR3, bSTR4, boolean4
'--------------------------------------------------
' Parameter 1 : (String) "MaterialViewMode"
' Parameter 2 : (String) "Default value"
' Parameter 3 : (String) "Unlocked"
' Parameter 4 : (Boolean) False
'--------------------------------------------------

long1 = settingRepository1.GetAttr("SubstanceEngineType")
'--------------------------------------------------
' Parameter 1 : (String) "SubstanceEngineType"
' Returned value : (Variant) (Long) 0
'--------------------------------------------------

Dim bSTR5
bSTR5 = ""
Dim bSTR6
bSTR6 = ""
Dim boolean5
settingRepository1.GetAttrInfo "SubstanceEngineType", bSTR5, bSTR6, boolean5
'--------------------------------------------------
' Parameter 1 : (String) "SubstanceEngineType"
' Parameter 2 : (String) "Default value"
' Parameter 3 : (String) "Unlocked"
' Parameter 4 : (Boolean) False
'--------------------------------------------------

long2 = settingRepository1.GetAttr("LightCreationMode")
'--------------------------------------------------
' Parameter 1 : (String) "LightCreationMode"
' Returned value : (Variant) (Long) 0
'--------------------------------------------------

Dim bSTR7
bSTR7 = ""
Dim bSTR8
bSTR8 = ""
Dim boolean6
settingRepository1.GetAttrInfo "LightCreationMode", bSTR7, bSTR8, boolean6
'--------------------------------------------------
' Parameter 1 : (String) "LightCreationMode"
' Parameter 2 : (String) "Default value"
' Parameter 3 : (String) "Unlocked"
' Parameter 4 : (Boolean) False
'--------------------------------------------------

long3 = settingRepository1.GetAttr("LightCreationAxis")
'--------------------------------------------------
' Parameter 1 : (String) "LightCreationAxis"
' Returned value : (Variant) (Long) 2
'--------------------------------------------------

Dim bSTR9
bSTR9 = ""
Dim bSTR10
bSTR10 = ""
Dim boolean7
settingRepository1.GetAttrInfo "LightCreationAxis", bSTR9, bSTR10, boolean7
'--------------------------------------------------
' Parameter 1 : (String) "LightCreationAxis"
' Parameter 2 : (String) "Default value"
' Parameter 3 : (String) "Unlocked"
' Parameter 4 : (Boolean) False
'--------------------------------------------------

long4 = settingRepository1.GetAttr("ViewpointMode")
'--------------------------------------------------
' Parameter 1 : (String) "ViewpointMode"
' Returned value : (Variant) (Long) 1
'--------------------------------------------------

Dim bSTR11
bSTR11 = ""
Dim bSTR12
bSTR12 = ""
Dim boolean8
settingRepository1.GetAttrInfo "ViewpointMode", bSTR11, bSTR12, boolean8
'--------------------------------------------------
' Parameter 1 : (String) "ViewpointMode"
' Parameter 2 : (String) "Default value"
' Parameter 3 : (String) "Unlocked"
' Parameter 4 : (Boolean) False
'--------------------------------------------------

End Sub
