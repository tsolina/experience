Language="VBSCRIPT"

Sub CATMain()

Set settingControllers1 = CATIA.SettingControllers

Set settingRepository1 = settingControllers1.Item("PLMEditorColor")

uLong1 = settingRepository1.GetAttr("RFLPGnrlBalloonDisplayOptions")
'--------------------------------------------------
' Parameter 1 : (String) "RFLPGnrlBalloonDisplayOptions"
' Returned value : (Variant) (Unsigned Long) 0
'--------------------------------------------------

Dim bSTR1
bSTR1 = ""
Dim bSTR2
bSTR2 = ""
Dim boolean1
settingRepository1.GetAttrInfo "RFLPGnrlBalloonDisplayOptions", bSTR1, bSTR2, boolean1
'--------------------------------------------------
' Parameter 1 : (String) "RFLPGnrlBalloonDisplayOptions"
' Parameter 2 : (String) "Default value"
' Parameter 3 : (String) "Unlocked"
' Parameter 4 : (Boolean) False
'--------------------------------------------------

uLong2 = settingRepository1.GetAttr("RFLPGnrlInsertCmdOptionsUseImmersiveChooser")
'--------------------------------------------------
' Parameter 1 : (String) "RFLPGnrlInsertCmdOptionsUseImmersiveChooser"
' Returned value : (Variant) (Unsigned Long) 1
'--------------------------------------------------

Dim bSTR3
bSTR3 = ""
Dim bSTR4
bSTR4 = ""
Dim boolean2
settingRepository1.GetAttrInfo "RFLPGnrlInsertCmdOptionsUseImmersiveChooser", bSTR3, bSTR4, boolean2
'--------------------------------------------------
' Parameter 1 : (String) "RFLPGnrlInsertCmdOptionsUseImmersiveChooser"
' Parameter 2 : (String) "Default value"
' Parameter 3 : (String) "Unlocked"
' Parameter 4 : (Boolean) False
'--------------------------------------------------

uLong3 = settingRepository1.GetAttr("RFLPGnrlDisplayNameDisplayIdentifierOption")
'--------------------------------------------------
' Parameter 1 : (String) "RFLPGnrlDisplayNameDisplayIdentifierOption"
' Returned value : (Variant) (Unsigned Long) 1
'--------------------------------------------------

Dim bSTR5
bSTR5 = ""
Dim bSTR6
bSTR6 = ""
Dim boolean3
settingRepository1.GetAttrInfo "RFLPGnrlDisplayNameDisplayIdentifierOption", bSTR5, bSTR6, boolean3
'--------------------------------------------------
' Parameter 1 : (String) "RFLPGnrlDisplayNameDisplayIdentifierOption"
' Parameter 2 : (String) "Default value"
' Parameter 3 : (String) "Unlocked"
' Parameter 4 : (Boolean) False
'--------------------------------------------------

uLong4 = settingRepository1.GetAttr("RFLPGnrlTextDispIn2DGraphWrapText")
'--------------------------------------------------
' Parameter 1 : (String) "RFLPGnrlTextDispIn2DGraphWrapText"
' Returned value : (Variant) (Unsigned Long) 0
'--------------------------------------------------

Dim bSTR7
bSTR7 = ""
Dim bSTR8
bSTR8 = ""
Dim boolean4
settingRepository1.GetAttrInfo "RFLPGnrlTextDispIn2DGraphWrapText", bSTR7, bSTR8, boolean4
'--------------------------------------------------
' Parameter 1 : (String) "RFLPGnrlTextDispIn2DGraphWrapText"
' Parameter 2 : (String) "Default value"
' Parameter 3 : (String) "Unlocked"
' Parameter 4 : (Boolean) False
'--------------------------------------------------

uLong5 = settingRepository1.GetAttr("RFLPGnrlConnectionNetworkCmdOptionsCleanUp")
'--------------------------------------------------
' Parameter 1 : (String) "RFLPGnrlConnectionNetworkCmdOptionsCleanUp"
' Returned value : (Variant) (Unsigned Long) 1
'--------------------------------------------------

Dim bSTR9
bSTR9 = ""
Dim bSTR10
bSTR10 = ""
Dim boolean5
settingRepository1.GetAttrInfo "RFLPGnrlConnectionNetworkCmdOptionsCleanUp", bSTR9, bSTR10, boolean5
'--------------------------------------------------
' Parameter 1 : (String) "RFLPGnrlConnectionNetworkCmdOptionsCleanUp"
' Parameter 2 : (String) "Default value"
' Parameter 3 : (String) "Unlocked"
' Parameter 4 : (Boolean) False
'--------------------------------------------------

uLong6 = settingRepository1.GetAttr("RFLPGnrlAgilityCmdOptionsAgility")
'--------------------------------------------------
' Parameter 1 : (String) "RFLPGnrlAgilityCmdOptionsAgility"
' Returned value : (Variant) (Unsigned Long) 1
'--------------------------------------------------

Dim bSTR11
bSTR11 = ""
Dim bSTR12
bSTR12 = ""
Dim boolean6
settingRepository1.GetAttrInfo "RFLPGnrlAgilityCmdOptionsAgility", bSTR11, bSTR12, boolean6
'--------------------------------------------------
' Parameter 1 : (String) "RFLPGnrlAgilityCmdOptionsAgility"
' Parameter 2 : (String) "Default value"
' Parameter 3 : (String) "Unlocked"
' Parameter 4 : (Boolean) False
'--------------------------------------------------

uLong7 = settingRepository1.GetAttr("RFLPGnrlAgilityCmdOptionsCleanUp")
'--------------------------------------------------
' Parameter 1 : (String) "RFLPGnrlAgilityCmdOptionsCleanUp"
' Returned value : (Variant) (Unsigned Long) 1
'--------------------------------------------------

Dim bSTR13
bSTR13 = ""
Dim bSTR14
bSTR14 = ""
Dim boolean7
settingRepository1.GetAttrInfo "RFLPGnrlAgilityCmdOptionsCleanUp", bSTR13, bSTR14, boolean7
'--------------------------------------------------
' Parameter 1 : (String) "RFLPGnrlAgilityCmdOptionsCleanUp"
' Parameter 2 : (String) "Default value"
' Parameter 3 : (String) "Unlocked"
' Parameter 4 : (Boolean) False
'--------------------------------------------------

uLong8 = settingRepository1.GetAttr("RFLPGnrlILOptionsUseAdvCmd")
'--------------------------------------------------
' Parameter 1 : (String) "RFLPGnrlILOptionsUseAdvCmd"
' Returned value : (Variant) (Unsigned Long) 1
'--------------------------------------------------

Dim bSTR15
bSTR15 = ""
Dim bSTR16
bSTR16 = ""
Dim boolean8
settingRepository1.GetAttrInfo "RFLPGnrlILOptionsUseAdvCmd", bSTR15, bSTR16, boolean8
'--------------------------------------------------
' Parameter 1 : (String) "RFLPGnrlILOptionsUseAdvCmd"
' Parameter 2 : (String) "Default value"
' Parameter 3 : (String) "Unlocked"
' Parameter 4 : (Boolean) False
'--------------------------------------------------

uLong9 = settingRepository1.GetAttr("RFLPGnrlPortSystemTypeOptionsUsePortSysTypeAssocn")
'--------------------------------------------------
' Parameter 1 : (String) "RFLPGnrlPortSystemTypeOptionsUsePortSysTypeAssocn"
' Returned value : (Variant) (Unsigned Long) 1
'--------------------------------------------------

Dim bSTR17
bSTR17 = ""
Dim bSTR18
bSTR18 = ""
Dim boolean9
settingRepository1.GetAttrInfo "RFLPGnrlPortSystemTypeOptionsUsePortSysTypeAssocn", bSTR17, bSTR18, boolean9
'--------------------------------------------------
' Parameter 1 : (String) "RFLPGnrlPortSystemTypeOptionsUsePortSysTypeAssocn"
' Parameter 2 : (String) "Default value"
' Parameter 3 : (String) "Unlocked"
' Parameter 4 : (Boolean) False
'--------------------------------------------------

uLong10 = settingRepository1.GetAttr("RFLPGnrlReUseITFOptions")
'--------------------------------------------------
' Parameter 1 : (String) "RFLPGnrlReUseITFOptions"
' Returned value : (Variant) (Unsigned Long) 1
'--------------------------------------------------

Dim bSTR19
bSTR19 = ""
Dim bSTR20
bSTR20 = ""
Dim boolean10
settingRepository1.GetAttrInfo "RFLPGnrlReUseITFOptions", bSTR19, bSTR20, boolean10
'--------------------------------------------------
' Parameter 1 : (String) "RFLPGnrlReUseITFOptions"
' Parameter 2 : (String) "Default value"
' Parameter 3 : (String) "Unlocked"
' Parameter 4 : (Boolean) False
'--------------------------------------------------

uLong11 = settingRepository1.GetAttr("RFLPGnrlFLFlowTypeOptionsAutoGenerateIdentifier")
'--------------------------------------------------
' Parameter 1 : (String) "RFLPGnrlFLFlowTypeOptionsAutoGenerateIdentifier"
' Returned value : (Variant) (Unsigned Long) 1
'--------------------------------------------------

Dim bSTR21
bSTR21 = ""
Dim bSTR22
bSTR22 = ""
Dim boolean11
settingRepository1.GetAttrInfo "RFLPGnrlFLFlowTypeOptionsAutoGenerateIdentifier", bSTR21, bSTR22, boolean11
'--------------------------------------------------
' Parameter 1 : (String) "RFLPGnrlFLFlowTypeOptionsAutoGenerateIdentifier"
' Parameter 2 : (String) "Default value"
' Parameter 3 : (String) "Unlocked"
' Parameter 4 : (Boolean) False
'--------------------------------------------------

uLong12 = settingRepository1.GetAttr("RFLPGnrlFLFlowTypeOptionsHideAutoGenerateIdentifier")
'--------------------------------------------------
' Parameter 1 : (String) "RFLPGnrlFLFlowTypeOptionsHideAutoGenerateIdentifier"
' Returned value : (Variant) (Unsigned Long) 0
'--------------------------------------------------

Dim bSTR23
bSTR23 = ""
Dim bSTR24
bSTR24 = ""
Dim boolean12
settingRepository1.GetAttrInfo "RFLPGnrlFLFlowTypeOptionsHideAutoGenerateIdentifier", bSTR23, bSTR24, boolean12
'--------------------------------------------------
' Parameter 1 : (String) "RFLPGnrlFLFlowTypeOptionsHideAutoGenerateIdentifier"
' Parameter 2 : (String) "Default value"
' Parameter 3 : (String) "Unlocked"
' Parameter 4 : (Boolean) False
'--------------------------------------------------

uLong13 = settingRepository1.GetAttr("RFLPGnrlAutoConnectProcessSubFlowConnection")
'--------------------------------------------------
' Parameter 1 : (String) "RFLPGnrlAutoConnectProcessSubFlowConnection"
' Returned value : (Variant) (Unsigned Long) 1
'--------------------------------------------------

Dim bSTR25
bSTR25 = ""
Dim bSTR26
bSTR26 = ""
Dim boolean13
settingRepository1.GetAttrInfo "RFLPGnrlAutoConnectProcessSubFlowConnection", bSTR25, bSTR26, boolean13
'--------------------------------------------------
' Parameter 1 : (String) "RFLPGnrlAutoConnectProcessSubFlowConnection"
' Parameter 2 : (String) "Default value"
' Parameter 3 : (String) "Unlocked"
' Parameter 4 : (Boolean) False
'--------------------------------------------------

uLong14 = settingRepository1.GetAttr("RFLPGnrlFLDefaultCnxOptions")
'--------------------------------------------------
' Parameter 1 : (String) "RFLPGnrlFLDefaultCnxOptions"
' Returned value : (Variant) (Unsigned Long) 0
'--------------------------------------------------

Dim bSTR27
bSTR27 = ""
Dim bSTR28
bSTR28 = ""
Dim boolean14
settingRepository1.GetAttrInfo "RFLPGnrlFLDefaultCnxOptions", bSTR27, bSTR28, boolean14
'--------------------------------------------------
' Parameter 1 : (String) "RFLPGnrlFLDefaultCnxOptions"
' Parameter 2 : (String) "Default value"
' Parameter 3 : (String) "Unlocked"
' Parameter 4 : (Boolean) False
'--------------------------------------------------

uLong15 = settingRepository1.GetAttr("RFLPGnrlCenterTreeatSelectionCenterTreeonSelectedObjects")
'--------------------------------------------------
' Parameter 1 : (String) "RFLPGnrlCenterTreeatSelectionCenterTreeonSelectedObjects"
' Returned value : (Variant) (Unsigned Long) 0
'--------------------------------------------------

Dim bSTR29
bSTR29 = ""
Dim bSTR30
bSTR30 = ""
Dim boolean15
settingRepository1.GetAttrInfo "RFLPGnrlCenterTreeatSelectionCenterTreeonSelectedObjects", bSTR29, bSTR30, boolean15
'--------------------------------------------------
' Parameter 1 : (String) "RFLPGnrlCenterTreeatSelectionCenterTreeonSelectedObjects"
' Parameter 2 : (String) "Default value"
' Parameter 3 : (String) "Unlocked"
' Parameter 4 : (Boolean) False
'--------------------------------------------------

uLong16 = settingRepository1.GetAttr("FctDisplayNameAssociationOptions")
'--------------------------------------------------
' Parameter 1 : (String) "FctDisplayNameAssociationOptions"
' Returned value : (Variant) (Unsigned Long) 2
'--------------------------------------------------

Dim bSTR31
bSTR31 = ""
Dim bSTR32
bSTR32 = ""
Dim boolean16
settingRepository1.GetAttrInfo "FctDisplayNameAssociationOptions", bSTR31, bSTR32, boolean16
'--------------------------------------------------
' Parameter 1 : (String) "FctDisplayNameAssociationOptions"
' Parameter 2 : (String) "Default value"
' Parameter 3 : (String) "Unlocked"
' Parameter 4 : (Boolean) False
'--------------------------------------------------

uLong17 = settingRepository1.GetAttr("FctDisplayNameRelationOptions")
'--------------------------------------------------
' Parameter 1 : (String) "FctDisplayNameRelationOptions"
' Returned value : (Variant) (Unsigned Long) 2
'--------------------------------------------------

Dim bSTR33
bSTR33 = ""
Dim bSTR34
bSTR34 = ""
Dim boolean17
settingRepository1.GetAttrInfo "FctDisplayNameRelationOptions", bSTR33, bSTR34, boolean17
'--------------------------------------------------
' Parameter 1 : (String) "FctDisplayNameRelationOptions"
' Parameter 2 : (String) "Default value"
' Parameter 3 : (String) "Unlocked"
' Parameter 4 : (Boolean) False
'--------------------------------------------------

uLong18 = settingRepository1.GetAttr("LogDisplayNameAssociationOptions")
'--------------------------------------------------
' Parameter 1 : (String) "LogDisplayNameAssociationOptions"
' Returned value : (Variant) (Unsigned Long) 2
'--------------------------------------------------

Dim bSTR35
bSTR35 = ""
Dim bSTR36
bSTR36 = ""
Dim boolean18
settingRepository1.GetAttrInfo "LogDisplayNameAssociationOptions", bSTR35, bSTR36, boolean18
'--------------------------------------------------
' Parameter 1 : (String) "LogDisplayNameAssociationOptions"
' Parameter 2 : (String) "Default value"
' Parameter 3 : (String) "Unlocked"
' Parameter 4 : (Boolean) False
'--------------------------------------------------

uLong19 = settingRepository1.GetAttr("LogDisplayNameRelationOptions")
'--------------------------------------------------
' Parameter 1 : (String) "LogDisplayNameRelationOptions"
' Returned value : (Variant) (Unsigned Long) 2
'--------------------------------------------------

Dim bSTR37
bSTR37 = ""
Dim bSTR38
bSTR38 = ""
Dim boolean19
settingRepository1.GetAttrInfo "LogDisplayNameRelationOptions", bSTR37, bSTR38, boolean19
'--------------------------------------------------
' Parameter 1 : (String) "LogDisplayNameRelationOptions"
' Parameter 2 : (String) "Default value"
' Parameter 3 : (String) "Unlocked"
' Parameter 4 : (Boolean) False
'--------------------------------------------------

uLong20 = settingRepository1.GetAttr("RFLPGnrlILOptionsContextOption")
'--------------------------------------------------
' Parameter 1 : (String) "RFLPGnrlILOptionsContextOption"
' Returned value : (Variant) (Unsigned Long) 0
'--------------------------------------------------

Dim bSTR39
bSTR39 = ""
Dim bSTR40
bSTR40 = ""
Dim boolean20
settingRepository1.GetAttrInfo "RFLPGnrlILOptionsContextOption", bSTR39, bSTR40, boolean20
'--------------------------------------------------
' Parameter 1 : (String) "RFLPGnrlILOptionsContextOption"
' Parameter 2 : (String) "Default value"
' Parameter 3 : (String) "Unlocked"
' Parameter 4 : (Boolean) False
'--------------------------------------------------

uLong21 = settingRepository1.GetAttr("RFLPGnrlFLITFOptions")
'--------------------------------------------------
' Parameter 1 : (String) "RFLPGnrlFLITFOptions"
' Returned value : (Variant) (Unsigned Long) 1
'--------------------------------------------------

Dim bSTR41
bSTR41 = ""
Dim bSTR42
bSTR42 = ""
Dim boolean21
settingRepository1.GetAttrInfo "RFLPGnrlFLITFOptions", bSTR41, bSTR42, boolean21
'--------------------------------------------------
' Parameter 1 : (String) "RFLPGnrlFLITFOptions"
' Parameter 2 : (String) "Default value"
' Parameter 3 : (String) "Unlocked"
' Parameter 4 : (Boolean) False
'--------------------------------------------------

End Sub
