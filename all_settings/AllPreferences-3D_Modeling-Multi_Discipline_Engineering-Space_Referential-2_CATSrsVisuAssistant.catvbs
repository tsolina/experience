Language="VBSCRIPT"

Sub CATMain()

Set settingControllers1 = CATIA.SettingControllers

Set settingRepository1 = settingControllers1.Item("CATSrsVisuAssistantPage")

boolean1 = settingRepository1.GetAttr("NbOfNodeOnDummy")
'--------------------------------------------------
' Parameter 1 : (String) "NbOfNodeOnDummy"
' Returned value : (Variant) (Boolean) False
'--------------------------------------------------

Dim bSTR1
bSTR1 = ""
Dim bSTR2
bSTR2 = ""
Dim boolean2
settingRepository1.GetAttrInfo "NbOfNodeOnDummy", bSTR1, bSTR2, boolean2
'--------------------------------------------------
' Parameter 1 : (String) "NbOfNodeOnDummy"
' Parameter 2 : (String) "Default value"
' Parameter 3 : (String) "Unlocked"
' Parameter 4 : (Boolean) False
'--------------------------------------------------

boolean3 = settingRepository1.GetAttr("DeepSearch")
'--------------------------------------------------
' Parameter 1 : (String) "DeepSearch"
' Returned value : (Variant) (Boolean) False
'--------------------------------------------------

Dim bSTR3
bSTR3 = ""
Dim bSTR4
bSTR4 = ""
Dim boolean4
settingRepository1.GetAttrInfo "DeepSearch", bSTR3, bSTR4, boolean4
'--------------------------------------------------
' Parameter 1 : (String) "DeepSearch"
' Parameter 2 : (String) "Default value"
' Parameter 3 : (String) "Unlocked"
' Parameter 4 : (Boolean) False
'--------------------------------------------------

boolean5 = settingRepository1.GetAttr("ApplySettingAutomatically")
'--------------------------------------------------
' Parameter 1 : (String) "ApplySettingAutomatically"
' Returned value : (Variant) (Boolean) False
'--------------------------------------------------

Dim bSTR5
bSTR5 = ""
Dim bSTR6
bSTR6 = ""
Dim boolean6
settingRepository1.GetAttrInfo "ApplySettingAutomatically", bSTR5, bSTR6, boolean6
'--------------------------------------------------
' Parameter 1 : (String) "ApplySettingAutomatically"
' Parameter 2 : (String) "Default value"
' Parameter 3 : (String) "Unlocked"
' Parameter 4 : (Boolean) False
'--------------------------------------------------

boolean7 = settingRepository1.GetAttr("SketchOrientation")
'--------------------------------------------------
' Parameter 1 : (String) "SketchOrientation"
' Returned value : (Variant) (Boolean) False
'--------------------------------------------------

Dim bSTR7
bSTR7 = ""
Dim bSTR8
bSTR8 = ""
Dim boolean8
settingRepository1.GetAttrInfo "SketchOrientation", bSTR7, bSTR8, boolean8
'--------------------------------------------------
' Parameter 1 : (String) "SketchOrientation"
' Parameter 2 : (String) "Default value"
' Parameter 3 : (String) "Unlocked"
' Parameter 4 : (Boolean) False
'--------------------------------------------------

End Sub
