Language="VBSCRIPT"

Sub CATMain()

Set settingControllers1 = CATIA.SettingControllers

Set settingRepository1 = settingControllers1.Item("DmtDocumentGeneral")

boolean1 = settingRepository1.GetAttr("DocumentExpandMode")
'--------------------------------------------------
' Parameter 1 : (String) "DocumentExpandMode"
' Returned value : (Variant) (Boolean) True
'--------------------------------------------------

Dim bSTR1
bSTR1 = ""
Dim bSTR2
bSTR2 = ""
Dim boolean2
settingRepository1.GetAttrInfo "DocumentExpandMode", bSTR1, bSTR2, boolean2
'--------------------------------------------------
' Parameter 1 : (String) "DocumentExpandMode"
' Parameter 2 : (String) "Default value"
' Parameter 3 : (String) "Unlocked"
' Parameter 4 : (Boolean) False
'--------------------------------------------------

boolean3 = settingRepository1.GetAttr("AlwaysAskWhileDnDFile")
'--------------------------------------------------
' Parameter 1 : (String) "AlwaysAskWhileDnDFile"
' Returned value : (Variant) (Boolean) True
'--------------------------------------------------

Dim bSTR3
bSTR3 = ""
Dim bSTR4
bSTR4 = ""
Dim boolean4
settingRepository1.GetAttrInfo "AlwaysAskWhileDnDFile", bSTR3, bSTR4, boolean4
'--------------------------------------------------
' Parameter 1 : (String) "AlwaysAskWhileDnDFile"
' Parameter 2 : (String) "Default value"
' Parameter 3 : (String) "Unlocked"
' Parameter 4 : (Boolean) False
'--------------------------------------------------

bSTR5 = settingRepository1.GetAttr("PreSelectedDocType")
'--------------------------------------------------
' Parameter 1 : (String) "PreSelectedDocType"
' Returned value : (Variant) (String) "Document Customized"
'--------------------------------------------------

Dim bSTR6
bSTR6 = ""
Dim bSTR7
bSTR7 = ""
Dim boolean5
settingRepository1.GetAttrInfo "PreSelectedDocType", bSTR6, bSTR7, boolean5
'--------------------------------------------------
' Parameter 1 : (String) "PreSelectedDocType"
' Parameter 2 : (String) "Default value"
' Parameter 3 : (String) "Unlocked"
' Parameter 4 : (Boolean) False
'--------------------------------------------------

End Sub
