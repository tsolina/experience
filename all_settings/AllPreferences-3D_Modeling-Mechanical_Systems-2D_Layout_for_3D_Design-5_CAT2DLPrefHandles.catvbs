Language="VBSCRIPT"

Sub CATMain()

Set settingControllers1 = CATIA.SettingControllers

Set settingRepository1 = settingControllers1.Item("CAT2DLToolsOptions")

long1 = settingRepository1.GetAttr("ManipTransparencySetting")
'--------------------------------------------------
' Parameter 1 : (String) "ManipTransparencySetting"
' Returned value : (Variant) (Long) 80
'--------------------------------------------------

Dim bSTR1
bSTR1 = ""
Dim bSTR2
bSTR2 = ""
Dim boolean1
settingRepository1.GetAttrInfo "ManipTransparencySetting", bSTR1, bSTR2, boolean1
'--------------------------------------------------
' Parameter 1 : (String) "ManipTransparencySetting"
' Parameter 2 : (String) "Default value"
' Parameter 3 : (String) "Unlocked"
' Parameter 4 : (Boolean) False
'--------------------------------------------------

double1 = settingRepository1.GetAttr("ManipRefSize")
'--------------------------------------------------
' Parameter 1 : (String) "ManipRefSize"
' Returned value : (Variant) (Double) 3.000000
'--------------------------------------------------

Dim bSTR3
bSTR3 = ""
Dim bSTR4
bSTR4 = ""
Dim boolean2
settingRepository1.GetAttrInfo "ManipRefSize", bSTR3, bSTR4, boolean2
'--------------------------------------------------
' Parameter 1 : (String) "ManipRefSize"
' Parameter 2 : (String) "Default value"
' Parameter 3 : (String) "Unlocked"
' Parameter 4 : (Boolean) False
'--------------------------------------------------

boolean3 = settingRepository1.GetAttr("ManipZoom")
'--------------------------------------------------
' Parameter 1 : (String) "ManipZoom"
' Returned value : (Variant) (Boolean) False
'--------------------------------------------------

Dim bSTR5
bSTR5 = ""
Dim bSTR6
bSTR6 = ""
Dim boolean4
settingRepository1.GetAttrInfo "ManipZoom", bSTR5, bSTR6, boolean4
'--------------------------------------------------
' Parameter 1 : (String) "ManipZoom"
' Parameter 2 : (String) "Default value"
' Parameter 3 : (String) "Unlocked"
' Parameter 4 : (Boolean) False
'--------------------------------------------------

boolean5 = settingRepository1.GetAttr("SnapToPaperGridSetting")
'--------------------------------------------------
' Parameter 1 : (String) "SnapToPaperGridSetting"
' Returned value : (Variant) (Boolean) True
'--------------------------------------------------

Dim bSTR7
bSTR7 = ""
Dim bSTR8
bSTR8 = ""
Dim boolean6
settingRepository1.GetAttrInfo "SnapToPaperGridSetting", bSTR7, bSTR8, boolean6
'--------------------------------------------------
' Parameter 1 : (String) "SnapToPaperGridSetting"
' Parameter 2 : (String) "Default value"
' Parameter 3 : (String) "Unlocked"
' Parameter 4 : (Boolean) False
'--------------------------------------------------

boolean7 = settingRepository1.GetAttr("RotSnapAuto")
'--------------------------------------------------
' Parameter 1 : (String) "RotSnapAuto"
' Returned value : (Variant) (Boolean) True
'--------------------------------------------------

Dim bSTR9
bSTR9 = ""
Dim bSTR10
bSTR10 = ""
Dim boolean8
settingRepository1.GetAttrInfo "RotSnapAuto", bSTR9, bSTR10, boolean8
'--------------------------------------------------
' Parameter 1 : (String) "RotSnapAuto"
' Parameter 2 : (String) "Default value"
' Parameter 3 : (String) "Unlocked"
' Parameter 4 : (Boolean) False
'--------------------------------------------------

boolean9 = settingRepository1.GetAttr("SnapOnDirectionSetting")
'--------------------------------------------------
' Parameter 1 : (String) "SnapOnDirectionSetting"
' Returned value : (Variant) (Boolean) True
'--------------------------------------------------

Dim bSTR11
bSTR11 = ""
Dim bSTR12
bSTR12 = ""
Dim boolean10
settingRepository1.GetAttrInfo "SnapOnDirectionSetting", bSTR11, bSTR12, boolean10
'--------------------------------------------------
' Parameter 1 : (String) "SnapOnDirectionSetting"
' Parameter 2 : (String) "Default value"
' Parameter 3 : (String) "Unlocked"
' Parameter 4 : (Boolean) False
'--------------------------------------------------

double2 = settingRepository1.GetAttr("PaperGridSpacingSetting")
'--------------------------------------------------
' Parameter 1 : (String) "PaperGridSpacingSetting"
' Returned value : (Variant) (Double) 1.000000
'--------------------------------------------------

Dim bSTR13
bSTR13 = ""
Dim bSTR14
bSTR14 = ""
Dim boolean11
settingRepository1.GetAttrInfo "PaperGridSpacingSetting", bSTR13, bSTR14, boolean11
'--------------------------------------------------
' Parameter 1 : (String) "PaperGridSpacingSetting"
' Parameter 2 : (String) "Default value"
' Parameter 3 : (String) "Unlocked"
' Parameter 4 : (Boolean) False
'--------------------------------------------------

double3 = settingRepository1.GetAttr("RotSnapAngle")
'--------------------------------------------------
' Parameter 1 : (String) "RotSnapAngle"
' Returned value : (Variant) (Double) 90.000000
'--------------------------------------------------

Dim bSTR15
bSTR15 = ""
Dim bSTR16
bSTR16 = ""
Dim boolean12
settingRepository1.GetAttrInfo "RotSnapAngle", bSTR15, bSTR16, boolean12
'--------------------------------------------------
' Parameter 1 : (String) "RotSnapAngle"
' Parameter 2 : (String) "Default value"
' Parameter 3 : (String) "Unlocked"
' Parameter 4 : (Boolean) False
'--------------------------------------------------

boolean13 = settingRepository1.GetAttr("ORunCre")
'--------------------------------------------------
' Parameter 1 : (String) "ORunCre"
' Returned value : (Variant) (Boolean) False
'--------------------------------------------------

Dim bSTR17
bSTR17 = ""
Dim bSTR18
bSTR18 = ""
Dim boolean14
settingRepository1.GetAttrInfo "ORunCre", bSTR17, bSTR18, boolean14
'--------------------------------------------------
' Parameter 1 : (String) "ORunCre"
' Parameter 2 : (String) "Default value"
' Parameter 3 : (String) "Unlocked"
' Parameter 4 : (Boolean) False
'--------------------------------------------------

boolean15 = settingRepository1.GetAttr("ORunMod")
'--------------------------------------------------
' Parameter 1 : (String) "ORunMod"
' Returned value : (Variant) (Boolean) False
'--------------------------------------------------

Dim bSTR19
bSTR19 = ""
Dim bSTR20
bSTR20 = ""
Dim boolean16
settingRepository1.GetAttrInfo "ORunMod", bSTR19, bSTR20, boolean16
'--------------------------------------------------
' Parameter 1 : (String) "ORunMod"
' Parameter 2 : (String) "Default value"
' Parameter 3 : (String) "Unlocked"
' Parameter 4 : (Boolean) False
'--------------------------------------------------

boolean17 = settingRepository1.GetAttr("BlankingCre")
'--------------------------------------------------
' Parameter 1 : (String) "BlankingCre"
' Returned value : (Variant) (Boolean) False
'--------------------------------------------------

Dim bSTR21
bSTR21 = ""
Dim bSTR22
bSTR22 = ""
Dim boolean18
settingRepository1.GetAttrInfo "BlankingCre", bSTR21, bSTR22, boolean18
'--------------------------------------------------
' Parameter 1 : (String) "BlankingCre"
' Parameter 2 : (String) "Default value"
' Parameter 3 : (String) "Unlocked"
' Parameter 4 : (Boolean) False
'--------------------------------------------------

boolean19 = settingRepository1.GetAttr("BlankingMod")
'--------------------------------------------------
' Parameter 1 : (String) "BlankingMod"
' Returned value : (Variant) (Boolean) True
'--------------------------------------------------

Dim bSTR23
bSTR23 = ""
Dim bSTR24
bSTR24 = ""
Dim boolean20
settingRepository1.GetAttrInfo "BlankingMod", bSTR23, bSTR24, boolean20
'--------------------------------------------------
' Parameter 1 : (String) "BlankingMod"
' Parameter 2 : (String) "Default value"
' Parameter 3 : (String) "Unlocked"
' Parameter 4 : (Boolean) False
'--------------------------------------------------

boolean21 = settingRepository1.GetAttr("ChangeSymbolCre")
'--------------------------------------------------
' Parameter 1 : (String) "ChangeSymbolCre"
' Returned value : (Variant) (Boolean) False
'--------------------------------------------------

Dim bSTR25
bSTR25 = ""
Dim bSTR26
bSTR26 = ""
Dim boolean22
settingRepository1.GetAttrInfo "ChangeSymbolCre", bSTR25, bSTR26, boolean22
'--------------------------------------------------
' Parameter 1 : (String) "ChangeSymbolCre"
' Parameter 2 : (String) "Default value"
' Parameter 3 : (String) "Unlocked"
' Parameter 4 : (Boolean) False
'--------------------------------------------------

boolean23 = settingRepository1.GetAttr("ChangeSymbolMod")
'--------------------------------------------------
' Parameter 1 : (String) "ChangeSymbolMod"
' Returned value : (Variant) (Boolean) False
'--------------------------------------------------

Dim bSTR27
bSTR27 = ""
Dim bSTR28
bSTR28 = ""
Dim boolean24
settingRepository1.GetAttrInfo "ChangeSymbolMod", bSTR27, bSTR28, boolean24
'--------------------------------------------------
' Parameter 1 : (String) "ChangeSymbolMod"
' Parameter 2 : (String) "Default value"
' Parameter 3 : (String) "Unlocked"
' Parameter 4 : (Boolean) False
'--------------------------------------------------

boolean25 = settingRepository1.GetAttr("BeforeCre")
'--------------------------------------------------
' Parameter 1 : (String) "BeforeCre"
' Returned value : (Variant) (Boolean) False
'--------------------------------------------------

Dim bSTR29
bSTR29 = ""
Dim bSTR30
bSTR30 = ""
Dim boolean26
settingRepository1.GetAttrInfo "BeforeCre", bSTR29, bSTR30, boolean26
'--------------------------------------------------
' Parameter 1 : (String) "BeforeCre"
' Parameter 2 : (String) "Default value"
' Parameter 3 : (String) "Unlocked"
' Parameter 4 : (Boolean) False
'--------------------------------------------------

boolean27 = settingRepository1.GetAttr("BeforeMod")
'--------------------------------------------------
' Parameter 1 : (String) "BeforeMod"
' Returned value : (Variant) (Boolean) False
'--------------------------------------------------

Dim bSTR31
bSTR31 = ""
Dim bSTR32
bSTR32 = ""
Dim boolean28
settingRepository1.GetAttrInfo "BeforeMod", bSTR31, bSTR32, boolean28
'--------------------------------------------------
' Parameter 1 : (String) "BeforeMod"
' Parameter 2 : (String) "Default value"
' Parameter 3 : (String) "Unlocked"
' Parameter 4 : (Boolean) False
'--------------------------------------------------

boolean29 = settingRepository1.GetAttr("AfterCre")
'--------------------------------------------------
' Parameter 1 : (String) "AfterCre"
' Returned value : (Variant) (Boolean) False
'--------------------------------------------------

Dim bSTR33
bSTR33 = ""
Dim bSTR34
bSTR34 = ""
Dim boolean30
settingRepository1.GetAttrInfo "AfterCre", bSTR33, bSTR34, boolean30
'--------------------------------------------------
' Parameter 1 : (String) "AfterCre"
' Parameter 2 : (String) "Default value"
' Parameter 3 : (String) "Unlocked"
' Parameter 4 : (Boolean) False
'--------------------------------------------------

boolean31 = settingRepository1.GetAttr("AfterMod")
'--------------------------------------------------
' Parameter 1 : (String) "AfterMod"
' Returned value : (Variant) (Boolean) False
'--------------------------------------------------

Dim bSTR35
bSTR35 = ""
Dim bSTR36
bSTR36 = ""
Dim boolean32
settingRepository1.GetAttrInfo "AfterMod", bSTR35, bSTR36, boolean32
'--------------------------------------------------
' Parameter 1 : (String) "AfterMod"
' Parameter 2 : (String) "Default value"
' Parameter 3 : (String) "Unlocked"
' Parameter 4 : (Boolean) False
'--------------------------------------------------

boolean33 = settingRepository1.GetAttr("MoveValueCre")
'--------------------------------------------------
' Parameter 1 : (String) "MoveValueCre"
' Returned value : (Variant) (Boolean) False
'--------------------------------------------------

Dim bSTR37
bSTR37 = ""
Dim bSTR38
bSTR38 = ""
Dim boolean34
settingRepository1.GetAttrInfo "MoveValueCre", bSTR37, bSTR38, boolean34
'--------------------------------------------------
' Parameter 1 : (String) "MoveValueCre"
' Parameter 2 : (String) "Default value"
' Parameter 3 : (String) "Unlocked"
' Parameter 4 : (Boolean) False
'--------------------------------------------------

boolean35 = settingRepository1.GetAttr("MoveValueMod")
'--------------------------------------------------
' Parameter 1 : (String) "MoveValueMod"
' Returned value : (Variant) (Boolean) False
'--------------------------------------------------

Dim bSTR39
bSTR39 = ""
Dim bSTR40
bSTR40 = ""
Dim boolean36
settingRepository1.GetAttrInfo "MoveValueMod", bSTR39, bSTR40, boolean36
'--------------------------------------------------
' Parameter 1 : (String) "MoveValueMod"
' Parameter 2 : (String) "Default value"
' Parameter 3 : (String) "Unlocked"
' Parameter 4 : (Boolean) False
'--------------------------------------------------

boolean37 = settingRepository1.GetAttr("MoveDimLineCre")
'--------------------------------------------------
' Parameter 1 : (String) "MoveDimLineCre"
' Returned value : (Variant) (Boolean) False
'--------------------------------------------------

Dim bSTR41
bSTR41 = ""
Dim bSTR42
bSTR42 = ""
Dim boolean38
settingRepository1.GetAttrInfo "MoveDimLineCre", bSTR41, bSTR42, boolean38
'--------------------------------------------------
' Parameter 1 : (String) "MoveDimLineCre"
' Parameter 2 : (String) "Default value"
' Parameter 3 : (String) "Unlocked"
' Parameter 4 : (Boolean) False
'--------------------------------------------------

boolean39 = settingRepository1.GetAttr("MoveDimLineMod")
'--------------------------------------------------
' Parameter 1 : (String) "MoveDimLineMod"
' Returned value : (Variant) (Boolean) False
'--------------------------------------------------

Dim bSTR43
bSTR43 = ""
Dim bSTR44
bSTR44 = ""
Dim boolean40
settingRepository1.GetAttrInfo "MoveDimLineMod", bSTR43, bSTR44, boolean40
'--------------------------------------------------
' Parameter 1 : (String) "MoveDimLineMod"
' Parameter 2 : (String) "Default value"
' Parameter 3 : (String) "Unlocked"
' Parameter 4 : (Boolean) False
'--------------------------------------------------

boolean41 = settingRepository1.GetAttr("Move2dPartCre")
'--------------------------------------------------
' Parameter 1 : (String) "Move2dPartCre"
' Returned value : (Variant) (Boolean) False
'--------------------------------------------------

Dim bSTR45
bSTR45 = ""
Dim bSTR46
bSTR46 = ""
Dim boolean42
settingRepository1.GetAttrInfo "Move2dPartCre", bSTR45, bSTR46, boolean42
'--------------------------------------------------
' Parameter 1 : (String) "Move2dPartCre"
' Parameter 2 : (String) "Default value"
' Parameter 3 : (String) "Unlocked"
' Parameter 4 : (Boolean) False
'--------------------------------------------------

boolean43 = settingRepository1.GetAttr("Move2dPartMod")
'--------------------------------------------------
' Parameter 1 : (String) "Move2dPartMod"
' Returned value : (Variant) (Boolean) False
'--------------------------------------------------

Dim bSTR47
bSTR47 = ""
Dim bSTR48
bSTR48 = ""
Dim boolean44
settingRepository1.GetAttrInfo "Move2dPartMod", bSTR47, bSTR48, boolean44
'--------------------------------------------------
' Parameter 1 : (String) "Move2dPartMod"
' Parameter 2 : (String) "Default value"
' Parameter 3 : (String) "Unlocked"
' Parameter 4 : (Boolean) False
'--------------------------------------------------

boolean45 = settingRepository1.GetAttr("MoveLeaderCre")
'--------------------------------------------------
' Parameter 1 : (String) "MoveLeaderCre"
' Returned value : (Variant) (Boolean) False
'--------------------------------------------------

Dim bSTR49
bSTR49 = ""
Dim bSTR50
bSTR50 = ""
Dim boolean46
settingRepository1.GetAttrInfo "MoveLeaderCre", bSTR49, bSTR50, boolean46
'--------------------------------------------------
' Parameter 1 : (String) "MoveLeaderCre"
' Parameter 2 : (String) "Default value"
' Parameter 3 : (String) "Unlocked"
' Parameter 4 : (Boolean) False
'--------------------------------------------------

boolean47 = settingRepository1.GetAttr("MoveLeaderMod")
'--------------------------------------------------
' Parameter 1 : (String) "MoveLeaderMod"
' Returned value : (Variant) (Boolean) True
'--------------------------------------------------

Dim bSTR51
bSTR51 = ""
Dim bSTR52
bSTR52 = ""
Dim boolean48
settingRepository1.GetAttrInfo "MoveLeaderMod", bSTR51, bSTR52, boolean48
'--------------------------------------------------
' Parameter 1 : (String) "MoveLeaderMod"
' Parameter 2 : (String) "Default value"
' Parameter 3 : (String) "Unlocked"
' Parameter 4 : (Boolean) False
'--------------------------------------------------

boolean49 = settingRepository1.GetAttr("ManipRotateAnnotCre")
'--------------------------------------------------
' Parameter 1 : (String) "ManipRotateAnnotCre"
' Returned value : (Variant) (Boolean) True
'--------------------------------------------------

Dim bSTR53
bSTR53 = ""
Dim bSTR54
bSTR54 = ""
Dim boolean50
settingRepository1.GetAttrInfo "ManipRotateAnnotCre", bSTR53, bSTR54, boolean50
'--------------------------------------------------
' Parameter 1 : (String) "ManipRotateAnnotCre"
' Parameter 2 : (String) "Default value"
' Parameter 3 : (String) "Unlocked"
' Parameter 4 : (Boolean) False
'--------------------------------------------------

boolean51 = settingRepository1.GetAttr("ManipRotateAnnotMod")
'--------------------------------------------------
' Parameter 1 : (String) "ManipRotateAnnotMod"
' Returned value : (Variant) (Boolean) True
'--------------------------------------------------

Dim bSTR55
bSTR55 = ""
Dim bSTR56
bSTR56 = ""
Dim boolean52
settingRepository1.GetAttrInfo "ManipRotateAnnotMod", bSTR55, bSTR56, boolean52
'--------------------------------------------------
' Parameter 1 : (String) "ManipRotateAnnotMod"
' Parameter 2 : (String) "Default value"
' Parameter 3 : (String) "Unlocked"
' Parameter 4 : (Boolean) False
'--------------------------------------------------

boolean53 = settingRepository1.GetAttr("ManipTranslationAnnotCre")
'--------------------------------------------------
' Parameter 1 : (String) "ManipTranslationAnnotCre"
' Returned value : (Variant) (Boolean) True
'--------------------------------------------------

Dim bSTR57
bSTR57 = ""
Dim bSTR58
bSTR58 = ""
Dim boolean54
settingRepository1.GetAttrInfo "ManipTranslationAnnotCre", bSTR57, bSTR58, boolean54
'--------------------------------------------------
' Parameter 1 : (String) "ManipTranslationAnnotCre"
' Parameter 2 : (String) "Default value"
' Parameter 3 : (String) "Unlocked"
' Parameter 4 : (Boolean) False
'--------------------------------------------------

boolean55 = settingRepository1.GetAttr("ManipTranslationAnnotMod")
'--------------------------------------------------
' Parameter 1 : (String) "ManipTranslationAnnotMod"
' Returned value : (Variant) (Boolean) True
'--------------------------------------------------

Dim bSTR59
bSTR59 = ""
Dim bSTR60
bSTR60 = ""
Dim boolean56
settingRepository1.GetAttrInfo "ManipTranslationAnnotMod", bSTR59, bSTR60, boolean56
'--------------------------------------------------
' Parameter 1 : (String) "ManipTranslationAnnotMod"
' Parameter 2 : (String) "Default value"
' Parameter 3 : (String) "Unlocked"
' Parameter 4 : (Boolean) False
'--------------------------------------------------

boolean57 = settingRepository1.GetAttr("ManipResizeAnnotCre")
'--------------------------------------------------
' Parameter 1 : (String) "ManipResizeAnnotCre"
' Returned value : (Variant) (Boolean) True
'--------------------------------------------------

Dim bSTR61
bSTR61 = ""
Dim bSTR62
bSTR62 = ""
Dim boolean58
settingRepository1.GetAttrInfo "ManipResizeAnnotCre", bSTR61, bSTR62, boolean58
'--------------------------------------------------
' Parameter 1 : (String) "ManipResizeAnnotCre"
' Parameter 2 : (String) "Default value"
' Parameter 3 : (String) "Unlocked"
' Parameter 4 : (Boolean) False
'--------------------------------------------------

boolean59 = settingRepository1.GetAttr("ManipResizeAnnotMod")
'--------------------------------------------------
' Parameter 1 : (String) "ManipResizeAnnotMod"
' Returned value : (Variant) (Boolean) True
'--------------------------------------------------

Dim bSTR63
bSTR63 = ""
Dim bSTR64
bSTR64 = ""
Dim boolean60
settingRepository1.GetAttrInfo "ManipResizeAnnotMod", bSTR63, bSTR64, boolean60
'--------------------------------------------------
' Parameter 1 : (String) "ManipResizeAnnotMod"
' Parameter 2 : (String) "Default value"
' Parameter 3 : (String) "Unlocked"
' Parameter 4 : (Boolean) False
'--------------------------------------------------

boolean61 = settingRepository1.GetAttr("ManipMoveValueAnnotCre")
'--------------------------------------------------
' Parameter 1 : (String) "ManipMoveValueAnnotCre"
' Returned value : (Variant) (Boolean) True
'--------------------------------------------------

Dim bSTR65
bSTR65 = ""
Dim bSTR66
bSTR66 = ""
Dim boolean62
settingRepository1.GetAttrInfo "ManipMoveValueAnnotCre", bSTR65, bSTR66, boolean62
'--------------------------------------------------
' Parameter 1 : (String) "ManipMoveValueAnnotCre"
' Parameter 2 : (String) "Default value"
' Parameter 3 : (String) "Unlocked"
' Parameter 4 : (Boolean) False
'--------------------------------------------------

boolean63 = settingRepository1.GetAttr("ManipMoveValueAnnotMod")
'--------------------------------------------------
' Parameter 1 : (String) "ManipMoveValueAnnotMod"
' Returned value : (Variant) (Boolean) False
'--------------------------------------------------

Dim bSTR67
bSTR67 = ""
Dim bSTR68
bSTR68 = ""
Dim boolean64
settingRepository1.GetAttrInfo "ManipMoveValueAnnotMod", bSTR67, bSTR68, boolean64
'--------------------------------------------------
' Parameter 1 : (String) "ManipMoveValueAnnotMod"
' Parameter 2 : (String) "Default value"
' Parameter 3 : (String) "Unlocked"
' Parameter 4 : (Boolean) False
'--------------------------------------------------

boolean65 = settingRepository1.GetAttr("ManipTranslationLeaderCre")
'--------------------------------------------------
' Parameter 1 : (String) "ManipTranslationLeaderCre"
' Returned value : (Variant) (Boolean) True
'--------------------------------------------------

Dim bSTR69
bSTR69 = ""
Dim bSTR70
bSTR70 = ""
Dim boolean66
settingRepository1.GetAttrInfo "ManipTranslationLeaderCre", bSTR69, bSTR70, boolean66
'--------------------------------------------------
' Parameter 1 : (String) "ManipTranslationLeaderCre"
' Parameter 2 : (String) "Default value"
' Parameter 3 : (String) "Unlocked"
' Parameter 4 : (Boolean) False
'--------------------------------------------------

boolean67 = settingRepository1.GetAttr("ManipTranslationLeaderMod")
'--------------------------------------------------
' Parameter 1 : (String) "ManipTranslationLeaderMod"
' Returned value : (Variant) (Boolean) False
'--------------------------------------------------

Dim bSTR71
bSTR71 = ""
Dim bSTR72
bSTR72 = ""
Dim boolean68
settingRepository1.GetAttrInfo "ManipTranslationLeaderMod", bSTR71, bSTR72, boolean68
'--------------------------------------------------
' Parameter 1 : (String) "ManipTranslationLeaderMod"
' Parameter 2 : (String) "Default value"
' Parameter 3 : (String) "Unlocked"
' Parameter 4 : (Boolean) False
'--------------------------------------------------

boolean69 = settingRepository1.GetAttr("ManipMoveLeaderAnchorCre")
'--------------------------------------------------
' Parameter 1 : (String) "ManipMoveLeaderAnchorCre"
' Returned value : (Variant) (Boolean) True
'--------------------------------------------------

Dim bSTR73
bSTR73 = ""
Dim bSTR74
bSTR74 = ""
Dim boolean70
settingRepository1.GetAttrInfo "ManipMoveLeaderAnchorCre", bSTR73, bSTR74, boolean70
'--------------------------------------------------
' Parameter 1 : (String) "ManipMoveLeaderAnchorCre"
' Parameter 2 : (String) "Default value"
' Parameter 3 : (String) "Unlocked"
' Parameter 4 : (Boolean) False
'--------------------------------------------------

boolean71 = settingRepository1.GetAttr("ManipMoveLeaderAnchorMod")
'--------------------------------------------------
' Parameter 1 : (String) "ManipMoveLeaderAnchorMod"
' Returned value : (Variant) (Boolean) False
'--------------------------------------------------

Dim bSTR75
bSTR75 = ""
Dim bSTR76
bSTR76 = ""
Dim boolean72
settingRepository1.GetAttrInfo "ManipMoveLeaderAnchorMod", bSTR75, bSTR76, boolean72
'--------------------------------------------------
' Parameter 1 : (String) "ManipMoveLeaderAnchorMod"
' Parameter 2 : (String) "Default value"
' Parameter 3 : (String) "Unlocked"
' Parameter 4 : (Boolean) False
'--------------------------------------------------

boolean73 = settingRepository1.GetAttr("ManipMoveLeaderCre")
'--------------------------------------------------
' Parameter 1 : (String) "ManipMoveLeaderCre"
' Returned value : (Variant) (Boolean) True
'--------------------------------------------------

Dim bSTR77
bSTR77 = ""
Dim bSTR78
bSTR78 = ""
Dim boolean74
settingRepository1.GetAttrInfo "ManipMoveLeaderCre", bSTR77, bSTR78, boolean74
'--------------------------------------------------
' Parameter 1 : (String) "ManipMoveLeaderCre"
' Parameter 2 : (String) "Default value"
' Parameter 3 : (String) "Unlocked"
' Parameter 4 : (Boolean) False
'--------------------------------------------------

boolean75 = settingRepository1.GetAttr("ManipMoveLeaderMod")
'--------------------------------------------------
' Parameter 1 : (String) "ManipMoveLeaderMod"
' Returned value : (Variant) (Boolean) False
'--------------------------------------------------

Dim bSTR79
bSTR79 = ""
Dim bSTR80
bSTR80 = ""
Dim boolean76
settingRepository1.GetAttrInfo "ManipMoveLeaderMod", bSTR79, bSTR80, boolean76
'--------------------------------------------------
' Parameter 1 : (String) "ManipMoveLeaderMod"
' Parameter 2 : (String) "Default value"
' Parameter 3 : (String) "Unlocked"
' Parameter 4 : (Boolean) False
'--------------------------------------------------

boolean77 = settingRepository1.GetAttr("ManipMovableDatumCre")
'--------------------------------------------------
' Parameter 1 : (String) "ManipMovableDatumCre"
' Returned value : (Variant) (Boolean) True
'--------------------------------------------------

Dim bSTR81
bSTR81 = ""
Dim bSTR82
bSTR82 = ""
Dim boolean78
settingRepository1.GetAttrInfo "ManipMovableDatumCre", bSTR81, bSTR82, boolean78
'--------------------------------------------------
' Parameter 1 : (String) "ManipMovableDatumCre"
' Parameter 2 : (String) "Default value"
' Parameter 3 : (String) "Unlocked"
' Parameter 4 : (Boolean) False
'--------------------------------------------------

boolean79 = settingRepository1.GetAttr("ManipMovableDatumMod")
'--------------------------------------------------
' Parameter 1 : (String) "ManipMovableDatumMod"
' Returned value : (Variant) (Boolean) True
'--------------------------------------------------

Dim bSTR83
bSTR83 = ""
Dim bSTR84
bSTR84 = ""
Dim boolean80
settingRepository1.GetAttrInfo "ManipMovableDatumMod", bSTR83, bSTR84, boolean80
'--------------------------------------------------
' Parameter 1 : (String) "ManipMovableDatumMod"
' Parameter 2 : (String) "Default value"
' Parameter 3 : (String) "Unlocked"
' Parameter 4 : (Boolean) False
'--------------------------------------------------

boolean81 = settingRepository1.GetAttr("ManipInvertSurfaceTextureCre")
'--------------------------------------------------
' Parameter 1 : (String) "ManipInvertSurfaceTextureCre"
' Returned value : (Variant) (Boolean) True
'--------------------------------------------------

Dim bSTR85
bSTR85 = ""
Dim bSTR86
bSTR86 = ""
Dim boolean82
settingRepository1.GetAttrInfo "ManipInvertSurfaceTextureCre", bSTR85, bSTR86, boolean82
'--------------------------------------------------
' Parameter 1 : (String) "ManipInvertSurfaceTextureCre"
' Parameter 2 : (String) "Default value"
' Parameter 3 : (String) "Unlocked"
' Parameter 4 : (Boolean) False
'--------------------------------------------------

boolean83 = settingRepository1.GetAttr("ManipInvertSurfaceTextureMod")
'--------------------------------------------------
' Parameter 1 : (String) "ManipInvertSurfaceTextureMod"
' Returned value : (Variant) (Boolean) True
'--------------------------------------------------

Dim bSTR87
bSTR87 = ""
Dim bSTR88
bSTR88 = ""
Dim boolean84
settingRepository1.GetAttrInfo "ManipInvertSurfaceTextureMod", bSTR87, bSTR88, boolean84
'--------------------------------------------------
' Parameter 1 : (String) "ManipInvertSurfaceTextureMod"
' Parameter 2 : (String) "Default value"
' Parameter 3 : (String) "Unlocked"
' Parameter 4 : (Boolean) False
'--------------------------------------------------

End Sub
