Language="VBSCRIPT"

Sub CATMain()

Set settingControllers1 = CATIA.SettingControllers

Set settingRepository1 = settingControllers1.Item("L3dPipeDesignCriteria")

long1 = settingRepository1.GetAttr("L3dFBDIOfRunToCheck")
'--------------------------------------------------
' Parameter 1 : (String) "L3dFBDIOfRunToCheck"
' Returned value : (Variant) (Long) 0
'--------------------------------------------------

Dim bSTR1
bSTR1 = ""
Dim bSTR2
bSTR2 = ""
Dim boolean1
settingRepository1.GetAttrInfo "L3dFBDIOfRunToCheck", bSTR1, bSTR2, boolean1
'--------------------------------------------------
' Parameter 1 : (String) "L3dFBDIOfRunToCheck"
' Parameter 2 : (String) "Default value"
' Parameter 3 : (String) "Unlocked"
' Parameter 4 : (Boolean) False
'--------------------------------------------------

long2 = settingRepository1.GetAttr("L3dFBDIObjectTypeCreation")
'--------------------------------------------------
' Parameter 1 : (String) "L3dFBDIObjectTypeCreation"
' Returned value : (Variant) (Long) 0
'--------------------------------------------------

Dim bSTR3
bSTR3 = ""
Dim bSTR4
bSTR4 = ""
Dim boolean2
settingRepository1.GetAttrInfo "L3dFBDIObjectTypeCreation", bSTR3, bSTR4, boolean2
'--------------------------------------------------
' Parameter 1 : (String) "L3dFBDIObjectTypeCreation"
' Parameter 2 : (String) "Default value"
' Parameter 3 : (String) "Unlocked"
' Parameter 4 : (Boolean) False
'--------------------------------------------------

End Sub
