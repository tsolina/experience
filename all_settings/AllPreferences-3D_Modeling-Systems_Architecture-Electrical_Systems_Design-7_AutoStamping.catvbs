Language="VBSCRIPT"

Sub CATMain()

Set settingControllers1 = CATIA.SettingControllers

Set settingRepository1 = settingControllers1.Item("ELEditorToolsOptions")

uLong1 = settingRepository1.GetAttr("SchStampingChkButton")
'--------------------------------------------------
' Parameter 1 : (String) "SchStampingChkButton"
' Returned value : (Variant) (Unsigned Long) 1
'--------------------------------------------------

Dim bSTR1
bSTR1 = ""
Dim bSTR2
bSTR2 = ""
Dim boolean1
settingRepository1.GetAttrInfo "SchStampingChkButton", bSTR1, bSTR2, boolean1
'--------------------------------------------------
' Parameter 1 : (String) "SchStampingChkButton"
' Parameter 2 : (String) "Default value"
' Parameter 3 : (String) "Unlocked"
' Parameter 4 : (Boolean) False
'--------------------------------------------------

End Sub
