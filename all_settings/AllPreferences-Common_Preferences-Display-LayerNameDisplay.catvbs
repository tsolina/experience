Language="VBSCRIPT"

Sub CATMain()

Set settingControllers1 = CATIA.SettingControllers

Set settingRepository1 = settingControllers1.Item("LayerNameDisplay")

long1 = settingRepository1.GetAttr("ApplyFilterMode")
'--------------------------------------------------
' Parameter 1 : (String) "ApplyFilterMode"
' Returned value : (Variant) (Long) 0
'--------------------------------------------------

Dim bSTR1
bSTR1 = ""
Dim bSTR2
bSTR2 = ""
Dim boolean1
settingRepository1.GetAttrInfo "ApplyFilterMode", bSTR1, bSTR2, boolean1
'--------------------------------------------------
' Parameter 1 : (String) "ApplyFilterMode"
' Parameter 2 : (String) "Default value"
' Parameter 3 : (String) "Unlocked"
' Parameter 4 : (Boolean) False
'--------------------------------------------------

End Sub
