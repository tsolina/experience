Language="VBSCRIPT"

Sub CATMain()

Set settingControllers1 = CATIA.SettingControllers

Set settingRepository1 = settingControllers1.Item("DELMfgContextBuilderSettings")

long1 = settingRepository1.GetAttr("SpreadsheetLayout")
'--------------------------------------------------
' Parameter 1 : (String) "SpreadsheetLayout"
' Returned value : (Variant) (Long) 2
'--------------------------------------------------

Dim bSTR1
bSTR1 = ""
Dim bSTR2
bSTR2 = ""
Dim boolean1
settingRepository1.GetAttrInfo "SpreadsheetLayout", bSTR1, bSTR2, boolean1
'--------------------------------------------------
' Parameter 1 : (String) "SpreadsheetLayout"
' Parameter 2 : (String) "Default value"
' Parameter 3 : (String) "Unlocked"
' Parameter 4 : (Boolean) False
'--------------------------------------------------

End Sub
