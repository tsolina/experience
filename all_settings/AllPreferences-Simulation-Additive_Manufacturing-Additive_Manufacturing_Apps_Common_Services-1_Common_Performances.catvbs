Language="VBSCRIPT"

Sub CATMain()

Set settingControllers1 = CATIA.SettingControllers

Set settingRepository1 = settingControllers1.Item("NCMfgDisplay")

bSTR1 = settingRepository1.GetAttr("ButtonOptimizePerformance")
'--------------------------------------------------
' Parameter 1 : (String) "ButtonOptimizePerformance"
' Returned value : (Variant) (String) ""
'--------------------------------------------------

Dim bSTR2
bSTR2 = ""
Dim bSTR3
bSTR3 = ""
Dim boolean1
settingRepository1.GetAttrInfo "ButtonOptimizePerformance", bSTR2, bSTR3, boolean1
'--------------------------------------------------
' Parameter 1 : (String) "ButtonOptimizePerformance"
' Parameter 2 : (String) "Default value"
' Parameter 3 : (String) "Unlocked"
' Parameter 4 : (Boolean) False
'--------------------------------------------------

boolean2 = settingRepository1.GetAttr("AutoUpdate")
'--------------------------------------------------
' Parameter 1 : (String) "AutoUpdate"
' Returned value : (Variant) (Boolean) False
'--------------------------------------------------

Dim bSTR4
bSTR4 = ""
Dim bSTR5
bSTR5 = ""
Dim boolean3
settingRepository1.GetAttrInfo "AutoUpdate", bSTR4, bSTR5, boolean3
'--------------------------------------------------
' Parameter 1 : (String) "AutoUpdate"
' Parameter 2 : (String) "Default value"
' Parameter 3 : (String) "Unlocked"
' Parameter 4 : (Boolean) False
'--------------------------------------------------

boolean4 = settingRepository1.GetAttr("TransitionPathDisplay")
'--------------------------------------------------
' Parameter 1 : (String) "TransitionPathDisplay"
' Returned value : (Variant) (Boolean) False
'--------------------------------------------------

Dim bSTR6
bSTR6 = ""
Dim bSTR7
bSTR7 = ""
Dim boolean5
settingRepository1.GetAttrInfo "TransitionPathDisplay", bSTR6, bSTR7, boolean5
'--------------------------------------------------
' Parameter 1 : (String) "TransitionPathDisplay"
' Parameter 2 : (String) "Default value"
' Parameter 3 : (String) "Unlocked"
' Parameter 4 : (Boolean) False
'--------------------------------------------------

boolean6 = settingRepository1.GetAttr("RunMfgAssistant")
'--------------------------------------------------
' Parameter 1 : (String) "RunMfgAssistant"
' Returned value : (Variant) (Boolean) True
'--------------------------------------------------

Dim bSTR8
bSTR8 = ""
Dim bSTR9
bSTR9 = ""
Dim boolean7
settingRepository1.GetAttrInfo "RunMfgAssistant", bSTR8, bSTR9, boolean7
'--------------------------------------------------
' Parameter 1 : (String) "RunMfgAssistant"
' Parameter 2 : (String) "Default value"
' Parameter 3 : (String) "Unlocked"
' Parameter 4 : (Boolean) False
'--------------------------------------------------

boolean8 = settingRepository1.GetAttr("ShowOnlyCurrentMachine")
'--------------------------------------------------
' Parameter 1 : (String) "ShowOnlyCurrentMachine"
' Returned value : (Variant) (Boolean) False
'--------------------------------------------------

Dim bSTR10
bSTR10 = ""
Dim bSTR11
bSTR11 = ""
Dim boolean9
settingRepository1.GetAttrInfo "ShowOnlyCurrentMachine", bSTR10, bSTR11, boolean9
'--------------------------------------------------
' Parameter 1 : (String) "ShowOnlyCurrentMachine"
' Parameter 2 : (String) "Default value"
' Parameter 3 : (String) "Unlocked"
' Parameter 4 : (Boolean) False
'--------------------------------------------------

boolean10 = settingRepository1.GetAttr("PrefixPLMObjects")
'--------------------------------------------------
' Parameter 1 : (String) "PrefixPLMObjects"
' Returned value : (Variant) (Boolean) True
'--------------------------------------------------

Dim bSTR12
bSTR12 = ""
Dim bSTR13
bSTR13 = ""
Dim boolean11
settingRepository1.GetAttrInfo "PrefixPLMObjects", bSTR12, bSTR13, boolean11
'--------------------------------------------------
' Parameter 1 : (String) "PrefixPLMObjects"
' Parameter 2 : (String) "Default value"
' Parameter 3 : (String) "Unlocked"
' Parameter 4 : (Boolean) False
'--------------------------------------------------

boolean12 = settingRepository1.GetAttr("MandatoryCompensationRule")
'--------------------------------------------------
' Parameter 1 : (String) "MandatoryCompensationRule"
' Returned value : (Variant) (Boolean) False
'--------------------------------------------------

Dim bSTR14
bSTR14 = ""
Dim bSTR15
bSTR15 = ""
Dim boolean13
settingRepository1.GetAttrInfo "MandatoryCompensationRule", bSTR14, bSTR15, boolean13
'--------------------------------------------------
' Parameter 1 : (String) "MandatoryCompensationRule"
' Parameter 2 : (String) "Default value"
' Parameter 3 : (String) "Unlocked"
' Parameter 4 : (Boolean) False
'--------------------------------------------------

End Sub
