Language="VBSCRIPT"

Sub CATMain()

Set settingControllers1 = CATIA.SettingControllers

Set settingRepository1 = settingControllers1.Item("DELMfgFastenerSettings")

uLong1 = settingRepository1.GetAttr("MfgFastenerZAxis")
'--------------------------------------------------
' Parameter 1 : (String) "MfgFastenerZAxis"
' Returned value : (Variant) (Unsigned Long) 0
'--------------------------------------------------

Dim bSTR1
bSTR1 = ""
Dim bSTR2
bSTR2 = ""
Dim boolean1
settingRepository1.GetAttrInfo "MfgFastenerZAxis", bSTR1, bSTR2, boolean1
'--------------------------------------------------
' Parameter 1 : (String) "MfgFastenerZAxis"
' Parameter 2 : (String) "Default value"
' Parameter 3 : (String) "Unlocked"
' Parameter 4 : (Boolean) False
'--------------------------------------------------

uLong2 = settingRepository1.GetAttr("MfgFastenerUserParam")
'--------------------------------------------------
' Parameter 1 : (String) "MfgFastenerUserParam"
' Returned value : (Variant) (Unsigned Long) 0
'--------------------------------------------------

Dim bSTR3
bSTR3 = ""
Dim bSTR4
bSTR4 = ""
Dim boolean2
settingRepository1.GetAttrInfo "MfgFastenerUserParam", bSTR3, bSTR4, boolean2
'--------------------------------------------------
' Parameter 1 : (String) "MfgFastenerUserParam"
' Parameter 2 : (String) "Default value"
' Parameter 3 : (String) "Unlocked"
' Parameter 4 : (Boolean) False
'--------------------------------------------------

uLong3 = settingRepository1.GetAttr("MFTNameDisplay")
'--------------------------------------------------
' Parameter 1 : (String) "MFTNameDisplay"
' Returned value : (Variant) (Unsigned Long) 0
'--------------------------------------------------

Dim bSTR5
bSTR5 = ""
Dim bSTR6
bSTR6 = ""
Dim boolean3
settingRepository1.GetAttrInfo "MFTNameDisplay", bSTR5, bSTR6, boolean3
'--------------------------------------------------
' Parameter 1 : (String) "MFTNameDisplay"
' Parameter 2 : (String) "Default value"
' Parameter 3 : (String) "Unlocked"
' Parameter 4 : (Boolean) False
'--------------------------------------------------

End Sub
