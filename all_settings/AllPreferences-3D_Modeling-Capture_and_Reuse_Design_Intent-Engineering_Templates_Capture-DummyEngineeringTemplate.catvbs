Language="VBSCRIPT"

Sub CATMain()

Set settingControllers1 = CATIA.SettingControllers

Set settingRepository1 = settingControllers1.Item("EngineeringTemplate")

boolean1 = settingRepository1.GetAttr("CATBLNewTemplate")
'--------------------------------------------------
' Parameter 1 : (String) "CATBLNewTemplate"
' Returned value : (Variant) (Boolean) False
'--------------------------------------------------

Dim bSTR1
bSTR1 = ""
Dim bSTR2
bSTR2 = ""
Dim boolean2
settingRepository1.GetAttrInfo "CATBLNewTemplate", bSTR1, bSTR2, boolean2
'--------------------------------------------------
' Parameter 1 : (String) "CATBLNewTemplate"
' Parameter 2 : (String) "Default value"
' Parameter 3 : (String) "Unlocked"
' Parameter 4 : (Boolean) False
'--------------------------------------------------

End Sub
