Language="VBSCRIPT"

Sub CATMain()

Set settingControllers1 = CATIA.SettingControllers

Set settingRepository1 = settingControllers1.Item("IG2")

boolean1 = settingRepository1.GetAttr("ImportPaperSpacesInBackground")
'--------------------------------------------------
' Parameter 1 : (String) "ImportPaperSpacesInBackground"
' Returned value : (Variant) (Boolean) False
'--------------------------------------------------

Dim bSTR1
bSTR1 = ""
Dim bSTR2
bSTR2 = ""
Dim boolean2
settingRepository1.GetAttrInfo "ImportPaperSpacesInBackground", bSTR1, bSTR2, boolean2
'--------------------------------------------------
' Parameter 1 : (String) "ImportPaperSpacesInBackground"
' Parameter 2 : (String) "Default value"
' Parameter 3 : (String) "Unlocked"
' Parameter 4 : (Boolean) False
'--------------------------------------------------

boolean3 = settingRepository1.GetAttr("ImportKeepModelSpace")
'--------------------------------------------------
' Parameter 1 : (String) "ImportKeepModelSpace"
' Returned value : (Variant) (Boolean) False
'--------------------------------------------------

Dim bSTR3
bSTR3 = ""
Dim bSTR4
bSTR4 = ""
Dim boolean4
settingRepository1.GetAttrInfo "ImportKeepModelSpace", bSTR3, bSTR4, boolean4
'--------------------------------------------------
' Parameter 1 : (String) "ImportKeepModelSpace"
' Parameter 2 : (String) "Default value"
' Parameter 3 : (String) "Unlocked"
' Parameter 4 : (Boolean) False
'--------------------------------------------------

boolean5 = settingRepository1.GetAttr("ImportMapLayerOn2DL")
'--------------------------------------------------
' Parameter 1 : (String) "ImportMapLayerOn2DL"
' Returned value : (Variant) (Boolean) True
'--------------------------------------------------

Dim bSTR5
bSTR5 = ""
Dim bSTR6
bSTR6 = ""
Dim boolean6
settingRepository1.GetAttrInfo "ImportMapLayerOn2DL", bSTR5, bSTR6, boolean6
'--------------------------------------------------
' Parameter 1 : (String) "ImportMapLayerOn2DL"
' Parameter 2 : (String) "Default value"
' Parameter 3 : (String) "Unlocked"
' Parameter 4 : (Boolean) False
'--------------------------------------------------

boolean7 = settingRepository1.GetAttr("ImportMapColor")
'--------------------------------------------------
' Parameter 1 : (String) "ImportMapColor"
' Returned value : (Variant) (Boolean) True
'--------------------------------------------------

Dim bSTR7
bSTR7 = ""
Dim bSTR8
bSTR8 = ""
Dim boolean8
settingRepository1.GetAttrInfo "ImportMapColor", bSTR7, bSTR8, boolean8
'--------------------------------------------------
' Parameter 1 : (String) "ImportMapColor"
' Parameter 2 : (String) "Default value"
' Parameter 3 : (String) "Unlocked"
' Parameter 4 : (Boolean) False
'--------------------------------------------------

boolean9 = settingRepository1.GetAttr("ExportViewAsViewport")
'--------------------------------------------------
' Parameter 1 : (String) "ExportViewAsViewport"
' Returned value : (Variant) (Boolean) False
'--------------------------------------------------

Dim bSTR9
bSTR9 = ""
Dim bSTR10
bSTR10 = ""
Dim boolean10
settingRepository1.GetAttrInfo "ExportViewAsViewport", bSTR9, bSTR10, boolean10
'--------------------------------------------------
' Parameter 1 : (String) "ExportViewAsViewport"
' Parameter 2 : (String) "Default value"
' Parameter 3 : (String) "Unlocked"
' Parameter 4 : (Boolean) False
'--------------------------------------------------

bSTR11 = settingRepository1.GetAttr("ImportDftStandard")
'--------------------------------------------------
' Parameter 1 : (String) "ImportDftStandard"
' Returned value : (Variant) (String) "ISO"
'--------------------------------------------------

Dim bSTR12
bSTR12 = ""
Dim bSTR13
bSTR13 = ""
Dim boolean11
settingRepository1.GetAttrInfo "ImportDftStandard", bSTR12, bSTR13, boolean11
'--------------------------------------------------
' Parameter 1 : (String) "ImportDftStandard"
' Parameter 2 : (String) "Default value"
' Parameter 3 : (String) "Unlocked"
' Parameter 4 : (Boolean) False
'--------------------------------------------------

long1 = settingRepository1.GetAttr("ImportUnit")
'--------------------------------------------------
' Parameter 1 : (String) "ImportUnit"
' Returned value : (Variant) (Long) 5
'--------------------------------------------------

Dim bSTR14
bSTR14 = ""
Dim bSTR15
bSTR15 = ""
Dim boolean12
settingRepository1.GetAttrInfo "ImportUnit", bSTR14, bSTR15, boolean12
'--------------------------------------------------
' Parameter 1 : (String) "ImportUnit"
' Parameter 2 : (String) "Default value"
' Parameter 3 : (String) "Unlocked"
' Parameter 4 : (Boolean) False
'--------------------------------------------------

long2 = settingRepository1.GetAttr("ImportEndPoints")
'--------------------------------------------------
' Parameter 1 : (String) "ImportEndPoints"
' Returned value : (Variant) (Long) 0
'--------------------------------------------------

Dim bSTR16
bSTR16 = ""
Dim bSTR17
bSTR17 = ""
Dim boolean13
settingRepository1.GetAttrInfo "ImportEndPoints", bSTR16, bSTR17, boolean13
'--------------------------------------------------
' Parameter 1 : (String) "ImportEndPoints"
' Parameter 2 : (String) "Default value"
' Parameter 3 : (String) "Unlocked"
' Parameter 4 : (Boolean) False
'--------------------------------------------------

long3 = settingRepository1.GetAttr("ImportDimensions")
'--------------------------------------------------
' Parameter 1 : (String) "ImportDimensions"
' Returned value : (Variant) (Long) 1
'--------------------------------------------------

Dim bSTR18
bSTR18 = ""
Dim bSTR19
bSTR19 = ""
Dim boolean14
settingRepository1.GetAttrInfo "ImportDimensions", bSTR18, bSTR19, boolean14
'--------------------------------------------------
' Parameter 1 : (String) "ImportDimensions"
' Parameter 2 : (String) "Default value"
' Parameter 3 : (String) "Unlocked"
' Parameter 4 : (Boolean) False
'--------------------------------------------------

long4 = settingRepository1.GetAttr("ExportSheets")
'--------------------------------------------------
' Parameter 1 : (String) "ExportSheets"
' Returned value : (Variant) (Long) 0
'--------------------------------------------------

Dim bSTR20
bSTR20 = ""
Dim bSTR21
bSTR21 = ""
Dim boolean15
settingRepository1.GetAttrInfo "ExportSheets", bSTR20, bSTR21, boolean15
'--------------------------------------------------
' Parameter 1 : (String) "ExportSheets"
' Parameter 2 : (String) "Default value"
' Parameter 3 : (String) "Unlocked"
' Parameter 4 : (Boolean) False
'--------------------------------------------------

long5 = settingRepository1.GetAttr("ExportMode")
'--------------------------------------------------
' Parameter 1 : (String) "ExportMode"
' Returned value : (Variant) (Long) 2
'--------------------------------------------------

Dim bSTR22
bSTR22 = ""
Dim bSTR23
bSTR23 = ""
Dim boolean16
settingRepository1.GetAttrInfo "ExportMode", bSTR22, bSTR23, boolean16
'--------------------------------------------------
' Parameter 1 : (String) "ExportMode"
' Parameter 2 : (String) "Default value"
' Parameter 3 : (String) "Unlocked"
' Parameter 4 : (Boolean) False
'--------------------------------------------------

End Sub
