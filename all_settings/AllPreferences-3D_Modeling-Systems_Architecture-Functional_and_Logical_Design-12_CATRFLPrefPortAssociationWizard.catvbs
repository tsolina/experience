Language="VBSCRIPT"

Sub CATMain()

Set settingControllers1 = CATIA.SettingControllers

Set settingRepository1 = settingControllers1.Item("PLMEditorColor")

uLong1 = settingRepository1.GetAttr("PortAssoWizardStepbyStepReplaceMode")
'--------------------------------------------------
' Parameter 1 : (String) "PortAssoWizardStepbyStepReplaceMode"
' Returned value : (Variant) (Unsigned Long) 0
'--------------------------------------------------

Dim bSTR1
bSTR1 = ""
Dim bSTR2
bSTR2 = ""
Dim boolean1
settingRepository1.GetAttrInfo "PortAssoWizardStepbyStepReplaceMode", bSTR1, bSTR2, boolean1
'--------------------------------------------------
' Parameter 1 : (String) "PortAssoWizardStepbyStepReplaceMode"
' Parameter 2 : (String) "Default value"
' Parameter 3 : (String) "Unlocked"
' Parameter 4 : (Boolean) False
'--------------------------------------------------

uLong2 = settingRepository1.GetAttr("PortAssoWizardAutoOrSkipMode")
'--------------------------------------------------
' Parameter 1 : (String) "PortAssoWizardAutoOrSkipMode"
' Returned value : (Variant) (Unsigned Long) 0
'--------------------------------------------------

Dim bSTR3
bSTR3 = ""
Dim bSTR4
bSTR4 = ""
Dim boolean2
settingRepository1.GetAttrInfo "PortAssoWizardAutoOrSkipMode", bSTR3, bSTR4, boolean2
'--------------------------------------------------
' Parameter 1 : (String) "PortAssoWizardAutoOrSkipMode"
' Parameter 2 : (String) "Default value"
' Parameter 3 : (String) "Unlocked"
' Parameter 4 : (Boolean) False
'--------------------------------------------------

uLong3 = settingRepository1.GetAttr("PortAssoWizardReplaceAllMode")
'--------------------------------------------------
' Parameter 1 : (String) "PortAssoWizardReplaceAllMode"
' Returned value : (Variant) (Unsigned Long) 0
'--------------------------------------------------

Dim bSTR5
bSTR5 = ""
Dim bSTR6
bSTR6 = ""
Dim boolean3
settingRepository1.GetAttrInfo "PortAssoWizardReplaceAllMode", bSTR5, bSTR6, boolean3
'--------------------------------------------------
' Parameter 1 : (String) "PortAssoWizardReplaceAllMode"
' Parameter 2 : (String) "Default value"
' Parameter 3 : (String) "Unlocked"
' Parameter 4 : (Boolean) False
'--------------------------------------------------

End Sub
