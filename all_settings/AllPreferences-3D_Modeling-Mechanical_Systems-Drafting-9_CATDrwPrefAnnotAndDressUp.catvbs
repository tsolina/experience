Language="VBSCRIPT"

Sub CATMain()

Set settingControllers1 = CATIA.SettingControllers

Set settingRepository1 = settingControllers1.Item("DraftingOptions")

boolean1 = settingRepository1.GetAttr("DrwTextSnappingOn")
'--------------------------------------------------
' Parameter 1 : (String) "DrwTextSnappingOn"
' Returned value : (Variant) (Boolean) False
'--------------------------------------------------

Dim bSTR1
bSTR1 = ""
Dim bSTR2
bSTR2 = ""
Dim boolean2
settingRepository1.GetAttrInfo "DrwTextSnappingOn", bSTR1, bSTR2, boolean2
'--------------------------------------------------
' Parameter 1 : (String) "DrwTextSnappingOn"
' Parameter 2 : (String) "Default value"
' Parameter 3 : (String) "Unlocked"
' Parameter 4 : (Boolean) False
'--------------------------------------------------

boolean3 = settingRepository1.GetAttr("CATDrwResizeTableEdition")
'--------------------------------------------------
' Parameter 1 : (String) "CATDrwResizeTableEdition"
' Returned value : (Variant) (Boolean) True
'--------------------------------------------------

Dim bSTR3
bSTR3 = ""
Dim bSTR4
bSTR4 = ""
Dim boolean4
settingRepository1.GetAttrInfo "CATDrwResizeTableEdition", bSTR3, bSTR4, boolean4
'--------------------------------------------------
' Parameter 1 : (String) "CATDrwResizeTableEdition"
' Parameter 2 : (String) "Default value"
' Parameter 3 : (String) "Unlocked"
' Parameter 4 : (Boolean) False
'--------------------------------------------------

boolean5 = settingRepository1.GetAttr("CATDrwPreventTableAutoSplit")
'--------------------------------------------------
' Parameter 1 : (String) "CATDrwPreventTableAutoSplit"
' Returned value : (Variant) (Boolean) True
'--------------------------------------------------

Dim bSTR5
bSTR5 = ""
Dim bSTR6
bSTR6 = ""
Dim boolean6
settingRepository1.GetAttrInfo "CATDrwPreventTableAutoSplit", bSTR5, bSTR6, boolean6
'--------------------------------------------------
' Parameter 1 : (String) "CATDrwPreventTableAutoSplit"
' Parameter 2 : (String) "Default value"
' Parameter 3 : (String) "Unlocked"
' Parameter 4 : (Boolean) False
'--------------------------------------------------

boolean7 = settingRepository1.GetAttr("CATDrwAFAskForDelSupport")
'--------------------------------------------------
' Parameter 1 : (String) "CATDrwAFAskForDelSupport"
' Returned value : (Variant) (Boolean) True
'--------------------------------------------------

Dim bSTR7
bSTR7 = ""
Dim bSTR8
bSTR8 = ""
Dim boolean8
settingRepository1.GetAttrInfo "CATDrwAFAskForDelSupport", bSTR7, bSTR8, boolean8
'--------------------------------------------------
' Parameter 1 : (String) "CATDrwAFAskForDelSupport"
' Parameter 2 : (String) "Default value"
' Parameter 3 : (String) "Unlocked"
' Parameter 4 : (Boolean) False
'--------------------------------------------------

boolean9 = settingRepository1.GetAttr("DrwTextLeadSnappingOn")
'--------------------------------------------------
' Parameter 1 : (String) "DrwTextLeadSnappingOn"
' Returned value : (Variant) (Boolean) False
'--------------------------------------------------

Dim bSTR9
bSTR9 = ""
Dim bSTR10
bSTR10 = ""
Dim boolean10
settingRepository1.GetAttrInfo "DrwTextLeadSnappingOn", bSTR9, bSTR10, boolean10
'--------------------------------------------------
' Parameter 1 : (String) "DrwTextLeadSnappingOn"
' Parameter 2 : (String) "Default value"
' Parameter 3 : (String) "Unlocked"
' Parameter 4 : (Boolean) False
'--------------------------------------------------

boolean11 = settingRepository1.GetAttr("DrwGDTSnappingOn")
'--------------------------------------------------
' Parameter 1 : (String) "DrwGDTSnappingOn"
' Returned value : (Variant) (Boolean) False
'--------------------------------------------------

Dim bSTR11
bSTR11 = ""
Dim bSTR12
bSTR12 = ""
Dim boolean12
settingRepository1.GetAttrInfo "DrwGDTSnappingOn", bSTR11, bSTR12, boolean12
'--------------------------------------------------
' Parameter 1 : (String) "DrwGDTSnappingOn"
' Parameter 2 : (String) "Default value"
' Parameter 3 : (String) "Unlocked"
' Parameter 4 : (Boolean) False
'--------------------------------------------------

boolean13 = settingRepository1.GetAttr("DrwTextRigidPosLink")
'--------------------------------------------------
' Parameter 1 : (String) "DrwTextRigidPosLink"
' Returned value : (Variant) (Boolean) False
'--------------------------------------------------

Dim bSTR13
bSTR13 = ""
Dim bSTR14
bSTR14 = ""
Dim boolean14
settingRepository1.GetAttrInfo "DrwTextRigidPosLink", bSTR13, bSTR14, boolean14
'--------------------------------------------------
' Parameter 1 : (String) "DrwTextRigidPosLink"
' Parameter 2 : (String) "Default value"
' Parameter 3 : (String) "Unlocked"
' Parameter 4 : (Boolean) False
'--------------------------------------------------

boolean15 = settingRepository1.GetAttr("DrwTableRigidPosLink")
'--------------------------------------------------
' Parameter 1 : (String) "DrwTableRigidPosLink"
' Returned value : (Variant) (Boolean) False
'--------------------------------------------------

Dim bSTR15
bSTR15 = ""
Dim bSTR16
bSTR16 = ""
Dim boolean16
settingRepository1.GetAttrInfo "DrwTableRigidPosLink", bSTR15, bSTR16, boolean16
'--------------------------------------------------
' Parameter 1 : (String) "DrwTableRigidPosLink"
' Parameter 2 : (String) "Default value"
' Parameter 3 : (String) "Unlocked"
' Parameter 4 : (Boolean) False
'--------------------------------------------------

boolean17 = settingRepository1.GetAttr("DrwGDTRigidPosLink")
'--------------------------------------------------
' Parameter 1 : (String) "DrwGDTRigidPosLink"
' Returned value : (Variant) (Boolean) False
'--------------------------------------------------

Dim bSTR17
bSTR17 = ""
Dim bSTR18
bSTR18 = ""
Dim boolean18
settingRepository1.GetAttrInfo "DrwGDTRigidPosLink", bSTR17, bSTR18, boolean18
'--------------------------------------------------
' Parameter 1 : (String) "DrwGDTRigidPosLink"
' Parameter 2 : (String) "Default value"
' Parameter 3 : (String) "Unlocked"
' Parameter 4 : (Boolean) False
'--------------------------------------------------

boolean19 = settingRepository1.GetAttr("DrwTextOnAttachmentPtsOnly")
'--------------------------------------------------
' Parameter 1 : (String) "DrwTextOnAttachmentPtsOnly"
' Returned value : (Variant) (Boolean) True
'--------------------------------------------------

Dim bSTR19
bSTR19 = ""
Dim bSTR20
bSTR20 = ""
Dim boolean20
settingRepository1.GetAttrInfo "DrwTextOnAttachmentPtsOnly", bSTR19, bSTR20, boolean20
'--------------------------------------------------
' Parameter 1 : (String) "DrwTextOnAttachmentPtsOnly"
' Parameter 2 : (String) "Default value"
' Parameter 3 : (String) "Unlocked"
' Parameter 4 : (Boolean) False
'--------------------------------------------------

double1 = settingRepository1.GetAttr("DrwLegendTableTitleHeight")
'--------------------------------------------------
' Parameter 1 : (String) "DrwLegendTableTitleHeight"
' Returned value : (Variant) (Double) 0.010000
'--------------------------------------------------

Dim bSTR21
bSTR21 = ""
Dim bSTR22
bSTR22 = ""
Dim boolean21
settingRepository1.GetAttrInfo "DrwLegendTableTitleHeight", bSTR21, bSTR22, boolean21
'--------------------------------------------------
' Parameter 1 : (String) "DrwLegendTableTitleHeight"
' Parameter 2 : (String) "Default value"
' Parameter 3 : (String) "Unlocked"
' Parameter 4 : (Boolean) False
'--------------------------------------------------

boolean22 = settingRepository1.GetAttr("DrwLegendTableTitleHeightNoOverload")
'--------------------------------------------------
' Parameter 1 : (String) "DrwLegendTableTitleHeightNoOverload"
' Returned value : (Variant) (Boolean) False
'--------------------------------------------------

Dim bSTR23
bSTR23 = ""
Dim bSTR24
bSTR24 = ""
Dim boolean23
settingRepository1.GetAttrInfo "DrwLegendTableTitleHeightNoOverload", bSTR23, bSTR24, boolean23
'--------------------------------------------------
' Parameter 1 : (String) "DrwLegendTableTitleHeightNoOverload"
' Parameter 2 : (String) "Default value"
' Parameter 3 : (String) "Unlocked"
' Parameter 4 : (Boolean) False
'--------------------------------------------------

uLong1 = settingRepository1.GetAttr("DrwLegendTableTitleAlignment")
'--------------------------------------------------
' Parameter 1 : (String) "DrwLegendTableTitleAlignment"
' Returned value : (Variant) (Unsigned Long) 5
'--------------------------------------------------

Dim bSTR25
bSTR25 = ""
Dim bSTR26
bSTR26 = ""
Dim boolean24
settingRepository1.GetAttrInfo "DrwLegendTableTitleAlignment", bSTR25, bSTR26, boolean24
'--------------------------------------------------
' Parameter 1 : (String) "DrwLegendTableTitleAlignment"
' Parameter 2 : (String) "Default value"
' Parameter 3 : (String) "Unlocked"
' Parameter 4 : (Boolean) False
'--------------------------------------------------

boolean25 = settingRepository1.GetAttr("DrwLegendTableTitleAlignmentNoOverload")
'--------------------------------------------------
' Parameter 1 : (String) "DrwLegendTableTitleAlignmentNoOverload"
' Returned value : (Variant) (Boolean) False
'--------------------------------------------------

Dim bSTR27
bSTR27 = ""
Dim bSTR28
bSTR28 = ""
Dim boolean26
settingRepository1.GetAttrInfo "DrwLegendTableTitleAlignmentNoOverload", bSTR27, bSTR28, boolean26
'--------------------------------------------------
' Parameter 1 : (String) "DrwLegendTableTitleAlignmentNoOverload"
' Parameter 2 : (String) "Default value"
' Parameter 3 : (String) "Unlocked"
' Parameter 4 : (Boolean) False
'--------------------------------------------------

double2 = settingRepository1.GetAttr("DrwLegendTableImageWidth")
'--------------------------------------------------
' Parameter 1 : (String) "DrwLegendTableImageWidth"
' Returned value : (Variant) (Double) 0.010000
'--------------------------------------------------

Dim bSTR29
bSTR29 = ""
Dim bSTR30
bSTR30 = ""
Dim boolean27
settingRepository1.GetAttrInfo "DrwLegendTableImageWidth", bSTR29, bSTR30, boolean27
'--------------------------------------------------
' Parameter 1 : (String) "DrwLegendTableImageWidth"
' Parameter 2 : (String) "Default value"
' Parameter 3 : (String) "Unlocked"
' Parameter 4 : (Boolean) False
'--------------------------------------------------

boolean28 = settingRepository1.GetAttr("DrwLegendTableImageWidthNoOverload")
'--------------------------------------------------
' Parameter 1 : (String) "DrwLegendTableImageWidthNoOverload"
' Returned value : (Variant) (Boolean) False
'--------------------------------------------------

Dim bSTR31
bSTR31 = ""
Dim bSTR32
bSTR32 = ""
Dim boolean29
settingRepository1.GetAttrInfo "DrwLegendTableImageWidthNoOverload", bSTR31, bSTR32, boolean29
'--------------------------------------------------
' Parameter 1 : (String) "DrwLegendTableImageWidthNoOverload"
' Parameter 2 : (String) "Default value"
' Parameter 3 : (String) "Unlocked"
' Parameter 4 : (Boolean) False
'--------------------------------------------------

boolean30 = settingRepository1.GetAttr("DrwLegendTableImageHeight")
'--------------------------------------------------
' Parameter 1 : (String) "DrwLegendTableImageHeight"
' Returned value : (Variant) (Boolean) True
'--------------------------------------------------

Dim bSTR33
bSTR33 = ""
Dim bSTR34
bSTR34 = ""
Dim boolean31
settingRepository1.GetAttrInfo "DrwLegendTableImageHeight", bSTR33, bSTR34, boolean31
'--------------------------------------------------
' Parameter 1 : (String) "DrwLegendTableImageHeight"
' Parameter 2 : (String) "Default value"
' Parameter 3 : (String) "Unlocked"
' Parameter 4 : (Boolean) False
'--------------------------------------------------

boolean32 = settingRepository1.GetAttr("DrwLegendTableImageHeightNoOverload")
'--------------------------------------------------
' Parameter 1 : (String) "DrwLegendTableImageHeightNoOverload"
' Returned value : (Variant) (Boolean) False
'--------------------------------------------------

Dim bSTR35
bSTR35 = ""
Dim bSTR36
bSTR36 = ""
Dim boolean33
settingRepository1.GetAttrInfo "DrwLegendTableImageHeightNoOverload", bSTR35, bSTR36, boolean33
'--------------------------------------------------
' Parameter 1 : (String) "DrwLegendTableImageHeightNoOverload"
' Parameter 2 : (String) "Default value"
' Parameter 3 : (String) "Unlocked"
' Parameter 4 : (Boolean) False
'--------------------------------------------------

uLong2 = settingRepository1.GetAttr("DrwLegendTableImageAlignment")
'--------------------------------------------------
' Parameter 1 : (String) "DrwLegendTableImageAlignment"
' Returned value : (Variant) (Unsigned Long) 5
'--------------------------------------------------

Dim bSTR37
bSTR37 = ""
Dim bSTR38
bSTR38 = ""
Dim boolean34
settingRepository1.GetAttrInfo "DrwLegendTableImageAlignment", bSTR37, bSTR38, boolean34
'--------------------------------------------------
' Parameter 1 : (String) "DrwLegendTableImageAlignment"
' Parameter 2 : (String) "Default value"
' Parameter 3 : (String) "Unlocked"
' Parameter 4 : (Boolean) False
'--------------------------------------------------

boolean35 = settingRepository1.GetAttr("DrwLegendTableImageAlignmentNoOverload")
'--------------------------------------------------
' Parameter 1 : (String) "DrwLegendTableImageAlignmentNoOverload"
' Returned value : (Variant) (Boolean) False
'--------------------------------------------------

Dim bSTR39
bSTR39 = ""
Dim bSTR40
bSTR40 = ""
Dim boolean36
settingRepository1.GetAttrInfo "DrwLegendTableImageAlignmentNoOverload", bSTR39, bSTR40, boolean36
'--------------------------------------------------
' Parameter 1 : (String) "DrwLegendTableImageAlignmentNoOverload"
' Parameter 2 : (String) "Default value"
' Parameter 3 : (String) "Unlocked"
' Parameter 4 : (Boolean) False
'--------------------------------------------------

double3 = settingRepository1.GetAttr("DrwLegendTableLegendWidth")
'--------------------------------------------------
' Parameter 1 : (String) "DrwLegendTableLegendWidth"
' Returned value : (Variant) (Double) 0.010000
'--------------------------------------------------

Dim bSTR41
bSTR41 = ""
Dim bSTR42
bSTR42 = ""
Dim boolean37
settingRepository1.GetAttrInfo "DrwLegendTableLegendWidth", bSTR41, bSTR42, boolean37
'--------------------------------------------------
' Parameter 1 : (String) "DrwLegendTableLegendWidth"
' Parameter 2 : (String) "Default value"
' Parameter 3 : (String) "Unlocked"
' Parameter 4 : (Boolean) False
'--------------------------------------------------

boolean38 = settingRepository1.GetAttr("DrwLegendTableLegendWidthNoOverload")
'--------------------------------------------------
' Parameter 1 : (String) "DrwLegendTableLegendWidthNoOverload"
' Returned value : (Variant) (Boolean) False
'--------------------------------------------------

Dim bSTR43
bSTR43 = ""
Dim bSTR44
bSTR44 = ""
Dim boolean39
settingRepository1.GetAttrInfo "DrwLegendTableLegendWidthNoOverload", bSTR43, bSTR44, boolean39
'--------------------------------------------------
' Parameter 1 : (String) "DrwLegendTableLegendWidthNoOverload"
' Parameter 2 : (String) "Default value"
' Parameter 3 : (String) "Unlocked"
' Parameter 4 : (Boolean) False
'--------------------------------------------------

uLong3 = settingRepository1.GetAttr("DrwLegendTableLegendAlignment")
'--------------------------------------------------
' Parameter 1 : (String) "DrwLegendTableLegendAlignment"
' Returned value : (Variant) (Unsigned Long) 5
'--------------------------------------------------

Dim bSTR45
bSTR45 = ""
Dim bSTR46
bSTR46 = ""
Dim boolean40
settingRepository1.GetAttrInfo "DrwLegendTableLegendAlignment", bSTR45, bSTR46, boolean40
'--------------------------------------------------
' Parameter 1 : (String) "DrwLegendTableLegendAlignment"
' Parameter 2 : (String) "Default value"
' Parameter 3 : (String) "Unlocked"
' Parameter 4 : (Boolean) False
'--------------------------------------------------

boolean41 = settingRepository1.GetAttr("DrwLegendTableLegendAlignmentNoOverload")
'--------------------------------------------------
' Parameter 1 : (String) "DrwLegendTableLegendAlignmentNoOverload"
' Returned value : (Variant) (Boolean) False
'--------------------------------------------------

Dim bSTR47
bSTR47 = ""
Dim bSTR48
bSTR48 = ""
Dim boolean42
settingRepository1.GetAttrInfo "DrwLegendTableLegendAlignmentNoOverload", bSTR47, bSTR48, boolean42
'--------------------------------------------------
' Parameter 1 : (String) "DrwLegendTableLegendAlignmentNoOverload"
' Parameter 2 : (String) "Default value"
' Parameter 3 : (String) "Unlocked"
' Parameter 4 : (Boolean) False
'--------------------------------------------------

double4 = settingRepository1.GetAttr("DrwLegendTableCountPerViewWidth")
'--------------------------------------------------
' Parameter 1 : (String) "DrwLegendTableCountPerViewWidth"
' Returned value : (Variant) (Double) 0.010000
'--------------------------------------------------

Dim bSTR49
bSTR49 = ""
Dim bSTR50
bSTR50 = ""
Dim boolean43
settingRepository1.GetAttrInfo "DrwLegendTableCountPerViewWidth", bSTR49, bSTR50, boolean43
'--------------------------------------------------
' Parameter 1 : (String) "DrwLegendTableCountPerViewWidth"
' Parameter 2 : (String) "Default value"
' Parameter 3 : (String) "Unlocked"
' Parameter 4 : (Boolean) False
'--------------------------------------------------

boolean44 = settingRepository1.GetAttr("DrwLegendTableCountPerViewWidthNoOverload")
'--------------------------------------------------
' Parameter 1 : (String) "DrwLegendTableCountPerViewWidthNoOverload"
' Returned value : (Variant) (Boolean) False
'--------------------------------------------------

Dim bSTR51
bSTR51 = ""
Dim bSTR52
bSTR52 = ""
Dim boolean45
settingRepository1.GetAttrInfo "DrwLegendTableCountPerViewWidthNoOverload", bSTR51, bSTR52, boolean45
'--------------------------------------------------
' Parameter 1 : (String) "DrwLegendTableCountPerViewWidthNoOverload"
' Parameter 2 : (String) "Default value"
' Parameter 3 : (String) "Unlocked"
' Parameter 4 : (Boolean) False
'--------------------------------------------------

uLong4 = settingRepository1.GetAttr("DrwLegendTableCountPerViewAlignment")
'--------------------------------------------------
' Parameter 1 : (String) "DrwLegendTableCountPerViewAlignment"
' Returned value : (Variant) (Unsigned Long) 5
'--------------------------------------------------

Dim bSTR53
bSTR53 = ""
Dim bSTR54
bSTR54 = ""
Dim boolean46
settingRepository1.GetAttrInfo "DrwLegendTableCountPerViewAlignment", bSTR53, bSTR54, boolean46
'--------------------------------------------------
' Parameter 1 : (String) "DrwLegendTableCountPerViewAlignment"
' Parameter 2 : (String) "Default value"
' Parameter 3 : (String) "Unlocked"
' Parameter 4 : (Boolean) False
'--------------------------------------------------

boolean47 = settingRepository1.GetAttr("DrwLegendTableCountPerViewAlignmentNoOverload")
'--------------------------------------------------
' Parameter 1 : (String) "DrwLegendTableCountPerViewAlignmentNoOverload"
' Returned value : (Variant) (Boolean) False
'--------------------------------------------------

Dim bSTR55
bSTR55 = ""
Dim bSTR56
bSTR56 = ""
Dim boolean48
settingRepository1.GetAttrInfo "DrwLegendTableCountPerViewAlignmentNoOverload", bSTR55, bSTR56, boolean48
'--------------------------------------------------
' Parameter 1 : (String) "DrwLegendTableCountPerViewAlignmentNoOverload"
' Parameter 2 : (String) "Default value"
' Parameter 3 : (String) "Unlocked"
' Parameter 4 : (Boolean) False
'--------------------------------------------------

double5 = settingRepository1.GetAttr("DrwLegendTableTotalCountWidth")
'--------------------------------------------------
' Parameter 1 : (String) "DrwLegendTableTotalCountWidth"
' Returned value : (Variant) (Double) 0.010000
'--------------------------------------------------

Dim bSTR57
bSTR57 = ""
Dim bSTR58
bSTR58 = ""
Dim boolean49
settingRepository1.GetAttrInfo "DrwLegendTableTotalCountWidth", bSTR57, bSTR58, boolean49
'--------------------------------------------------
' Parameter 1 : (String) "DrwLegendTableTotalCountWidth"
' Parameter 2 : (String) "Default value"
' Parameter 3 : (String) "Unlocked"
' Parameter 4 : (Boolean) False
'--------------------------------------------------

boolean50 = settingRepository1.GetAttr("DrwLegendTableTotalCountWidthNoOverload")
'--------------------------------------------------
' Parameter 1 : (String) "DrwLegendTableTotalCountWidthNoOverload"
' Returned value : (Variant) (Boolean) False
'--------------------------------------------------

Dim bSTR59
bSTR59 = ""
Dim bSTR60
bSTR60 = ""
Dim boolean51
settingRepository1.GetAttrInfo "DrwLegendTableTotalCountWidthNoOverload", bSTR59, bSTR60, boolean51
'--------------------------------------------------
' Parameter 1 : (String) "DrwLegendTableTotalCountWidthNoOverload"
' Parameter 2 : (String) "Default value"
' Parameter 3 : (String) "Unlocked"
' Parameter 4 : (Boolean) False
'--------------------------------------------------

uLong5 = settingRepository1.GetAttr("DrwLegendTableTotalCountAlignment")
'--------------------------------------------------
' Parameter 1 : (String) "DrwLegendTableTotalCountAlignment"
' Returned value : (Variant) (Unsigned Long) 5
'--------------------------------------------------

Dim bSTR61
bSTR61 = ""
Dim bSTR62
bSTR62 = ""
Dim boolean52
settingRepository1.GetAttrInfo "DrwLegendTableTotalCountAlignment", bSTR61, bSTR62, boolean52
'--------------------------------------------------
' Parameter 1 : (String) "DrwLegendTableTotalCountAlignment"
' Parameter 2 : (String) "Default value"
' Parameter 3 : (String) "Unlocked"
' Parameter 4 : (Boolean) False
'--------------------------------------------------

boolean53 = settingRepository1.GetAttr("DrwLegendTableTotalCountAlignmentNoOverload")
'--------------------------------------------------
' Parameter 1 : (String) "DrwLegendTableTotalCountAlignmentNoOverload"
' Returned value : (Variant) (Boolean) False
'--------------------------------------------------

Dim bSTR63
bSTR63 = ""
Dim bSTR64
bSTR64 = ""
Dim boolean54
settingRepository1.GetAttrInfo "DrwLegendTableTotalCountAlignmentNoOverload", bSTR63, bSTR64, boolean54
'--------------------------------------------------
' Parameter 1 : (String) "DrwLegendTableTotalCountAlignmentNoOverload"
' Parameter 2 : (String) "Default value"
' Parameter 3 : (String) "Unlocked"
' Parameter 4 : (Boolean) False
'--------------------------------------------------

double6 = settingRepository1.GetAttr("DrwLegendTableHeadersHeight")
'--------------------------------------------------
' Parameter 1 : (String) "DrwLegendTableHeadersHeight"
' Returned value : (Variant) (Double) 0.010000
'--------------------------------------------------

Dim bSTR65
bSTR65 = ""
Dim bSTR66
bSTR66 = ""
Dim boolean55
settingRepository1.GetAttrInfo "DrwLegendTableHeadersHeight", bSTR65, bSTR66, boolean55
'--------------------------------------------------
' Parameter 1 : (String) "DrwLegendTableHeadersHeight"
' Parameter 2 : (String) "Default value"
' Parameter 3 : (String) "Unlocked"
' Parameter 4 : (Boolean) False
'--------------------------------------------------

boolean56 = settingRepository1.GetAttr("DrwLegendTableHeadersHeightNoOverload")
'--------------------------------------------------
' Parameter 1 : (String) "DrwLegendTableHeadersHeightNoOverload"
' Returned value : (Variant) (Boolean) False
'--------------------------------------------------

Dim bSTR67
bSTR67 = ""
Dim bSTR68
bSTR68 = ""
Dim boolean57
settingRepository1.GetAttrInfo "DrwLegendTableHeadersHeightNoOverload", bSTR67, bSTR68, boolean57
'--------------------------------------------------
' Parameter 1 : (String) "DrwLegendTableHeadersHeightNoOverload"
' Parameter 2 : (String) "Default value"
' Parameter 3 : (String) "Unlocked"
' Parameter 4 : (Boolean) False
'--------------------------------------------------

double7 = settingRepository1.GetAttr("DrwLegendTableReportedItemsHeight")
'--------------------------------------------------
' Parameter 1 : (String) "DrwLegendTableReportedItemsHeight"
' Returned value : (Variant) (Double) 0.010000
'--------------------------------------------------

Dim bSTR69
bSTR69 = ""
Dim bSTR70
bSTR70 = ""
Dim boolean58
settingRepository1.GetAttrInfo "DrwLegendTableReportedItemsHeight", bSTR69, bSTR70, boolean58
'--------------------------------------------------
' Parameter 1 : (String) "DrwLegendTableReportedItemsHeight"
' Parameter 2 : (String) "Default value"
' Parameter 3 : (String) "Unlocked"
' Parameter 4 : (Boolean) False
'--------------------------------------------------

boolean59 = settingRepository1.GetAttr("DrwLegendTableReportedItemsHeightNoOverload")
'--------------------------------------------------
' Parameter 1 : (String) "DrwLegendTableReportedItemsHeightNoOverload"
' Returned value : (Variant) (Boolean) False
'--------------------------------------------------

Dim bSTR71
bSTR71 = ""
Dim bSTR72
bSTR72 = ""
Dim boolean60
settingRepository1.GetAttrInfo "DrwLegendTableReportedItemsHeightNoOverload", bSTR71, bSTR72, boolean60
'--------------------------------------------------
' Parameter 1 : (String) "DrwLegendTableReportedItemsHeightNoOverload"
' Parameter 2 : (String) "Default value"
' Parameter 3 : (String) "Unlocked"
' Parameter 4 : (Boolean) False
'--------------------------------------------------

long1 = settingRepository1.GetAttr("CATDrwAFOptimizationMode")
'--------------------------------------------------
' Parameter 1 : (String) "CATDrwAFOptimizationMode"
' Returned value : (Variant) (Long) 0
'--------------------------------------------------

Dim bSTR73
bSTR73 = ""
Dim bSTR74
bSTR74 = ""
Dim boolean61
settingRepository1.GetAttrInfo "CATDrwAFOptimizationMode", bSTR73, bSTR74, boolean61
'--------------------------------------------------
' Parameter 1 : (String) "CATDrwAFOptimizationMode"
' Parameter 2 : (String) "Default value"
' Parameter 3 : (String) "Unlocked"
' Parameter 4 : (Boolean) False
'--------------------------------------------------

End Sub
