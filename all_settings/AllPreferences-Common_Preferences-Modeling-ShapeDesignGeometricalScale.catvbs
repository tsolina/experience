Language="VBSCRIPT"

Sub CATMain()

Set settingControllers1 = CATIA.SettingControllers

Set settingRepository1 = settingControllers1.Item("GeometricModeler")

double1 = settingRepository1.GetAttr("GeometricScale")
'--------------------------------------------------
' Parameter 1 : (String) "GeometricScale"
' Returned value : (Variant) (Double) 1.000000
'--------------------------------------------------

Dim bSTR1
bSTR1 = ""
Dim bSTR2
bSTR2 = ""
Dim boolean1
settingRepository1.GetAttrInfo "GeometricScale", bSTR1, bSTR2, boolean1
'--------------------------------------------------
' Parameter 1 : (String) "GeometricScale"
' Parameter 2 : (String) "Default value"
' Parameter 3 : (String) "Unlocked"
' Parameter 4 : (Boolean) False
'--------------------------------------------------

End Sub
