Language="VBSCRIPT"

Sub CATMain()

Set settingControllers1 = CATIA.SettingControllers

Set settingRepository1 = settingControllers1.Item("MaterialOptionsSettings")

long1 = settingRepository1.GetAttr("CheckButtonShowBrokenCnx")
'--------------------------------------------------
' Parameter 1 : (String) "CheckButtonShowBrokenCnx"
' Returned value : (Variant) (Long) 0
'--------------------------------------------------

Dim bSTR1
bSTR1 = ""
Dim bSTR2
bSTR2 = ""
Dim boolean1
settingRepository1.GetAttrInfo "CheckButtonShowBrokenCnx", bSTR1, bSTR2, boolean1
'--------------------------------------------------
' Parameter 1 : (String) "CheckButtonShowBrokenCnx"
' Parameter 2 : (String) "Default value"
' Parameter 3 : (String) "Unlocked"
' Parameter 4 : (Boolean) False
'--------------------------------------------------

bSTR3 = settingRepository1.GetAttr("SearchKeyWordEditor")
'--------------------------------------------------
' Parameter 1 : (String) "SearchKeyWordEditor"
' Returned value : (Variant) (String) " "
'--------------------------------------------------

Dim bSTR4
bSTR4 = ""
Dim bSTR5
bSTR5 = ""
Dim boolean2
settingRepository1.GetAttrInfo "SearchKeyWordEditor", bSTR4, bSTR5, boolean2
'--------------------------------------------------
' Parameter 1 : (String) "SearchKeyWordEditor"
' Parameter 2 : (String) "Default value"
' Parameter 3 : (String) "Unlocked"
' Parameter 4 : (Boolean) False
'--------------------------------------------------

long2 = settingRepository1.GetAttr("CheckButtonSearchAll")
'--------------------------------------------------
' Parameter 1 : (String) "CheckButtonSearchAll"
' Returned value : (Variant) (Long) 1
'--------------------------------------------------

Dim bSTR6
bSTR6 = ""
Dim bSTR7
bSTR7 = ""
Dim boolean3
settingRepository1.GetAttrInfo "CheckButtonSearchAll", bSTR6, bSTR7, boolean3
'--------------------------------------------------
' Parameter 1 : (String) "CheckButtonSearchAll"
' Parameter 2 : (String) "Default value"
' Parameter 3 : (String) "Unlocked"
' Parameter 4 : (Boolean) False
'--------------------------------------------------

long3 = settingRepository1.GetAttr("KeepMaterialInSession")
'--------------------------------------------------
' Parameter 1 : (String) "KeepMaterialInSession"
' Returned value : (Variant) (Long) 1
'--------------------------------------------------

Dim bSTR8
bSTR8 = ""
Dim bSTR9
bSTR9 = ""
Dim boolean4
settingRepository1.GetAttrInfo "KeepMaterialInSession", bSTR8, bSTR9, boolean4
'--------------------------------------------------
' Parameter 1 : (String) "KeepMaterialInSession"
' Parameter 2 : (String) "Default value"
' Parameter 3 : (String) "Unlocked"
' Parameter 4 : (Boolean) False
'--------------------------------------------------

long4 = settingRepository1.GetAttr("SimplifyApplyCmd")
'--------------------------------------------------
' Parameter 1 : (String) "SimplifyApplyCmd"
' Returned value : (Variant) (Long) 0
'--------------------------------------------------

Dim bSTR10
bSTR10 = ""
Dim bSTR11
bSTR11 = ""
Dim boolean5
settingRepository1.GetAttrInfo "SimplifyApplyCmd", bSTR10, bSTR11, boolean5
'--------------------------------------------------
' Parameter 1 : (String) "SimplifyApplyCmd"
' Parameter 2 : (String) "Default value"
' Parameter 3 : (String) "Unlocked"
' Parameter 4 : (Boolean) False
'--------------------------------------------------

long5 = settingRepository1.GetAttr("VectorInApplyCmd")
'--------------------------------------------------
' Parameter 1 : (String) "VectorInApplyCmd"
' Returned value : (Variant) (Long) 0
'--------------------------------------------------

Dim bSTR12
bSTR12 = ""
Dim bSTR13
bSTR13 = ""
Dim boolean6
settingRepository1.GetAttrInfo "VectorInApplyCmd", bSTR12, bSTR13, boolean6
'--------------------------------------------------
' Parameter 1 : (String) "VectorInApplyCmd"
' Parameter 2 : (String) "Default value"
' Parameter 3 : (String) "Unlocked"
' Parameter 4 : (Boolean) False
'--------------------------------------------------

long6 = settingRepository1.GetAttr("LayerInApplyCmd")
'--------------------------------------------------
' Parameter 1 : (String) "LayerInApplyCmd"
' Returned value : (Variant) (Long) 0
'--------------------------------------------------

Dim bSTR14
bSTR14 = ""
Dim bSTR15
bSTR15 = ""
Dim boolean7
settingRepository1.GetAttrInfo "LayerInApplyCmd", bSTR14, bSTR15, boolean7
'--------------------------------------------------
' Parameter 1 : (String) "LayerInApplyCmd"
' Parameter 2 : (String) "Default value"
' Parameter 3 : (String) "Unlocked"
' Parameter 4 : (Boolean) False
'--------------------------------------------------

long7 = settingRepository1.GetAttr("CheckButtonAutoUpdateCnx")
'--------------------------------------------------
' Parameter 1 : (String) "CheckButtonAutoUpdateCnx"
' Returned value : (Variant) (Long) 0
'--------------------------------------------------

Dim bSTR16
bSTR16 = ""
Dim bSTR17
bSTR17 = ""
Dim boolean8
settingRepository1.GetAttrInfo "CheckButtonAutoUpdateCnx", bSTR16, bSTR17, boolean8
'--------------------------------------------------
' Parameter 1 : (String) "CheckButtonAutoUpdateCnx"
' Parameter 2 : (String) "Default value"
' Parameter 3 : (String) "Unlocked"
' Parameter 4 : (Boolean) False
'--------------------------------------------------

End Sub
