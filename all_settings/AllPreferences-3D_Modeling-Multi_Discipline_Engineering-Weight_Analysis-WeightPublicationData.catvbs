Language="VBSCRIPT"

Sub CATMain()

Set settingControllers1 = CATIA.SettingControllers

Set settingRepository1 = settingControllers1.Item("WeightSettings")

bSTR1 = settingRepository1.GetAttr("MaskFile")
'--------------------------------------------------
' Parameter 1 : (String) "MaskFile"
' Returned value : (Variant) (String) ""
'--------------------------------------------------

Dim bSTR2
bSTR2 = ""
Dim bSTR3
bSTR3 = ""
Dim boolean1
settingRepository1.GetAttrInfo "MaskFile", bSTR2, bSTR3, boolean1
'--------------------------------------------------
' Parameter 1 : (String) "MaskFile"
' Parameter 2 : (String) "Default value"
' Parameter 3 : (String) "Unlocked"
' Parameter 4 : (Boolean) False
'--------------------------------------------------

bSTR4 = settingRepository1.GetAttr("PublishedDirectory")
'--------------------------------------------------
' Parameter 1 : (String) "PublishedDirectory"
' Returned value : (Variant) (String) ""
'--------------------------------------------------

Dim bSTR5
bSTR5 = ""
Dim bSTR6
bSTR6 = ""
Dim boolean2
settingRepository1.GetAttrInfo "PublishedDirectory", bSTR5, bSTR6, boolean2
'--------------------------------------------------
' Parameter 1 : (String) "PublishedDirectory"
' Parameter 2 : (String) "Default value"
' Parameter 3 : (String) "Unlocked"
' Parameter 4 : (Boolean) False
'--------------------------------------------------

End Sub
