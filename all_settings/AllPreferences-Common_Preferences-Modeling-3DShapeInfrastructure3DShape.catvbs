Language="VBSCRIPT"

Sub CATMain()

Set settingControllers1 = CATIA.SettingControllers

Set settingRepository1 = settingControllers1.Item("3DShapeInfrastructure3DShape")

boolean1 = settingRepository1.GetAttr("ShowReferencePlanesMode")
'--------------------------------------------------
' Parameter 1 : (String) "ShowReferencePlanesMode"
' Returned value : (Variant) (Boolean) True
'--------------------------------------------------

Dim bSTR1
bSTR1 = ""
Dim bSTR2
bSTR2 = ""
Dim boolean2
settingRepository1.GetAttrInfo "ShowReferencePlanesMode", bSTR1, bSTR2, boolean2
'--------------------------------------------------
' Parameter 1 : (String) "ShowReferencePlanesMode"
' Parameter 2 : (String) "Default value"
' Parameter 3 : (String) "Unlocked"
' Parameter 4 : (Boolean) False
'--------------------------------------------------

boolean3 = settingRepository1.GetAttr("HybridDesignMode")
'--------------------------------------------------
' Parameter 1 : (String) "HybridDesignMode"
' Returned value : (Variant) (Boolean) True
'--------------------------------------------------

Dim bSTR3
bSTR3 = ""
Dim bSTR4
bSTR4 = ""
Dim boolean4
settingRepository1.GetAttrInfo "HybridDesignMode", bSTR3, bSTR4, boolean4
'--------------------------------------------------
' Parameter 1 : (String) "HybridDesignMode"
' Parameter 2 : (String) "Default value"
' Parameter 3 : (String) "Unlocked"
' Parameter 4 : (Boolean) False
'--------------------------------------------------

boolean5 = settingRepository1.GetAttr("KnowledgeInHybridDesignMode")
'--------------------------------------------------
' Parameter 1 : (String) "KnowledgeInHybridDesignMode"
' Returned value : (Variant) (Boolean) False
'--------------------------------------------------

Dim bSTR5
bSTR5 = ""
Dim bSTR6
bSTR6 = ""
Dim boolean6
settingRepository1.GetAttrInfo "KnowledgeInHybridDesignMode", bSTR5, bSTR6, boolean6
'--------------------------------------------------
' Parameter 1 : (String) "KnowledgeInHybridDesignMode"
' Parameter 2 : (String) "Default value"
' Parameter 3 : (String) "Unlocked"
' Parameter 4 : (Boolean) False
'--------------------------------------------------

short1 = settingRepository1.GetAttr("TesselationType")
'--------------------------------------------------
' Parameter 1 : (String) "TesselationType"
' Returned value : (Variant) (Short) 1
'--------------------------------------------------

Dim bSTR7
bSTR7 = ""
Dim bSTR8
bSTR8 = ""
Dim boolean7
settingRepository1.GetAttrInfo "TesselationType", bSTR7, bSTR8, boolean7
'--------------------------------------------------
' Parameter 1 : (String) "TesselationType"
' Parameter 2 : (String) "Default value"
' Parameter 3 : (String) "Unlocked"
' Parameter 4 : (Boolean) False
'--------------------------------------------------

double1 = settingRepository1.GetAttr("TesselationSag")
'--------------------------------------------------
' Parameter 1 : (String) "TesselationSag"
' Returned value : (Variant) (Double) 0.100000
'--------------------------------------------------

Dim bSTR9
bSTR9 = ""
Dim bSTR10
bSTR10 = ""
Dim boolean8
settingRepository1.GetAttrInfo "TesselationSag", bSTR9, bSTR10, boolean8
'--------------------------------------------------
' Parameter 1 : (String) "TesselationSag"
' Parameter 2 : (String) "Default value"
' Parameter 3 : (String) "Unlocked"
' Parameter 4 : (Boolean) False
'--------------------------------------------------

End Sub
