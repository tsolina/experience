Language="VBSCRIPT"

Sub CATMain()

Set settingControllers1 = CATIA.SettingControllers

Set settingRepository1 = settingControllers1.Item("RFLPNavigator")

Dim arrayOfVariantOfULong1
arrayOfVariantOfULong1 = settingRepository1.GetAttrArray("BackgroundColor")
'--------------------------------------------------
' Parameter 1 : (String) "BackgroundColor"
' Returned value : (Array) 
'    Array[0] : (Variant) (Unsigned Long) 212
'    Array[1] : (Variant) (Unsigned Long) 212
'    Array[2] : (Variant) (Unsigned Long) 223
'--------------------------------------------------

Dim bSTR1
bSTR1 = ""
Dim bSTR2
bSTR2 = ""
Dim boolean1
settingRepository1.GetAttrInfo "BackgroundColor", bSTR1, bSTR2, boolean1
'--------------------------------------------------
' Parameter 1 : (String) "BackgroundColor"
' Parameter 2 : (String) "Default value"
' Parameter 3 : (String) "Unlocked"
' Parameter 4 : (Boolean) False
'--------------------------------------------------

long1 = settingRepository1.GetAttr("NavigateWithPicture")
'--------------------------------------------------
' Parameter 1 : (String) "NavigateWithPicture"
' Returned value : (Variant) (Long) 1
'--------------------------------------------------

Dim bSTR3
bSTR3 = ""
Dim bSTR4
bSTR4 = ""
Dim boolean2
settingRepository1.GetAttrInfo "NavigateWithPicture", bSTR3, bSTR4, boolean2
'--------------------------------------------------
' Parameter 1 : (String) "NavigateWithPicture"
' Parameter 2 : (String) "Default value"
' Parameter 3 : (String) "Unlocked"
' Parameter 4 : (Boolean) False
'--------------------------------------------------

Set settingRepository2 = settingControllers1.Item("VPMNavigator")

boolean3 = settingRepository2.GetAttr("Navigation3D")
'--------------------------------------------------
' Parameter 1 : (String) "Navigation3D"
' Returned value : (Variant) (Boolean) True
'--------------------------------------------------

Dim bSTR5
bSTR5 = ""
Dim bSTR6
bSTR6 = ""
Dim boolean4
settingRepository2.GetAttrInfo "Navigation3D", bSTR5, bSTR6, boolean4
'--------------------------------------------------
' Parameter 1 : (String) "Navigation3D"
' Parameter 2 : (String) "Default value"
' Parameter 3 : (String) "Unlocked"
' Parameter 4 : (Boolean) False
'--------------------------------------------------

boolean5 = settingRepository2.GetAttr("Nav3DHD")
'--------------------------------------------------
' Parameter 1 : (String) "Nav3DHD"
' Returned value : (Variant) (Boolean) True
'--------------------------------------------------

Dim bSTR7
bSTR7 = ""
Dim bSTR8
bSTR8 = ""
Dim boolean6
settingRepository2.GetAttrInfo "Nav3DHD", bSTR7, bSTR8, boolean6
'--------------------------------------------------
' Parameter 1 : (String) "Nav3DHD"
' Parameter 2 : (String) "Default value"
' Parameter 3 : (String) "Unlocked"
' Parameter 4 : (Boolean) False
'--------------------------------------------------

uLong1 = settingRepository2.GetAttr("Nav3DHDDensityCV")
'--------------------------------------------------
' Parameter 1 : (String) "Nav3DHDDensityCV"
' Returned value : (Variant) (Unsigned Long) 5
'--------------------------------------------------

Dim bSTR9
bSTR9 = ""
Dim bSTR10
bSTR10 = ""
Dim boolean7
settingRepository2.GetAttrInfo "Nav3DHDDensityCV", bSTR9, bSTR10, boolean7
'--------------------------------------------------
' Parameter 1 : (String) "Nav3DHDDensityCV"
' Parameter 2 : (String) "Default value"
' Parameter 3 : (String) "Unlocked"
' Parameter 4 : (Boolean) False
'--------------------------------------------------

uLong2 = settingRepository2.GetAttr("Nav3DHDDensityCVCloud")
'--------------------------------------------------
' Parameter 1 : (String) "Nav3DHDDensityCVCloud"
' Returned value : (Variant) (Unsigned Long) 1
'--------------------------------------------------

Dim bSTR11
bSTR11 = ""
Dim bSTR12
bSTR12 = ""
Dim boolean8
settingRepository2.GetAttrInfo "Nav3DHDDensityCVCloud", bSTR11, bSTR12, boolean8
'--------------------------------------------------
' Parameter 1 : (String) "Nav3DHDDensityCVCloud"
' Parameter 2 : (String) "Default value"
' Parameter 3 : (String) "Unlocked"
' Parameter 4 : (Boolean) False
'--------------------------------------------------

boolean9 = settingRepository2.GetAttr("NoMultiRep")
'--------------------------------------------------
' Parameter 1 : (String) "NoMultiRep"
' Returned value : (Variant) (Boolean) False
'--------------------------------------------------

Dim bSTR13
bSTR13 = ""
Dim bSTR14
bSTR14 = ""
Dim boolean10
settingRepository2.GetAttrInfo "NoMultiRep", bSTR13, bSTR14, boolean10
'--------------------------------------------------
' Parameter 1 : (String) "NoMultiRep"
' Parameter 2 : (String) "Default value"
' Parameter 3 : (String) "Unlocked"
' Parameter 4 : (Boolean) False
'--------------------------------------------------

uLong3 = settingRepository2.GetAttr("3DSearchMaxItemsBeforeWarn")
'--------------------------------------------------
' Parameter 1 : (String) "3DSearchMaxItemsBeforeWarn"
' Returned value : (Variant) (Unsigned Long) 0
'--------------------------------------------------

Dim bSTR15
bSTR15 = ""
Dim bSTR16
bSTR16 = ""
Dim boolean11
settingRepository2.GetAttrInfo "3DSearchMaxItemsBeforeWarn", bSTR15, bSTR16, boolean11
'--------------------------------------------------
' Parameter 1 : (String) "3DSearchMaxItemsBeforeWarn"
' Parameter 2 : (String) "Default value"
' Parameter 3 : (String) "Unlocked"
' Parameter 4 : (Boolean) False
'--------------------------------------------------

boolean12 = settingRepository2.GetAttr("AntiZFighting")
'--------------------------------------------------
' Parameter 1 : (String) "AntiZFighting"
' Returned value : (Variant) (Boolean) False
'--------------------------------------------------

Dim bSTR17
bSTR17 = ""
Dim bSTR18
bSTR18 = ""
Dim boolean13
settingRepository2.GetAttrInfo "AntiZFighting", bSTR17, bSTR18, boolean13
'--------------------------------------------------
' Parameter 1 : (String) "AntiZFighting"
' Parameter 2 : (String) "Default value"
' Parameter 3 : (String) "Unlocked"
' Parameter 4 : (Boolean) False
'--------------------------------------------------

long2 = settingRepository2.GetAttr("TurntableReframe")
'--------------------------------------------------
' Parameter 1 : (String) "TurntableReframe"
' Returned value : (Variant) (Long) 1
'--------------------------------------------------

Dim bSTR19
bSTR19 = ""
Dim bSTR20
bSTR20 = ""
Dim boolean14
settingRepository2.GetAttrInfo "TurntableReframe", bSTR19, bSTR20, boolean14
'--------------------------------------------------
' Parameter 1 : (String) "TurntableReframe"
' Parameter 2 : (String) "Default value"
' Parameter 3 : (String) "Unlocked"
' Parameter 4 : (Boolean) False
'--------------------------------------------------

long3 = settingRepository2.GetAttr("TurntableAnimation")
'--------------------------------------------------
' Parameter 1 : (String) "TurntableAnimation"
' Returned value : (Variant) (Long) 1
'--------------------------------------------------

Dim bSTR21
bSTR21 = ""
Dim bSTR22
bSTR22 = ""
Dim boolean15
settingRepository2.GetAttrInfo "TurntableAnimation", bSTR21, bSTR22, boolean15
'--------------------------------------------------
' Parameter 1 : (String) "TurntableAnimation"
' Parameter 2 : (String) "Default value"
' Parameter 3 : (String) "Unlocked"
' Parameter 4 : (Boolean) False
'--------------------------------------------------

boolean16 = settingRepository2.GetAttr("Navigation3D")
'--------------------------------------------------
' Parameter 1 : (String) "Navigation3D"
' Returned value : (Variant) (Boolean) True
'--------------------------------------------------

Dim bSTR23
bSTR23 = ""
Dim bSTR24
bSTR24 = ""
Dim boolean17
settingRepository2.GetAttrInfo "Navigation3D", bSTR23, bSTR24, boolean17
'--------------------------------------------------
' Parameter 1 : (String) "Navigation3D"
' Parameter 2 : (String) "Default value"
' Parameter 3 : (String) "Unlocked"
' Parameter 4 : (Boolean) False
'--------------------------------------------------

boolean18 = settingRepository2.GetAttr("NavRepOrNothing")
'--------------------------------------------------
' Parameter 1 : (String) "NavRepOrNothing"
' Returned value : (Variant) (Boolean) True
'--------------------------------------------------

Dim bSTR25
bSTR25 = ""
Dim bSTR26
bSTR26 = ""
Dim boolean19
settingRepository2.GetAttrInfo "NavRepOrNothing", bSTR25, bSTR26, boolean19
'--------------------------------------------------
' Parameter 1 : (String) "NavRepOrNothing"
' Parameter 2 : (String) "Default value"
' Parameter 3 : (String) "Unlocked"
' Parameter 4 : (Boolean) False
'--------------------------------------------------

boolean20 = settingRepository2.GetAttr("Navigation3D")
'--------------------------------------------------
' Parameter 1 : (String) "Navigation3D"
' Returned value : (Variant) (Boolean) True
'--------------------------------------------------

Dim bSTR27
bSTR27 = ""
Dim bSTR28
bSTR28 = ""
Dim boolean21
settingRepository2.GetAttrInfo "Navigation3D", bSTR27, bSTR28, boolean21
'--------------------------------------------------
' Parameter 1 : (String) "Navigation3D"
' Parameter 2 : (String) "Default value"
' Parameter 3 : (String) "Unlocked"
' Parameter 4 : (Boolean) False
'--------------------------------------------------

End Sub
