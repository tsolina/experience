Language="VBSCRIPT"

Sub CATMain()

Set settingControllers1 = CATIA.SettingControllers

Set settingRepository1 = settingControllers1.Item("SMAWflUISettings")

long1 = settingRepository1.GetAttr("DefaultLoggingLevel")
'--------------------------------------------------
' Parameter 1 : (String) "DefaultLoggingLevel"
' Returned value : (Variant) (Long) 1
'--------------------------------------------------

Dim bSTR1
bSTR1 = ""
Dim bSTR2
bSTR2 = ""
Dim boolean1
settingRepository1.GetAttrInfo "DefaultLoggingLevel", bSTR1, bSTR2, boolean1
'--------------------------------------------------
' Parameter 1 : (String) "DefaultLoggingLevel"
' Parameter 2 : (String) "Default value"
' Parameter 3 : (String) "Unlocked"
' Parameter 4 : (Boolean) False
'--------------------------------------------------

bSTR3 = settingRepository1.GetAttr("tenantID")
'--------------------------------------------------
' Parameter 1 : (String) "tenantID"
' Returned value : (Variant) (String) ""
'--------------------------------------------------

Dim bSTR4
bSTR4 = ""
Dim bSTR5
bSTR5 = ""
Dim boolean2
settingRepository1.GetAttrInfo "tenantID", bSTR4, bSTR5, boolean2
'--------------------------------------------------
' Parameter 1 : (String) "tenantID"
' Parameter 2 : (String) "Default value"
' Parameter 3 : (String) "Unlocked"
' Parameter 4 : (Boolean) False
'--------------------------------------------------

long2 = settingRepository1.GetAttr("LicensingScheme")
'--------------------------------------------------
' Parameter 1 : (String) "LicensingScheme"
' Returned value : (Variant) (Long) 0
'--------------------------------------------------

Dim bSTR6
bSTR6 = ""
Dim bSTR7
bSTR7 = ""
Dim boolean3
settingRepository1.GetAttrInfo "LicensingScheme", bSTR6, bSTR7, boolean3
'--------------------------------------------------
' Parameter 1 : (String) "LicensingScheme"
' Parameter 2 : (String) "Default value"
' Parameter 3 : (String) "Unlocked"
' Parameter 4 : (Boolean) False
'--------------------------------------------------

long3 = settingRepository1.GetAttr("RandomSeedFlag")
'--------------------------------------------------
' Parameter 1 : (String) "RandomSeedFlag"
' Returned value : (Variant) (Long) 0
'--------------------------------------------------

Dim bSTR8
bSTR8 = ""
Dim bSTR9
bSTR9 = ""
Dim boolean4
settingRepository1.GetAttrInfo "RandomSeedFlag", bSTR8, bSTR9, boolean4
'--------------------------------------------------
' Parameter 1 : (String) "RandomSeedFlag"
' Parameter 2 : (String) "Default value"
' Parameter 3 : (String) "Unlocked"
' Parameter 4 : (Boolean) False
'--------------------------------------------------

long4 = settingRepository1.GetAttr("RandomSeedValue")
'--------------------------------------------------
' Parameter 1 : (String) "RandomSeedValue"
' Returned value : (Variant) (Long) 0
'--------------------------------------------------

Dim bSTR10
bSTR10 = ""
Dim bSTR11
bSTR11 = ""
Dim boolean5
settingRepository1.GetAttrInfo "RandomSeedValue", bSTR10, bSTR11, boolean5
'--------------------------------------------------
' Parameter 1 : (String) "RandomSeedValue"
' Parameter 2 : (String) "Default value"
' Parameter 3 : (String) "Unlocked"
' Parameter 4 : (Boolean) False
'--------------------------------------------------

End Sub
