Language="VBSCRIPT"

Sub CATMain()

Set settingControllers1 = CATIA.SettingControllers

Set settingRepository1 = settingControllers1.Item("ElectricalHarnessInstallation")

long1 = settingRepository1.GetAttr("ElecAttrPropOption")
'--------------------------------------------------
' Parameter 1 : (String) "ElecAttrPropOption"
' Returned value : (Variant) (Long) 0
'--------------------------------------------------

Dim bSTR1
bSTR1 = ""
Dim bSTR2
bSTR2 = ""
Dim boolean1
settingRepository1.GetAttrInfo "ElecAttrPropOption", bSTR1, bSTR2, boolean1
'--------------------------------------------------
' Parameter 1 : (String) "ElecAttrPropOption"
' Parameter 2 : (String) "Default value"
' Parameter 3 : (String) "Unlocked"
' Parameter 4 : (Boolean) False
'--------------------------------------------------

long2 = settingRepository1.GetAttr("OnlyElecAttrProp")
'--------------------------------------------------
' Parameter 1 : (String) "OnlyElecAttrProp"
' Returned value : (Variant) (Long) 0
'--------------------------------------------------

Dim bSTR3
bSTR3 = ""
Dim bSTR4
bSTR4 = ""
Dim boolean2
settingRepository1.GetAttrInfo "OnlyElecAttrProp", bSTR3, bSTR4, boolean2
'--------------------------------------------------
' Parameter 1 : (String) "OnlyElecAttrProp"
' Parameter 2 : (String) "Default value"
' Parameter 3 : (String) "Unlocked"
' Parameter 4 : (Boolean) False
'--------------------------------------------------

End Sub
