Language="VBSCRIPT"

Sub CATMain()

Set settingControllers1 = CATIA.SettingControllers

Set settingRepository1 = settingControllers1.Item("DELSweptVolSettings")

double1 = settingRepository1.GetAttr("ExecStepSize")
'--------------------------------------------------
' Parameter 1 : (String) "ExecStepSize"
' Returned value : (Variant) (Double) 0.100000
'--------------------------------------------------

Dim bSTR1
bSTR1 = ""
Dim bSTR2
bSTR2 = ""
Dim boolean1
settingRepository1.GetAttrInfo "ExecStepSize", bSTR1, bSTR2, boolean1
'--------------------------------------------------
' Parameter 1 : (String) "ExecStepSize"
' Parameter 2 : (String) "Default value"
' Parameter 3 : (String) "Unlocked"
' Parameter 4 : (Boolean) False
'--------------------------------------------------

uLong1 = settingRepository1.GetAttr("SweepStartOperIndexStat")
'--------------------------------------------------
' Parameter 1 : (String) "SweepStartOperIndexStat"
' Returned value : (Variant) (Unsigned Long) 0
'--------------------------------------------------

Dim bSTR3
bSTR3 = ""
Dim bSTR4
bSTR4 = ""
Dim boolean2
settingRepository1.GetAttrInfo "SweepStartOperIndexStat", bSTR3, bSTR4, boolean2
'--------------------------------------------------
' Parameter 1 : (String) "SweepStartOperIndexStat"
' Parameter 2 : (String) "Default value"
' Parameter 3 : (String) "Unlocked"
' Parameter 4 : (Boolean) False
'--------------------------------------------------

Dim arrayOfVariantOfULong1
arrayOfVariantOfULong1 = settingRepository1.GetAttrArray("ExecSweepColor")
'--------------------------------------------------
' Parameter 1 : (String) "ExecSweepColor"
' Returned value : (Array) 
'    Array[0] : (Variant) (Unsigned Long) 255
'    Array[1] : (Variant) (Unsigned Long) 0
'    Array[2] : (Variant) (Unsigned Long) 0
'--------------------------------------------------

Dim bSTR5
bSTR5 = ""
Dim bSTR6
bSTR6 = ""
Dim boolean3
settingRepository1.GetAttrInfo "ExecSweepColor", bSTR5, bSTR6, boolean3
'--------------------------------------------------
' Parameter 1 : (String) "ExecSweepColor"
' Parameter 2 : (String) "Default value"
' Parameter 3 : (String) "Unlocked"
' Parameter 4 : (Boolean) False
'--------------------------------------------------

uLong2 = settingRepository1.GetAttr("ExecSweepTransp")
'--------------------------------------------------
' Parameter 1 : (String) "ExecSweepTransp"
' Returned value : (Variant) (Unsigned Long) 125
'--------------------------------------------------

Dim bSTR7
bSTR7 = ""
Dim bSTR8
bSTR8 = ""
Dim boolean4
settingRepository1.GetAttrInfo "ExecSweepTransp", bSTR7, bSTR8, boolean4
'--------------------------------------------------
' Parameter 1 : (String) "ExecSweepTransp"
' Parameter 2 : (String) "Default value"
' Parameter 3 : (String) "Unlocked"
' Parameter 4 : (Boolean) False
'--------------------------------------------------

uLong3 = settingRepository1.GetAttr("OperSweepsStat")
'--------------------------------------------------
' Parameter 1 : (String) "OperSweepsStat"
' Returned value : (Variant) (Unsigned Long) 0
'--------------------------------------------------

Dim bSTR9
bSTR9 = ""
Dim bSTR10
bSTR10 = ""
Dim boolean5
settingRepository1.GetAttrInfo "OperSweepsStat", bSTR9, bSTR10, boolean5
'--------------------------------------------------
' Parameter 1 : (String) "OperSweepsStat"
' Parameter 2 : (String) "Default value"
' Parameter 3 : (String) "Unlocked"
' Parameter 4 : (Boolean) False
'--------------------------------------------------

uLong4 = settingRepository1.GetAttr("SingleSweepStat")
'--------------------------------------------------
' Parameter 1 : (String) "SingleSweepStat"
' Returned value : (Variant) (Unsigned Long) 0
'--------------------------------------------------

Dim bSTR11
bSTR11 = ""
Dim bSTR12
bSTR12 = ""
Dim boolean6
settingRepository1.GetAttrInfo "SingleSweepStat", bSTR11, bSTR12, boolean6
'--------------------------------------------------
' Parameter 1 : (String) "SingleSweepStat"
' Parameter 2 : (String) "Default value"
' Parameter 3 : (String) "Unlocked"
' Parameter 4 : (Boolean) False
'--------------------------------------------------

double2 = settingRepository1.GetAttr("SweepMemoryThreshold")
'--------------------------------------------------
' Parameter 1 : (String) "SweepMemoryThreshold"
' Returned value : (Variant) (Double) 5.000000
'--------------------------------------------------

Dim bSTR13
bSTR13 = ""
Dim bSTR14
bSTR14 = ""
Dim boolean7
settingRepository1.GetAttrInfo "SweepMemoryThreshold", bSTR13, bSTR14, boolean7
'--------------------------------------------------
' Parameter 1 : (String) "SweepMemoryThreshold"
' Parameter 2 : (String) "Default value"
' Parameter 3 : (String) "Unlocked"
' Parameter 4 : (Boolean) False
'--------------------------------------------------

uLong5 = settingRepository1.GetAttr("PosPrecisionStat")
'--------------------------------------------------
' Parameter 1 : (String) "PosPrecisionStat"
' Returned value : (Variant) (Unsigned Long) 1
'--------------------------------------------------

Dim bSTR15
bSTR15 = ""
Dim bSTR16
bSTR16 = ""
Dim boolean8
settingRepository1.GetAttrInfo "PosPrecisionStat", bSTR15, bSTR16, boolean8
'--------------------------------------------------
' Parameter 1 : (String) "PosPrecisionStat"
' Parameter 2 : (String) "Default value"
' Parameter 3 : (String) "Unlocked"
' Parameter 4 : (Boolean) False
'--------------------------------------------------

double3 = settingRepository1.GetAttr("PosPrecisionVal")
'--------------------------------------------------
' Parameter 1 : (String) "PosPrecisionVal"
' Returned value : (Variant) (Double) 0.200000
'--------------------------------------------------

Dim bSTR17
bSTR17 = ""
Dim bSTR18
bSTR18 = ""
Dim boolean9
settingRepository1.GetAttrInfo "PosPrecisionVal", bSTR17, bSTR18, boolean9
'--------------------------------------------------
' Parameter 1 : (String) "PosPrecisionVal"
' Parameter 2 : (String) "Default value"
' Parameter 3 : (String) "Unlocked"
' Parameter 4 : (Boolean) False
'--------------------------------------------------

uLong6 = settingRepository1.GetAttr("WrapGrainStat")
'--------------------------------------------------
' Parameter 1 : (String) "WrapGrainStat"
' Returned value : (Variant) (Unsigned Long) 1
'--------------------------------------------------

Dim bSTR19
bSTR19 = ""
Dim bSTR20
bSTR20 = ""
Dim boolean10
settingRepository1.GetAttrInfo "WrapGrainStat", bSTR19, bSTR20, boolean10
'--------------------------------------------------
' Parameter 1 : (String) "WrapGrainStat"
' Parameter 2 : (String) "Default value"
' Parameter 3 : (String) "Unlocked"
' Parameter 4 : (Boolean) False
'--------------------------------------------------

double4 = settingRepository1.GetAttr("WrapGrainVal")
'--------------------------------------------------
' Parameter 1 : (String) "WrapGrainVal"
' Returned value : (Variant) (Double) 50.000000
'--------------------------------------------------

Dim bSTR21
bSTR21 = ""
Dim bSTR22
bSTR22 = ""
Dim boolean11
settingRepository1.GetAttrInfo "WrapGrainVal", bSTR21, bSTR22, boolean11
'--------------------------------------------------
' Parameter 1 : (String) "WrapGrainVal"
' Parameter 2 : (String) "Default value"
' Parameter 3 : (String) "Unlocked"
' Parameter 4 : (Boolean) False
'--------------------------------------------------

uLong7 = settingRepository1.GetAttr("AccuracyStat")
'--------------------------------------------------
' Parameter 1 : (String) "AccuracyStat"
' Returned value : (Variant) (Unsigned Long) 0
'--------------------------------------------------

Dim bSTR23
bSTR23 = ""
Dim bSTR24
bSTR24 = ""
Dim boolean12
settingRepository1.GetAttrInfo "AccuracyStat", bSTR23, bSTR24, boolean12
'--------------------------------------------------
' Parameter 1 : (String) "AccuracyStat"
' Parameter 2 : (String) "Default value"
' Parameter 3 : (String) "Unlocked"
' Parameter 4 : (Boolean) False
'--------------------------------------------------

double5 = settingRepository1.GetAttr("AccuracyVal")
'--------------------------------------------------
' Parameter 1 : (String) "AccuracyVal"
' Returned value : (Variant) (Double) 5.000000
'--------------------------------------------------

Dim bSTR25
bSTR25 = ""
Dim bSTR26
bSTR26 = ""
Dim boolean13
settingRepository1.GetAttrInfo "AccuracyVal", bSTR25, bSTR26, boolean13
'--------------------------------------------------
' Parameter 1 : (String) "AccuracyVal"
' Parameter 2 : (String) "Default value"
' Parameter 3 : (String) "Unlocked"
' Parameter 4 : (Boolean) False
'--------------------------------------------------

End Sub
