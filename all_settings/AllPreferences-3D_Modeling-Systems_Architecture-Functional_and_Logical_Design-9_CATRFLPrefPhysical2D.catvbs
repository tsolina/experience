Language="VBSCRIPT"

Sub CATMain()

Set settingControllers1 = CATIA.SettingControllers

Set settingRepository1 = settingControllers1.Item("PLMEditorColor")

Dim arrayOfVariantOfULong1
arrayOfVariantOfULong1 = settingRepository1.GetAttrArray("Physical2DRepFillColor")
'--------------------------------------------------
' Parameter 1 : (String) "Physical2DRepFillColor"
' Returned value : (Array) 
'    Array[0] : (Variant) (Unsigned Long) 148
'    Array[1] : (Variant) (Unsigned Long) 148
'    Array[2] : (Variant) (Unsigned Long) 148
'--------------------------------------------------

Dim bSTR1
bSTR1 = ""
Dim bSTR2
bSTR2 = ""
Dim boolean1
settingRepository1.GetAttrInfo "Physical2DRepFillColor", bSTR1, bSTR2, boolean1
'--------------------------------------------------
' Parameter 1 : (String) "Physical2DRepFillColor"
' Parameter 2 : (String) "Default value"
' Parameter 3 : (String) "Unlocked"
' Parameter 4 : (Boolean) False
'--------------------------------------------------

uLong1 = settingRepository1.GetAttr("Physical2DRepFillTransparency")
'--------------------------------------------------
' Parameter 1 : (String) "Physical2DRepFillTransparency"
' Returned value : (Variant) (Unsigned Long) 70
'--------------------------------------------------

Dim bSTR3
bSTR3 = ""
Dim bSTR4
bSTR4 = ""
Dim boolean2
settingRepository1.GetAttrInfo "Physical2DRepFillTransparency", bSTR3, bSTR4, boolean2
'--------------------------------------------------
' Parameter 1 : (String) "Physical2DRepFillTransparency"
' Parameter 2 : (String) "Default value"
' Parameter 3 : (String) "Unlocked"
' Parameter 4 : (Boolean) False
'--------------------------------------------------

Dim arrayOfVariantOfULong2
arrayOfVariantOfULong2 = settingRepository1.GetAttrArray("Physical2DRepLineColor")
'--------------------------------------------------
' Parameter 1 : (String) "Physical2DRepLineColor"
' Returned value : (Array) 
'    Array[0] : (Variant) (Unsigned Long) 65
'    Array[1] : (Variant) (Unsigned Long) 92
'    Array[2] : (Variant) (Unsigned Long) 108
'--------------------------------------------------

Dim bSTR5
bSTR5 = ""
Dim bSTR6
bSTR6 = ""
Dim boolean3
settingRepository1.GetAttrInfo "Physical2DRepLineColor", bSTR5, bSTR6, boolean3
'--------------------------------------------------
' Parameter 1 : (String) "Physical2DRepLineColor"
' Parameter 2 : (String) "Default value"
' Parameter 3 : (String) "Unlocked"
' Parameter 4 : (Boolean) False
'--------------------------------------------------

uLong2 = settingRepository1.GetAttr("Physical2DRepLineType")
'--------------------------------------------------
' Parameter 1 : (String) "Physical2DRepLineType"
' Returned value : (Variant) (Unsigned Long) 1
'--------------------------------------------------

Dim bSTR7
bSTR7 = ""
Dim bSTR8
bSTR8 = ""
Dim boolean4
settingRepository1.GetAttrInfo "Physical2DRepLineType", bSTR7, bSTR8, boolean4
'--------------------------------------------------
' Parameter 1 : (String) "Physical2DRepLineType"
' Parameter 2 : (String) "Default value"
' Parameter 3 : (String) "Unlocked"
' Parameter 4 : (Boolean) False
'--------------------------------------------------

uLong3 = settingRepository1.GetAttr("Physical2DRepLineWeight")
'--------------------------------------------------
' Parameter 1 : (String) "Physical2DRepLineWeight"
' Returned value : (Variant) (Unsigned Long) 1
'--------------------------------------------------

Dim bSTR9
bSTR9 = ""
Dim bSTR10
bSTR10 = ""
Dim boolean5
settingRepository1.GetAttrInfo "Physical2DRepLineWeight", bSTR9, bSTR10, boolean5
'--------------------------------------------------
' Parameter 1 : (String) "Physical2DRepLineWeight"
' Parameter 2 : (String) "Default value"
' Parameter 3 : (String) "Unlocked"
' Parameter 4 : (Boolean) False
'--------------------------------------------------

Dim arrayOfVariantOfULong3
arrayOfVariantOfULong3 = settingRepository1.GetAttrArray("Physical2DRepTextFillColor")
'--------------------------------------------------
' Parameter 1 : (String) "Physical2DRepTextFillColor"
' Returned value : (Array) 
'    Array[0] : (Variant) (Unsigned Long) 0
'    Array[1] : (Variant) (Unsigned Long) 51
'    Array[2] : (Variant) (Unsigned Long) 0
'--------------------------------------------------

Dim bSTR11
bSTR11 = ""
Dim bSTR12
bSTR12 = ""
Dim boolean6
settingRepository1.GetAttrInfo "Physical2DRepTextFillColor", bSTR11, bSTR12, boolean6
'--------------------------------------------------
' Parameter 1 : (String) "Physical2DRepTextFillColor"
' Parameter 2 : (String) "Default value"
' Parameter 3 : (String) "Unlocked"
' Parameter 4 : (Boolean) False
'--------------------------------------------------

uLong4 = settingRepository1.GetAttr("Physical2DRepTextFillTransparency")
'--------------------------------------------------
' Parameter 1 : (String) "Physical2DRepTextFillTransparency"
' Returned value : (Variant) (Unsigned Long) 0
'--------------------------------------------------

Dim bSTR13
bSTR13 = ""
Dim bSTR14
bSTR14 = ""
Dim boolean7
settingRepository1.GetAttrInfo "Physical2DRepTextFillTransparency", bSTR13, bSTR14, boolean7
'--------------------------------------------------
' Parameter 1 : (String) "Physical2DRepTextFillTransparency"
' Parameter 2 : (String) "Default value"
' Parameter 3 : (String) "Unlocked"
' Parameter 4 : (Boolean) False
'--------------------------------------------------

Dim arrayOfVariantOfULong4
arrayOfVariantOfULong4 = settingRepository1.GetAttrArray("Physical2DRepTextFontColor")
'--------------------------------------------------
' Parameter 1 : (String) "Physical2DRepTextFontColor"
' Returned value : (Array) 
'    Array[0] : (Variant) (Unsigned Long) 255
'    Array[1] : (Variant) (Unsigned Long) 255
'    Array[2] : (Variant) (Unsigned Long) 255
'--------------------------------------------------

Dim bSTR15
bSTR15 = ""
Dim bSTR16
bSTR16 = ""
Dim boolean8
settingRepository1.GetAttrInfo "Physical2DRepTextFontColor", bSTR15, bSTR16, boolean8
'--------------------------------------------------
' Parameter 1 : (String) "Physical2DRepTextFontColor"
' Parameter 2 : (String) "Default value"
' Parameter 3 : (String) "Unlocked"
' Parameter 4 : (Boolean) False
'--------------------------------------------------

uLong5 = settingRepository1.GetAttr("Physical2DRepTextPosition")
'--------------------------------------------------
' Parameter 1 : (String) "Physical2DRepTextPosition"
' Returned value : (Variant) (Unsigned Long) 0
'--------------------------------------------------

Dim bSTR17
bSTR17 = ""
Dim bSTR18
bSTR18 = ""
Dim boolean9
settingRepository1.GetAttrInfo "Physical2DRepTextPosition", bSTR17, bSTR18, boolean9
'--------------------------------------------------
' Parameter 1 : (String) "Physical2DRepTextPosition"
' Parameter 2 : (String) "Default value"
' Parameter 3 : (String) "Unlocked"
' Parameter 4 : (Boolean) False
'--------------------------------------------------

uLong6 = settingRepository1.GetAttr("Physical2DRepTextFontSize")
'--------------------------------------------------
' Parameter 1 : (String) "Physical2DRepTextFontSize"
' Returned value : (Variant) (Unsigned Long) 4
'--------------------------------------------------

Dim bSTR19
bSTR19 = ""
Dim bSTR20
bSTR20 = ""
Dim boolean10
settingRepository1.GetAttrInfo "Physical2DRepTextFontSize", bSTR19, bSTR20, boolean10
'--------------------------------------------------
' Parameter 1 : (String) "Physical2DRepTextFontSize"
' Parameter 2 : (String) "Default value"
' Parameter 3 : (String) "Unlocked"
' Parameter 4 : (Boolean) False
'--------------------------------------------------

End Sub
