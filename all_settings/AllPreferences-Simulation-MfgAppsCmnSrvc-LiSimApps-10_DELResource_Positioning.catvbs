Language="VBSCRIPT"

Sub CATMain()

Set settingControllers1 = CATIA.SettingControllers

Set settingRepository1 = settingControllers1.Item("DNBMfgLayoutSettings")

uLong1 = settingRepository1.GetAttr("SnapPreview")
'--------------------------------------------------
' Parameter 1 : (String) "SnapPreview"
' Returned value : (Variant) (Unsigned Long) 1
'--------------------------------------------------

Dim bSTR1
bSTR1 = ""
Dim bSTR2
bSTR2 = ""
Dim boolean1
settingRepository1.GetAttrInfo "SnapPreview", bSTR1, bSTR2, boolean1
'--------------------------------------------------
' Parameter 1 : (String) "SnapPreview"
' Parameter 2 : (String) "Default value"
' Parameter 3 : (String) "Unlocked"
' Parameter 4 : (Boolean) False
'--------------------------------------------------

uLong2 = settingRepository1.GetAttr("AdvancedSnap")
'--------------------------------------------------
' Parameter 1 : (String) "AdvancedSnap"
' Returned value : (Variant) (Unsigned Long) 0
'--------------------------------------------------

Dim bSTR3
bSTR3 = ""
Dim bSTR4
bSTR4 = ""
Dim boolean2
settingRepository1.GetAttrInfo "AdvancedSnap", bSTR3, bSTR4, boolean2
'--------------------------------------------------
' Parameter 1 : (String) "AdvancedSnap"
' Parameter 2 : (String) "Default value"
' Parameter 3 : (String) "Unlocked"
' Parameter 4 : (Boolean) False
'--------------------------------------------------

uLong3 = settingRepository1.GetAttr("ObjectPositioningNew")
'--------------------------------------------------
' Parameter 1 : (String) "ObjectPositioningNew"
' Returned value : (Variant) (Unsigned Long) 1
'--------------------------------------------------

Dim bSTR5
bSTR5 = ""
Dim bSTR6
bSTR6 = ""
Dim boolean3
settingRepository1.GetAttrInfo "ObjectPositioningNew", bSTR5, bSTR6, boolean3
'--------------------------------------------------
' Parameter 1 : (String) "ObjectPositioningNew"
' Parameter 2 : (String) "Default value"
' Parameter 3 : (String) "Unlocked"
' Parameter 4 : (Boolean) False
'--------------------------------------------------

bSTR7 = settingRepository1.GetAttr("ObjectPositioningPreference")
'--------------------------------------------------
' Parameter 1 : (String) "ObjectPositioningPreference"
' Returned value : (Variant) (String) "UseComponentOrigin"
'--------------------------------------------------

Dim bSTR8
bSTR8 = ""
Dim bSTR9
bSTR9 = ""
Dim boolean4
settingRepository1.GetAttrInfo "ObjectPositioningPreference", bSTR8, bSTR9, boolean4
'--------------------------------------------------
' Parameter 1 : (String) "ObjectPositioningPreference"
' Parameter 2 : (String) "Default value"
' Parameter 3 : (String) "Unlocked"
' Parameter 4 : (Boolean) False
'--------------------------------------------------

uLong4 = settingRepository1.GetAttr("LocatorMechPort")
'--------------------------------------------------
' Parameter 1 : (String) "LocatorMechPort"
' Returned value : (Variant) (Unsigned Long) 1
'--------------------------------------------------

Dim bSTR10
bSTR10 = ""
Dim bSTR11
bSTR11 = ""
Dim boolean5
settingRepository1.GetAttrInfo "LocatorMechPort", bSTR10, bSTR11, boolean5
'--------------------------------------------------
' Parameter 1 : (String) "LocatorMechPort"
' Parameter 2 : (String) "Default value"
' Parameter 3 : (String) "Unlocked"
' Parameter 4 : (Boolean) False
'--------------------------------------------------

uLong5 = settingRepository1.GetAttr("SmartSnapConstraint")
'--------------------------------------------------
' Parameter 1 : (String) "SmartSnapConstraint"
' Returned value : (Variant) (Unsigned Long) 1
'--------------------------------------------------

Dim bSTR12
bSTR12 = ""
Dim bSTR13
bSTR13 = ""
Dim boolean6
settingRepository1.GetAttrInfo "SmartSnapConstraint", bSTR12, bSTR13, boolean6
'--------------------------------------------------
' Parameter 1 : (String) "SmartSnapConstraint"
' Parameter 2 : (String) "Default value"
' Parameter 3 : (String) "Unlocked"
' Parameter 4 : (Boolean) False
'--------------------------------------------------

uLong6 = settingRepository1.GetAttr("SmartSnapAxisRed")
'--------------------------------------------------
' Parameter 1 : (String) "SmartSnapAxisRed"
' Returned value : (Variant) (Unsigned Long) 255
'--------------------------------------------------

Dim bSTR14
bSTR14 = ""
Dim bSTR15
bSTR15 = ""
Dim boolean7
settingRepository1.GetAttrInfo "SmartSnapAxisRed", bSTR14, bSTR15, boolean7
'--------------------------------------------------
' Parameter 1 : (String) "SmartSnapAxisRed"
' Parameter 2 : (String) "Default value"
' Parameter 3 : (String) "Unlocked"
' Parameter 4 : (Boolean) False
'--------------------------------------------------

uLong7 = settingRepository1.GetAttr("SmartSnapAxisGreen")
'--------------------------------------------------
' Parameter 1 : (String) "SmartSnapAxisGreen"
' Returned value : (Variant) (Unsigned Long) 0
'--------------------------------------------------

Dim bSTR16
bSTR16 = ""
Dim bSTR17
bSTR17 = ""
Dim boolean8
settingRepository1.GetAttrInfo "SmartSnapAxisGreen", bSTR16, bSTR17, boolean8
'--------------------------------------------------
' Parameter 1 : (String) "SmartSnapAxisGreen"
' Parameter 2 : (String) "Default value"
' Parameter 3 : (String) "Unlocked"
' Parameter 4 : (Boolean) False
'--------------------------------------------------

uLong8 = settingRepository1.GetAttr("SmartSnapAxisBlue")
'--------------------------------------------------
' Parameter 1 : (String) "SmartSnapAxisBlue"
' Returned value : (Variant) (Unsigned Long) 0
'--------------------------------------------------

Dim bSTR18
bSTR18 = ""
Dim bSTR19
bSTR19 = ""
Dim boolean9
settingRepository1.GetAttrInfo "SmartSnapAxisBlue", bSTR18, bSTR19, boolean9
'--------------------------------------------------
' Parameter 1 : (String) "SmartSnapAxisBlue"
' Parameter 2 : (String) "Default value"
' Parameter 3 : (String) "Unlocked"
' Parameter 4 : (Boolean) False
'--------------------------------------------------

uLong9 = settingRepository1.GetAttr("ShowSnapPanel")
'--------------------------------------------------
' Parameter 1 : (String) "ShowSnapPanel"
' Returned value : (Variant) (Unsigned Long) 1
'--------------------------------------------------

Dim bSTR20
bSTR20 = ""
Dim bSTR21
bSTR21 = ""
Dim boolean10
settingRepository1.GetAttrInfo "ShowSnapPanel", bSTR20, bSTR21, boolean10
'--------------------------------------------------
' Parameter 1 : (String) "ShowSnapPanel"
' Parameter 2 : (String) "Default value"
' Parameter 3 : (String) "Unlocked"
' Parameter 4 : (Boolean) False
'--------------------------------------------------

End Sub
