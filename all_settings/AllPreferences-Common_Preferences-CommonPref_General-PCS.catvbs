Language="VBSCRIPT"

Sub CATMain()

Set settingControllers1 = CATIA.SettingControllers

Set settingRepository1 = settingControllers1.Item("GeneralPCS")

uLong1 = settingRepository1.GetAttr("UndoMax")
'--------------------------------------------------
' Parameter 1 : (String) "UndoMax"
' Returned value : (Variant) (Unsigned Long) 10
'--------------------------------------------------

Dim bSTR1
bSTR1 = ""
Dim bSTR2
bSTR2 = ""
Dim boolean1
settingRepository1.GetAttrInfo "UndoMax", bSTR1, bSTR2, boolean1
'--------------------------------------------------
' Parameter 1 : (String) "UndoMax"
' Parameter 2 : (String) "Default value"
' Parameter 3 : (String) "Unlocked"
' Parameter 4 : (Boolean) False
'--------------------------------------------------

short1 = settingRepository1.GetAttr("UndoMacro")
'--------------------------------------------------
' Parameter 1 : (String) "UndoMacro"
' Returned value : (Variant) (Short) 0
'--------------------------------------------------

Dim bSTR3
bSTR3 = ""
Dim bSTR4
bSTR4 = ""
Dim boolean2
settingRepository1.GetAttrInfo "UndoMacro", bSTR3, bSTR4, boolean2
'--------------------------------------------------
' Parameter 1 : (String) "UndoMacro"
' Parameter 2 : (String) "Default value"
' Parameter 3 : (String) "Unlocked"
' Parameter 4 : (Boolean) False
'--------------------------------------------------

uLong2 = settingRepository1.GetAttr("ExpandMax")
'--------------------------------------------------
' Parameter 1 : (String) "ExpandMax"
' Returned value : (Variant) (Unsigned Long) 3
'--------------------------------------------------

Dim bSTR5
bSTR5 = ""
Dim bSTR6
bSTR6 = ""
Dim boolean3
settingRepository1.GetAttrInfo "ExpandMax", bSTR5, bSTR6, boolean3
'--------------------------------------------------
' Parameter 1 : (String) "ExpandMax"
' Parameter 2 : (String) "Default value"
' Parameter 3 : (String) "Unlocked"
' Parameter 4 : (Boolean) False
'--------------------------------------------------

uLong3 = settingRepository1.GetAttr("StackFullWarning")
'--------------------------------------------------
' Parameter 1 : (String) "StackFullWarning"
' Returned value : (Variant) (Unsigned Long) 0
'--------------------------------------------------

Dim bSTR7
bSTR7 = ""
Dim bSTR8
bSTR8 = ""
Dim boolean4
settingRepository1.GetAttrInfo "StackFullWarning", bSTR7, bSTR8, boolean4
'--------------------------------------------------
' Parameter 1 : (String) "StackFullWarning"
' Parameter 2 : (String) "Default value"
' Parameter 3 : (String) "Unlocked"
' Parameter 4 : (Boolean) False
'--------------------------------------------------

End Sub
