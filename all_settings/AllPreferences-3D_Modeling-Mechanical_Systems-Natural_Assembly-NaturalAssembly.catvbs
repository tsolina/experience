Language="VBSCRIPT"

Sub CATMain()

Set settingControllers1 = CATIA.SettingControllers

Set settingRepository1 = settingControllers1.Item("CATLiveShapeSettings")

boolean1 = settingRepository1.GetAttr("Referent")
'--------------------------------------------------
' Parameter 1 : (String) "Referent"
' Returned value : (Variant) (Boolean) False
'--------------------------------------------------

Dim bSTR1
bSTR1 = ""
Dim bSTR2
bSTR2 = ""
Dim boolean2
settingRepository1.GetAttrInfo "Referent", bSTR1, bSTR2, boolean2
'--------------------------------------------------
' Parameter 1 : (String) "Referent"
' Parameter 2 : (String) "Default value"
' Parameter 3 : (String) "Unlocked"
' Parameter 4 : (Boolean) False
'--------------------------------------------------

boolean3 = settingRepository1.GetAttr("SpecTree")
'--------------------------------------------------
' Parameter 1 : (String) "SpecTree"
' Returned value : (Variant) (Boolean) False
'--------------------------------------------------

Dim bSTR3
bSTR3 = ""
Dim bSTR4
bSTR4 = ""
Dim boolean4
settingRepository1.GetAttrInfo "SpecTree", bSTR3, bSTR4, boolean4
'--------------------------------------------------
' Parameter 1 : (String) "SpecTree"
' Parameter 2 : (String) "Default value"
' Parameter 3 : (String) "Unlocked"
' Parameter 4 : (Boolean) False
'--------------------------------------------------

boolean5 = settingRepository1.GetAttr("ReframeOnInsert")
'--------------------------------------------------
' Parameter 1 : (String) "ReframeOnInsert"
' Returned value : (Variant) (Boolean) True
'--------------------------------------------------

Dim bSTR5
bSTR5 = ""
Dim bSTR6
bSTR6 = ""
Dim boolean6
settingRepository1.GetAttrInfo "ReframeOnInsert", bSTR5, bSTR6, boolean6
'--------------------------------------------------
' Parameter 1 : (String) "ReframeOnInsert"
' Parameter 2 : (String) "Default value"
' Parameter 3 : (String) "Unlocked"
' Parameter 4 : (Boolean) False
'--------------------------------------------------

boolean7 = settingRepository1.GetAttr("GhostOutOfContext")
'--------------------------------------------------
' Parameter 1 : (String) "GhostOutOfContext"
' Returned value : (Variant) (Boolean) True
'--------------------------------------------------

Dim bSTR7
bSTR7 = ""
Dim bSTR8
bSTR8 = ""
Dim boolean8
settingRepository1.GetAttrInfo "GhostOutOfContext", bSTR7, bSTR8, boolean8
'--------------------------------------------------
' Parameter 1 : (String) "GhostOutOfContext"
' Parameter 2 : (String) "Default value"
' Parameter 3 : (String) "Unlocked"
' Parameter 4 : (Boolean) False
'--------------------------------------------------

boolean9 = settingRepository1.GetAttr("OrientOnTables")
'--------------------------------------------------
' Parameter 1 : (String) "OrientOnTables"
' Returned value : (Variant) (Boolean) True
'--------------------------------------------------

Dim bSTR9
bSTR9 = ""
Dim bSTR10
bSTR10 = ""
Dim boolean10
settingRepository1.GetAttrInfo "OrientOnTables", bSTR9, bSTR10, boolean10
'--------------------------------------------------
' Parameter 1 : (String) "OrientOnTables"
' Parameter 2 : (String) "Default value"
' Parameter 3 : (String) "Unlocked"
' Parameter 4 : (Boolean) False
'--------------------------------------------------

float1 = settingRepository1.GetAttr("LinearizationFactor")
'--------------------------------------------------
' Parameter 1 : (String) "LinearizationFactor"
' Returned value : (Variant) (Float) 0.000000
'--------------------------------------------------

Dim bSTR11
bSTR11 = ""
Dim bSTR12
bSTR12 = ""
Dim boolean11
settingRepository1.GetAttrInfo "LinearizationFactor", bSTR11, bSTR12, boolean11
'--------------------------------------------------
' Parameter 1 : (String) "LinearizationFactor"
' Parameter 2 : (String) "Default value"
' Parameter 3 : (String) "Unlocked"
' Parameter 4 : (Boolean) False
'--------------------------------------------------

Set settingRepository2 = settingControllers1.Item("EngineeringConnection")

long1 = settingRepository2.GetAttr("EnggConnectionVisualizationStatus")
'--------------------------------------------------
' Parameter 1 : (String) "EnggConnectionVisualizationStatus"
' Returned value : (Variant) (Long) 0
'--------------------------------------------------

Dim bSTR13
bSTR13 = ""
Dim bSTR14
bSTR14 = ""
Dim boolean12
settingRepository2.GetAttrInfo "EnggConnectionVisualizationStatus", bSTR13, bSTR14, boolean12
'--------------------------------------------------
' Parameter 1 : (String) "EnggConnectionVisualizationStatus"
' Parameter 2 : (String) "Default value"
' Parameter 3 : (String) "Unlocked"
' Parameter 4 : (Boolean) False
'--------------------------------------------------

End Sub
