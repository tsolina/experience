Language="VBSCRIPT"

Sub CATMain()

Set settingControllers1 = CATIA.SettingControllers

Set settingRepository1 = settingControllers1.Item("SIMAnimationSettings")

uLong1 = settingRepository1.GetAttr("PositionInitState")
'--------------------------------------------------
' Parameter 1 : (String) "PositionInitState"
' Returned value : (Variant) (Unsigned Long) 0
'--------------------------------------------------

Dim bSTR1
bSTR1 = ""
Dim bSTR2
bSTR2 = ""
Dim boolean1
settingRepository1.GetAttrInfo "PositionInitState", bSTR1, bSTR2, boolean1
'--------------------------------------------------
' Parameter 1 : (String) "PositionInitState"
' Parameter 2 : (String) "Default value"
' Parameter 3 : (String) "Unlocked"
' Parameter 4 : (Boolean) False
'--------------------------------------------------

uLong2 = settingRepository1.GetAttr("ColorInitState")
'--------------------------------------------------
' Parameter 1 : (String) "ColorInitState"
' Returned value : (Variant) (Unsigned Long) 0
'--------------------------------------------------

Dim bSTR3
bSTR3 = ""
Dim bSTR4
bSTR4 = ""
Dim boolean2
settingRepository1.GetAttrInfo "ColorInitState", bSTR3, bSTR4, boolean2
'--------------------------------------------------
' Parameter 1 : (String) "ColorInitState"
' Parameter 2 : (String) "Default value"
' Parameter 3 : (String) "Unlocked"
' Parameter 4 : (Boolean) False
'--------------------------------------------------

uLong3 = settingRepository1.GetAttr("VisInitState")
'--------------------------------------------------
' Parameter 1 : (String) "VisInitState"
' Returned value : (Variant) (Unsigned Long) 0
'--------------------------------------------------

Dim bSTR5
bSTR5 = ""
Dim bSTR6
bSTR6 = ""
Dim boolean3
settingRepository1.GetAttrInfo "VisInitState", bSTR5, bSTR6, boolean3
'--------------------------------------------------
' Parameter 1 : (String) "VisInitState"
' Parameter 2 : (String) "Default value"
' Parameter 3 : (String) "Unlocked"
' Parameter 4 : (Boolean) False
'--------------------------------------------------

uLong4 = settingRepository1.GetAttr("ProductHighlight")
'--------------------------------------------------
' Parameter 1 : (String) "ProductHighlight"
' Returned value : (Variant) (Unsigned Long) 1
'--------------------------------------------------

Dim bSTR7
bSTR7 = ""
Dim bSTR8
bSTR8 = ""
Dim boolean4
settingRepository1.GetAttrInfo "ProductHighlight", bSTR7, bSTR8, boolean4
'--------------------------------------------------
' Parameter 1 : (String) "ProductHighlight"
' Parameter 2 : (String) "Default value"
' Parameter 3 : (String) "Unlocked"
' Parameter 4 : (Boolean) False
'--------------------------------------------------

End Sub
