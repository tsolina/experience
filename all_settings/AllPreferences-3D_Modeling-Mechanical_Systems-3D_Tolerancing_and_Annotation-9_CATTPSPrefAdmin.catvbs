Language="VBSCRIPT"

Sub CATMain()

Set settingControllers1 = CATIA.SettingControllers

Set settingRepository1 = settingControllers1.Item("CATTPSEditor")

boolean1 = settingRepository1.GetAttr("DrwStyleCreation")
'--------------------------------------------------
' Parameter 1 : (String) "DrwStyleCreation"
' Returned value : (Variant) (Boolean) False
'--------------------------------------------------

Dim bSTR1
bSTR1 = ""
Dim bSTR2
bSTR2 = ""
Dim boolean2
settingRepository1.GetAttrInfo "DrwStyleCreation", bSTR1, bSTR2, boolean2
'--------------------------------------------------
' Parameter 1 : (String) "DrwStyleCreation"
' Parameter 2 : (String) "Default value"
' Parameter 3 : (String) "Unlocked"
' Parameter 4 : (Boolean) False
'--------------------------------------------------

boolean3 = settingRepository1.GetAttr("DrwButtonReset")
'--------------------------------------------------
' Parameter 1 : (String) "DrwButtonReset"
' Returned value : (Variant) (Boolean) True
'--------------------------------------------------

Dim bSTR3
bSTR3 = ""
Dim bSTR4
bSTR4 = ""
Dim boolean4
settingRepository1.GetAttrInfo "DrwButtonReset", bSTR3, bSTR4, boolean4
'--------------------------------------------------
' Parameter 1 : (String) "DrwButtonReset"
' Parameter 2 : (String) "Default value"
' Parameter 3 : (String) "Unlocked"
' Parameter 4 : (Boolean) False
'--------------------------------------------------

boolean5 = settingRepository1.GetAttr("DisableAnnotLockEditionPropAccess")
'--------------------------------------------------
' Parameter 1 : (String) "DisableAnnotLockEditionPropAccess"
' Returned value : (Variant) (Boolean) False
'--------------------------------------------------

Dim bSTR5
bSTR5 = ""
Dim bSTR6
bSTR6 = ""
Dim boolean6
settingRepository1.GetAttrInfo "DisableAnnotLockEditionPropAccess", bSTR5, bSTR6, boolean6
'--------------------------------------------------
' Parameter 1 : (String) "DisableAnnotLockEditionPropAccess"
' Parameter 2 : (String) "Default value"
' Parameter 3 : (String) "Unlocked"
' Parameter 4 : (Boolean) False
'--------------------------------------------------

boolean7 = settingRepository1.GetAttr("ViewNameUnicitySetting")
'--------------------------------------------------
' Parameter 1 : (String) "ViewNameUnicitySetting"
' Returned value : (Variant) (Boolean) False
'--------------------------------------------------

Dim bSTR7
bSTR7 = ""
Dim bSTR8
bSTR8 = ""
Dim boolean8
settingRepository1.GetAttrInfo "ViewNameUnicitySetting", bSTR7, bSTR8, boolean8
'--------------------------------------------------
' Parameter 1 : (String) "ViewNameUnicitySetting"
' Parameter 2 : (String) "Default value"
' Parameter 3 : (String) "Unlocked"
' Parameter 4 : (Boolean) False
'--------------------------------------------------

boolean9 = settingRepository1.GetAttr("CaptureNameUnicitySetting")
'--------------------------------------------------
' Parameter 1 : (String) "CaptureNameUnicitySetting"
' Returned value : (Variant) (Boolean) False
'--------------------------------------------------

Dim bSTR9
bSTR9 = ""
Dim bSTR10
bSTR10 = ""
Dim boolean10
settingRepository1.GetAttrInfo "CaptureNameUnicitySetting", bSTR9, bSTR10, boolean10
'--------------------------------------------------
' Parameter 1 : (String) "CaptureNameUnicitySetting"
' Parameter 2 : (String) "Default value"
' Parameter 3 : (String) "Unlocked"
' Parameter 4 : (Boolean) False
'--------------------------------------------------

long1 = settingRepository1.GetAttr("EngineeringConnectionLocation")
'--------------------------------------------------
' Parameter 1 : (String) "EngineeringConnectionLocation"
' Returned value : (Variant) (Long) 0
'--------------------------------------------------

Dim bSTR11
bSTR11 = ""
Dim bSTR12
bSTR12 = ""
Dim boolean11
settingRepository1.GetAttrInfo "EngineeringConnectionLocation", bSTR11, bSTR12, boolean11
'--------------------------------------------------
' Parameter 1 : (String) "EngineeringConnectionLocation"
' Parameter 2 : (String) "Default value"
' Parameter 3 : (String) "Unlocked"
' Parameter 4 : (Boolean) False
'--------------------------------------------------

boolean12 = settingRepository1.GetAttr("PUBLISHED_GEOMETRY")
'--------------------------------------------------
' Parameter 1 : (String) "PUBLISHED_GEOMETRY"
' Returned value : (Variant) (Boolean) False
'--------------------------------------------------

Dim bSTR13
bSTR13 = ""
Dim bSTR14
bSTR14 = ""
Dim boolean13
settingRepository1.GetAttrInfo "PUBLISHED_GEOMETRY", bSTR13, bSTR14, boolean13
'--------------------------------------------------
' Parameter 1 : (String) "PUBLISHED_GEOMETRY"
' Parameter 2 : (String) "Default value"
' Parameter 3 : (String) "Unlocked"
' Parameter 4 : (Boolean) False
'--------------------------------------------------

boolean14 = settingRepository1.GetAttr("CATDWC_FTA_ARM_OPTION")
'--------------------------------------------------
' Parameter 1 : (String) "CATDWC_FTA_ARM_OPTION"
' Returned value : (Variant) (Boolean) False
'--------------------------------------------------

Dim bSTR15
bSTR15 = ""
Dim bSTR16
bSTR16 = ""
Dim boolean15
settingRepository1.GetAttrInfo "CATDWC_FTA_ARM_OPTION", bSTR15, bSTR16, boolean15
'--------------------------------------------------
' Parameter 1 : (String) "CATDWC_FTA_ARM_OPTION"
' Parameter 2 : (String) "Default value"
' Parameter 3 : (String) "Unlocked"
' Parameter 4 : (Boolean) False
'--------------------------------------------------

boolean16 = settingRepository1.GetAttr("AttrBrwsrAllowAutoRefresh")
'--------------------------------------------------
' Parameter 1 : (String) "AttrBrwsrAllowAutoRefresh"
' Returned value : (Variant) (Boolean) True
'--------------------------------------------------

Dim bSTR17
bSTR17 = ""
Dim bSTR18
bSTR18 = ""
Dim boolean17
settingRepository1.GetAttrInfo "AttrBrwsrAllowAutoRefresh", bSTR17, bSTR18, boolean17
'--------------------------------------------------
' Parameter 1 : (String) "AttrBrwsrAllowAutoRefresh"
' Parameter 2 : (String) "Default value"
' Parameter 3 : (String) "Unlocked"
' Parameter 4 : (Boolean) False
'--------------------------------------------------

boolean18 = settingRepository1.GetAttr("AttrBrwsrDispKnowledge")
'--------------------------------------------------
' Parameter 1 : (String) "AttrBrwsrDispKnowledge"
' Returned value : (Variant) (Boolean) True
'--------------------------------------------------

Dim bSTR19
bSTR19 = ""
Dim bSTR20
bSTR20 = ""
Dim boolean19
settingRepository1.GetAttrInfo "AttrBrwsrDispKnowledge", bSTR19, bSTR20, boolean19
'--------------------------------------------------
' Parameter 1 : (String) "AttrBrwsrDispKnowledge"
' Parameter 2 : (String) "Default value"
' Parameter 3 : (String) "Unlocked"
' Parameter 4 : (Boolean) False
'--------------------------------------------------

boolean20 = settingRepository1.GetAttr("AttrBrwsrDisp3DAnnotations")
'--------------------------------------------------
' Parameter 1 : (String) "AttrBrwsrDisp3DAnnotations"
' Returned value : (Variant) (Boolean) True
'--------------------------------------------------

Dim bSTR21
bSTR21 = ""
Dim bSTR22
bSTR22 = ""
Dim boolean21
settingRepository1.GetAttrInfo "AttrBrwsrDisp3DAnnotations", bSTR21, bSTR22, boolean21
'--------------------------------------------------
' Parameter 1 : (String) "AttrBrwsrDisp3DAnnotations"
' Parameter 2 : (String) "Default value"
' Parameter 3 : (String) "Unlocked"
' Parameter 4 : (Boolean) False
'--------------------------------------------------

boolean22 = settingRepository1.GetAttr("AttrBrwsrDispMechanical")
'--------------------------------------------------
' Parameter 1 : (String) "AttrBrwsrDispMechanical"
' Returned value : (Variant) (Boolean) True
'--------------------------------------------------

Dim bSTR23
bSTR23 = ""
Dim bSTR24
bSTR24 = ""
Dim boolean23
settingRepository1.GetAttrInfo "AttrBrwsrDispMechanical", bSTR23, bSTR24, boolean23
'--------------------------------------------------
' Parameter 1 : (String) "AttrBrwsrDispMechanical"
' Parameter 2 : (String) "Default value"
' Parameter 3 : (String) "Unlocked"
' Parameter 4 : (Boolean) False
'--------------------------------------------------

boolean24 = settingRepository1.GetAttr("AttrBrwsrDispElectrical")
'--------------------------------------------------
' Parameter 1 : (String) "AttrBrwsrDispElectrical"
' Returned value : (Variant) (Boolean) True
'--------------------------------------------------

Dim bSTR25
bSTR25 = ""
Dim bSTR26
bSTR26 = ""
Dim boolean25
settingRepository1.GetAttrInfo "AttrBrwsrDispElectrical", bSTR25, bSTR26, boolean25
'--------------------------------------------------
' Parameter 1 : (String) "AttrBrwsrDispElectrical"
' Parameter 2 : (String) "Default value"
' Parameter 3 : (String) "Unlocked"
' Parameter 4 : (Boolean) False
'--------------------------------------------------

boolean26 = settingRepository1.GetAttr("AttrBrwsrDispPathway")
'--------------------------------------------------
' Parameter 1 : (String) "AttrBrwsrDispPathway"
' Returned value : (Variant) (Boolean) True
'--------------------------------------------------

Dim bSTR27
bSTR27 = ""
Dim bSTR28
bSTR28 = ""
Dim boolean27
settingRepository1.GetAttrInfo "AttrBrwsrDispPathway", bSTR27, bSTR28, boolean27
'--------------------------------------------------
' Parameter 1 : (String) "AttrBrwsrDispPathway"
' Parameter 2 : (String) "Default value"
' Parameter 3 : (String) "Unlocked"
' Parameter 4 : (Boolean) False
'--------------------------------------------------

boolean28 = settingRepository1.GetAttr("AttrBrwsrDispComposite")
'--------------------------------------------------
' Parameter 1 : (String) "AttrBrwsrDispComposite"
' Returned value : (Variant) (Boolean) True
'--------------------------------------------------

Dim bSTR29
bSTR29 = ""
Dim bSTR30
bSTR30 = ""
Dim boolean29
settingRepository1.GetAttrInfo "AttrBrwsrDispComposite", bSTR29, bSTR30, boolean29
'--------------------------------------------------
' Parameter 1 : (String) "AttrBrwsrDispComposite"
' Parameter 2 : (String) "Default value"
' Parameter 3 : (String) "Unlocked"
' Parameter 4 : (Boolean) False
'--------------------------------------------------

boolean30 = settingRepository1.GetAttr("AttrBrwsrDispLayeredPrd")
'--------------------------------------------------
' Parameter 1 : (String) "AttrBrwsrDispLayeredPrd"
' Returned value : (Variant) (Boolean) True
'--------------------------------------------------

Dim bSTR31
bSTR31 = ""
Dim bSTR32
bSTR32 = ""
Dim boolean31
settingRepository1.GetAttrInfo "AttrBrwsrDispLayeredPrd", bSTR31, bSTR32, boolean31
'--------------------------------------------------
' Parameter 1 : (String) "AttrBrwsrDispLayeredPrd"
' Parameter 2 : (String) "Default value"
' Parameter 3 : (String) "Unlocked"
' Parameter 4 : (Boolean) False
'--------------------------------------------------

boolean32 = settingRepository1.GetAttr("AttrBrwsrDispGeometrical")
'--------------------------------------------------
' Parameter 1 : (String) "AttrBrwsrDispGeometrical"
' Returned value : (Variant) (Boolean) True
'--------------------------------------------------

Dim bSTR33
bSTR33 = ""
Dim bSTR34
bSTR34 = ""
Dim boolean33
settingRepository1.GetAttrInfo "AttrBrwsrDispGeometrical", bSTR33, bSTR34, boolean33
'--------------------------------------------------
' Parameter 1 : (String) "AttrBrwsrDispGeometrical"
' Parameter 2 : (String) "Default value"
' Parameter 3 : (String) "Unlocked"
' Parameter 4 : (Boolean) False
'--------------------------------------------------

boolean34 = settingRepository1.GetAttr("PreventRootUpgrade")
'--------------------------------------------------
' Parameter 1 : (String) "PreventRootUpgrade"
' Returned value : (Variant) (Boolean) False
'--------------------------------------------------

Dim bSTR35
bSTR35 = ""
Dim bSTR36
bSTR36 = ""
Dim boolean35
settingRepository1.GetAttrInfo "PreventRootUpgrade", bSTR35, bSTR36, boolean35
'--------------------------------------------------
' Parameter 1 : (String) "PreventRootUpgrade"
' Parameter 2 : (String) "Default value"
' Parameter 3 : (String) "Unlocked"
' Parameter 4 : (Boolean) False
'--------------------------------------------------

boolean36 = settingRepository1.GetAttr("PreventContentUpgrade")
'--------------------------------------------------
' Parameter 1 : (String) "PreventContentUpgrade"
' Returned value : (Variant) (Boolean) False
'--------------------------------------------------

Dim bSTR37
bSTR37 = ""
Dim bSTR38
bSTR38 = ""
Dim boolean37
settingRepository1.GetAttrInfo "PreventContentUpgrade", bSTR37, bSTR38, boolean37
'--------------------------------------------------
' Parameter 1 : (String) "PreventContentUpgrade"
' Parameter 2 : (String) "Default value"
' Parameter 3 : (String) "Unlocked"
' Parameter 4 : (Boolean) False
'--------------------------------------------------

boolean38 = settingRepository1.GetAttr("DisableTemplateCreation")
'--------------------------------------------------
' Parameter 1 : (String) "DisableTemplateCreation"
' Returned value : (Variant) (Boolean) True
'--------------------------------------------------

Dim bSTR39
bSTR39 = ""
Dim bSTR40
bSTR40 = ""
Dim boolean39
settingRepository1.GetAttrInfo "DisableTemplateCreation", bSTR39, bSTR40, boolean39
'--------------------------------------------------
' Parameter 1 : (String) "DisableTemplateCreation"
' Parameter 2 : (String) "Default value"
' Parameter 3 : (String) "Unlocked"
' Parameter 4 : (Boolean) False
'--------------------------------------------------

boolean40 = settingRepository1.GetAttr("NoaWithoutLinkToReference")
'--------------------------------------------------
' Parameter 1 : (String) "NoaWithoutLinkToReference"
' Returned value : (Variant) (Boolean) False
'--------------------------------------------------

Dim bSTR41
bSTR41 = ""
Dim bSTR42
bSTR42 = ""
Dim boolean41
settingRepository1.GetAttrInfo "NoaWithoutLinkToReference", bSTR41, bSTR42, boolean41
'--------------------------------------------------
' Parameter 1 : (String) "NoaWithoutLinkToReference"
' Parameter 2 : (String) "Default value"
' Parameter 3 : (String) "Unlocked"
' Parameter 4 : (Boolean) False
'--------------------------------------------------

boolean42 = settingRepository1.GetAttr("DisableGenMfgRequirements")
'--------------------------------------------------
' Parameter 1 : (String) "DisableGenMfgRequirements"
' Returned value : (Variant) (Boolean) True
'--------------------------------------------------

Dim bSTR43
bSTR43 = ""
Dim bSTR44
bSTR44 = ""
Dim boolean43
settingRepository1.GetAttrInfo "DisableGenMfgRequirements", bSTR43, bSTR44, boolean43
'--------------------------------------------------
' Parameter 1 : (String) "DisableGenMfgRequirements"
' Parameter 2 : (String) "Default value"
' Parameter 3 : (String) "Unlocked"
' Parameter 4 : (Boolean) False
'--------------------------------------------------

long2 = settingRepository1.GetAttr("ControlGenReqStatusAtSave")
'--------------------------------------------------
' Parameter 1 : (String) "ControlGenReqStatusAtSave"
' Returned value : (Variant) (Long) 0
'--------------------------------------------------

Dim bSTR45
bSTR45 = ""
Dim bSTR46
bSTR46 = ""
Dim boolean44
settingRepository1.GetAttrInfo "ControlGenReqStatusAtSave", bSTR45, bSTR46, boolean44
'--------------------------------------------------
' Parameter 1 : (String) "ControlGenReqStatusAtSave"
' Parameter 2 : (String) "Default value"
' Parameter 3 : (String) "Unlocked"
' Parameter 4 : (Boolean) False
'--------------------------------------------------

boolean45 = settingRepository1.GetAttr("DisableHideInvalidUnrepairableAnnotations")
'--------------------------------------------------
' Parameter 1 : (String) "DisableHideInvalidUnrepairableAnnotations"
' Returned value : (Variant) (Boolean) True
'--------------------------------------------------

Dim bSTR47
bSTR47 = ""
Dim bSTR48
bSTR48 = ""
Dim boolean46
settingRepository1.GetAttrInfo "DisableHideInvalidUnrepairableAnnotations", bSTR47, bSTR48, boolean46
'--------------------------------------------------
' Parameter 1 : (String) "DisableHideInvalidUnrepairableAnnotations"
' Parameter 2 : (String) "Default value"
' Parameter 3 : (String) "Unlocked"
' Parameter 4 : (Boolean) False
'--------------------------------------------------

long3 = settingRepository1.GetAttr("SelectionOnCurrentAssembly")
'--------------------------------------------------
' Parameter 1 : (String) "SelectionOnCurrentAssembly"
' Returned value : (Variant) (Long) 2
'--------------------------------------------------

Dim bSTR49
bSTR49 = ""
Dim bSTR50
bSTR50 = ""
Dim boolean47
settingRepository1.GetAttrInfo "SelectionOnCurrentAssembly", bSTR49, bSTR50, boolean47
'--------------------------------------------------
' Parameter 1 : (String) "SelectionOnCurrentAssembly"
' Parameter 2 : (String) "Default value"
' Parameter 3 : (String) "Unlocked"
' Parameter 4 : (Boolean) False
'--------------------------------------------------

boolean48 = settingRepository1.GetAttr("ShowWarningSelectionOutAssembly")
'--------------------------------------------------
' Parameter 1 : (String) "ShowWarningSelectionOutAssembly"
' Returned value : (Variant) (Boolean) False
'--------------------------------------------------

Dim bSTR51
bSTR51 = ""
Dim bSTR52
bSTR52 = ""
Dim boolean49
settingRepository1.GetAttrInfo "ShowWarningSelectionOutAssembly", bSTR51, bSTR52, boolean49
'--------------------------------------------------
' Parameter 1 : (String) "ShowWarningSelectionOutAssembly"
' Parameter 2 : (String) "Default value"
' Parameter 3 : (String) "Unlocked"
' Parameter 4 : (Boolean) False
'--------------------------------------------------

long4 = settingRepository1.GetAttr("CATDrwTbFontNameSetting")
'--------------------------------------------------
' Parameter 1 : (String) "CATDrwTbFontNameSetting"
' Returned value : (Variant) (Long) 2
'--------------------------------------------------

Dim bSTR53
bSTR53 = ""
Dim bSTR54
bSTR54 = ""
Dim boolean50
settingRepository1.GetAttrInfo "CATDrwTbFontNameSetting", bSTR53, bSTR54, boolean50
'--------------------------------------------------
' Parameter 1 : (String) "CATDrwTbFontNameSetting"
' Parameter 2 : (String) "Default value"
' Parameter 3 : (String) "Unlocked"
' Parameter 4 : (Boolean) False
'--------------------------------------------------

long5 = settingRepository1.GetAttr("CATDrwTbFontSizeSetting")
'--------------------------------------------------
' Parameter 1 : (String) "CATDrwTbFontSizeSetting"
' Returned value : (Variant) (Long) 2
'--------------------------------------------------

Dim bSTR55
bSTR55 = ""
Dim bSTR56
bSTR56 = ""
Dim boolean51
settingRepository1.GetAttrInfo "CATDrwTbFontSizeSetting", bSTR55, bSTR56, boolean51
'--------------------------------------------------
' Parameter 1 : (String) "CATDrwTbFontSizeSetting"
' Parameter 2 : (String) "Default value"
' Parameter 3 : (String) "Unlocked"
' Parameter 4 : (Boolean) False
'--------------------------------------------------

long6 = settingRepository1.GetAttr("CATDrwTbBoldSetting")
'--------------------------------------------------
' Parameter 1 : (String) "CATDrwTbBoldSetting"
' Returned value : (Variant) (Long) 2
'--------------------------------------------------

Dim bSTR57
bSTR57 = ""
Dim bSTR58
bSTR58 = ""
Dim boolean52
settingRepository1.GetAttrInfo "CATDrwTbBoldSetting", bSTR57, bSTR58, boolean52
'--------------------------------------------------
' Parameter 1 : (String) "CATDrwTbBoldSetting"
' Parameter 2 : (String) "Default value"
' Parameter 3 : (String) "Unlocked"
' Parameter 4 : (Boolean) False
'--------------------------------------------------

long7 = settingRepository1.GetAttr("CATDrwTbItalicSetting")
'--------------------------------------------------
' Parameter 1 : (String) "CATDrwTbItalicSetting"
' Returned value : (Variant) (Long) 2
'--------------------------------------------------

Dim bSTR59
bSTR59 = ""
Dim bSTR60
bSTR60 = ""
Dim boolean53
settingRepository1.GetAttrInfo "CATDrwTbItalicSetting", bSTR59, bSTR60, boolean53
'--------------------------------------------------
' Parameter 1 : (String) "CATDrwTbItalicSetting"
' Parameter 2 : (String) "Default value"
' Parameter 3 : (String) "Unlocked"
' Parameter 4 : (Boolean) False
'--------------------------------------------------

long8 = settingRepository1.GetAttr("CATDrwTbUnderOverLineSetting")
'--------------------------------------------------
' Parameter 1 : (String) "CATDrwTbUnderOverLineSetting"
' Returned value : (Variant) (Long) 2
'--------------------------------------------------

Dim bSTR61
bSTR61 = ""
Dim bSTR62
bSTR62 = ""
Dim boolean54
settingRepository1.GetAttrInfo "CATDrwTbUnderOverLineSetting", bSTR61, bSTR62, boolean54
'--------------------------------------------------
' Parameter 1 : (String) "CATDrwTbUnderOverLineSetting"
' Parameter 2 : (String) "Default value"
' Parameter 3 : (String) "Unlocked"
' Parameter 4 : (Boolean) False
'--------------------------------------------------

long9 = settingRepository1.GetAttr("CATDrwTbStrikeThroughSetting")
'--------------------------------------------------
' Parameter 1 : (String) "CATDrwTbStrikeThroughSetting"
' Returned value : (Variant) (Long) 2
'--------------------------------------------------

Dim bSTR63
bSTR63 = ""
Dim bSTR64
bSTR64 = ""
Dim boolean55
settingRepository1.GetAttrInfo "CATDrwTbStrikeThroughSetting", bSTR63, bSTR64, boolean55
'--------------------------------------------------
' Parameter 1 : (String) "CATDrwTbStrikeThroughSetting"
' Parameter 2 : (String) "Default value"
' Parameter 3 : (String) "Unlocked"
' Parameter 4 : (Boolean) False
'--------------------------------------------------

long10 = settingRepository1.GetAttr("CATDrwTbJustificationSetting")
'--------------------------------------------------
' Parameter 1 : (String) "CATDrwTbJustificationSetting"
' Returned value : (Variant) (Long) 2
'--------------------------------------------------

Dim bSTR65
bSTR65 = ""
Dim bSTR66
bSTR66 = ""
Dim boolean56
settingRepository1.GetAttrInfo "CATDrwTbJustificationSetting", bSTR65, bSTR66, boolean56
'--------------------------------------------------
' Parameter 1 : (String) "CATDrwTbJustificationSetting"
' Parameter 2 : (String) "Default value"
' Parameter 3 : (String) "Unlocked"
' Parameter 4 : (Boolean) False
'--------------------------------------------------

long11 = settingRepository1.GetAttr("CATDrwTbAnchorPointSetting")
'--------------------------------------------------
' Parameter 1 : (String) "CATDrwTbAnchorPointSetting"
' Returned value : (Variant) (Long) 2
'--------------------------------------------------

Dim bSTR67
bSTR67 = ""
Dim bSTR68
bSTR68 = ""
Dim boolean57
settingRepository1.GetAttrInfo "CATDrwTbAnchorPointSetting", bSTR67, bSTR68, boolean57
'--------------------------------------------------
' Parameter 1 : (String) "CATDrwTbAnchorPointSetting"
' Parameter 2 : (String) "Default value"
' Parameter 3 : (String) "Unlocked"
' Parameter 4 : (Boolean) False
'--------------------------------------------------

long12 = settingRepository1.GetAttr("CATDrwTbFrameSetting")
'--------------------------------------------------
' Parameter 1 : (String) "CATDrwTbFrameSetting"
' Returned value : (Variant) (Long) 2
'--------------------------------------------------

Dim bSTR69
bSTR69 = ""
Dim bSTR70
bSTR70 = ""
Dim boolean58
settingRepository1.GetAttrInfo "CATDrwTbFrameSetting", bSTR69, bSTR70, boolean58
'--------------------------------------------------
' Parameter 1 : (String) "CATDrwTbFrameSetting"
' Parameter 2 : (String) "Default value"
' Parameter 3 : (String) "Unlocked"
' Parameter 4 : (Boolean) False
'--------------------------------------------------

long13 = settingRepository1.GetAttr("CATDrwTbSymbolSetting")
'--------------------------------------------------
' Parameter 1 : (String) "CATDrwTbSymbolSetting"
' Returned value : (Variant) (Long) 2
'--------------------------------------------------

Dim bSTR71
bSTR71 = ""
Dim bSTR72
bSTR72 = ""
Dim boolean59
settingRepository1.GetAttrInfo "CATDrwTbSymbolSetting", bSTR71, bSTR72, boolean59
'--------------------------------------------------
' Parameter 1 : (String) "CATDrwTbSymbolSetting"
' Parameter 2 : (String) "Default value"
' Parameter 3 : (String) "Unlocked"
' Parameter 4 : (Boolean) False
'--------------------------------------------------

long14 = settingRepository1.GetAttr("CATDrwTbDimensionLineSetting")
'--------------------------------------------------
' Parameter 1 : (String) "CATDrwTbDimensionLineSetting"
' Returned value : (Variant) (Long) 2
'--------------------------------------------------

Dim bSTR73
bSTR73 = ""
Dim bSTR74
bSTR74 = ""
Dim boolean60
settingRepository1.GetAttrInfo "CATDrwTbDimensionLineSetting", bSTR73, bSTR74, boolean60
'--------------------------------------------------
' Parameter 1 : (String) "CATDrwTbDimensionLineSetting"
' Parameter 2 : (String) "Default value"
' Parameter 3 : (String) "Unlocked"
' Parameter 4 : (Boolean) False
'--------------------------------------------------

long15 = settingRepository1.GetAttr("CATDrwTbTolerancesSetting")
'--------------------------------------------------
' Parameter 1 : (String) "CATDrwTbTolerancesSetting"
' Returned value : (Variant) (Long) 2
'--------------------------------------------------

Dim bSTR75
bSTR75 = ""
Dim bSTR76
bSTR76 = ""
Dim boolean61
settingRepository1.GetAttrInfo "CATDrwTbTolerancesSetting", bSTR75, bSTR76, boolean61
'--------------------------------------------------
' Parameter 1 : (String) "CATDrwTbTolerancesSetting"
' Parameter 2 : (String) "Default value"
' Parameter 3 : (String) "Unlocked"
' Parameter 4 : (Boolean) False
'--------------------------------------------------

long16 = settingRepository1.GetAttr("CATDrwTbNumDispDescSetting")
'--------------------------------------------------
' Parameter 1 : (String) "CATDrwTbNumDispDescSetting"
' Returned value : (Variant) (Long) 2
'--------------------------------------------------

Dim bSTR77
bSTR77 = ""
Dim bSTR78
bSTR78 = ""
Dim boolean62
settingRepository1.GetAttrInfo "CATDrwTbNumDispDescSetting", bSTR77, bSTR78, boolean62
'--------------------------------------------------
' Parameter 1 : (String) "CATDrwTbNumDispDescSetting"
' Parameter 2 : (String) "Default value"
' Parameter 3 : (String) "Unlocked"
' Parameter 4 : (Boolean) False
'--------------------------------------------------

long17 = settingRepository1.GetAttr("CATDrwTbPrecisionSetting")
'--------------------------------------------------
' Parameter 1 : (String) "CATDrwTbPrecisionSetting"
' Returned value : (Variant) (Long) 2
'--------------------------------------------------

Dim bSTR79
bSTR79 = ""
Dim bSTR80
bSTR80 = ""
Dim boolean63
settingRepository1.GetAttrInfo "CATDrwTbPrecisionSetting", bSTR79, bSTR80, boolean63
'--------------------------------------------------
' Parameter 1 : (String) "CATDrwTbPrecisionSetting"
' Parameter 2 : (String) "Default value"
' Parameter 3 : (String) "Unlocked"
' Parameter 4 : (Boolean) False
'--------------------------------------------------

long18 = settingRepository1.GetAttr("CATDrwTbColorSetting")
'--------------------------------------------------
' Parameter 1 : (String) "CATDrwTbColorSetting"
' Returned value : (Variant) (Long) 2
'--------------------------------------------------

Dim bSTR81
bSTR81 = ""
Dim bSTR82
bSTR82 = ""
Dim boolean64
settingRepository1.GetAttrInfo "CATDrwTbColorSetting", bSTR81, bSTR82, boolean64
'--------------------------------------------------
' Parameter 1 : (String) "CATDrwTbColorSetting"
' Parameter 2 : (String) "Default value"
' Parameter 3 : (String) "Unlocked"
' Parameter 4 : (Boolean) False
'--------------------------------------------------

long19 = settingRepository1.GetAttr("CATDrwTbThicknessSetting")
'--------------------------------------------------
' Parameter 1 : (String) "CATDrwTbThicknessSetting"
' Returned value : (Variant) (Long) 2
'--------------------------------------------------

Dim bSTR83
bSTR83 = ""
Dim bSTR84
bSTR84 = ""
Dim boolean65
settingRepository1.GetAttrInfo "CATDrwTbThicknessSetting", bSTR83, bSTR84, boolean65
'--------------------------------------------------
' Parameter 1 : (String) "CATDrwTbThicknessSetting"
' Parameter 2 : (String) "Default value"
' Parameter 3 : (String) "Unlocked"
' Parameter 4 : (Boolean) False
'--------------------------------------------------

long20 = settingRepository1.GetAttr("CATDrwTbLineTypeSetting")
'--------------------------------------------------
' Parameter 1 : (String) "CATDrwTbLineTypeSetting"
' Returned value : (Variant) (Long) 2
'--------------------------------------------------

Dim bSTR85
bSTR85 = ""
Dim bSTR86
bSTR86 = ""
Dim boolean66
settingRepository1.GetAttrInfo "CATDrwTbLineTypeSetting", bSTR85, bSTR86, boolean66
'--------------------------------------------------
' Parameter 1 : (String) "CATDrwTbLineTypeSetting"
' Parameter 2 : (String) "Default value"
' Parameter 3 : (String) "Unlocked"
' Parameter 4 : (Boolean) False
'--------------------------------------------------

long21 = settingRepository1.GetAttr("CATDrwTbPointTypeSetting")
'--------------------------------------------------
' Parameter 1 : (String) "CATDrwTbPointTypeSetting"
' Returned value : (Variant) (Long) 2
'--------------------------------------------------

Dim bSTR87
bSTR87 = ""
Dim bSTR88
bSTR88 = ""
Dim boolean67
settingRepository1.GetAttrInfo "CATDrwTbPointTypeSetting", bSTR87, bSTR88, boolean67
'--------------------------------------------------
' Parameter 1 : (String) "CATDrwTbPointTypeSetting"
' Parameter 2 : (String) "Default value"
' Parameter 3 : (String) "Unlocked"
' Parameter 4 : (Boolean) False
'--------------------------------------------------

boolean68 = settingRepository1.GetAttr("DistinguishCodeInUnicitySetting")
'--------------------------------------------------
' Parameter 1 : (String) "DistinguishCodeInUnicitySetting"
' Returned value : (Variant) (Boolean) False
'--------------------------------------------------

Dim bSTR89
bSTR89 = ""
Dim bSTR90
bSTR90 = ""
Dim boolean69
settingRepository1.GetAttrInfo "DistinguishCodeInUnicitySetting", bSTR89, bSTR90, boolean69
'--------------------------------------------------
' Parameter 1 : (String) "DistinguishCodeInUnicitySetting"
' Parameter 2 : (String) "Default value"
' Parameter 3 : (String) "Unlocked"
' Parameter 4 : (Boolean) False
'--------------------------------------------------

boolean70 = settingRepository1.GetAttr("DistinguishCaseInUnicitySetting")
'--------------------------------------------------
' Parameter 1 : (String) "DistinguishCaseInUnicitySetting"
' Returned value : (Variant) (Boolean) False
'--------------------------------------------------

Dim bSTR91
bSTR91 = ""
Dim bSTR92
bSTR92 = ""
Dim boolean71
settingRepository1.GetAttrInfo "DistinguishCaseInUnicitySetting", bSTR91, bSTR92, boolean71
'--------------------------------------------------
' Parameter 1 : (String) "DistinguishCaseInUnicitySetting"
' Parameter 2 : (String) "Default value"
' Parameter 3 : (String) "Unlocked"
' Parameter 4 : (Boolean) False
'--------------------------------------------------

boolean72 = settingRepository1.GetAttr("ShowWarningSelectionOutFavoriteContext")
'--------------------------------------------------
' Parameter 1 : (String) "ShowWarningSelectionOutFavoriteContext"
' Returned value : (Variant) (Boolean) True
'--------------------------------------------------

Dim bSTR93
bSTR93 = ""
Dim bSTR94
bSTR94 = ""
Dim boolean73
settingRepository1.GetAttrInfo "ShowWarningSelectionOutFavoriteContext", bSTR93, bSTR94, boolean73
'--------------------------------------------------
' Parameter 1 : (String) "ShowWarningSelectionOutFavoriteContext"
' Parameter 2 : (String) "Default value"
' Parameter 3 : (String) "Unlocked"
' Parameter 4 : (Boolean) False
'--------------------------------------------------

End Sub
