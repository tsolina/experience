Language="VBSCRIPT"

Sub CATMain()

Set settingControllers1 = CATIA.SettingControllers

Set settingRepository1 = settingControllers1.Item("ASDPrefGeneral")

double1 = settingRepository1.GetAttr("DefaultMasterAngularTol")
'--------------------------------------------------
' Parameter 1 : (String) "DefaultMasterAngularTol"
' Returned value : (Variant) (Double) 15.000000
'--------------------------------------------------

Dim bSTR1
bSTR1 = ""
Dim bSTR2
bSTR2 = ""
Dim boolean1
settingRepository1.GetAttrInfo "DefaultMasterAngularTol", bSTR1, bSTR2, boolean1
'--------------------------------------------------
' Parameter 1 : (String) "DefaultMasterAngularTol"
' Parameter 2 : (String) "Default value"
' Parameter 3 : (String) "Unlocked"
' Parameter 4 : (Boolean) False
'--------------------------------------------------

boolean2 = settingRepository1.GetAttr("SameMasterSlaveAngularTol")
'--------------------------------------------------
' Parameter 1 : (String) "SameMasterSlaveAngularTol"
' Returned value : (Variant) (Boolean) True
'--------------------------------------------------

Dim bSTR3
bSTR3 = ""
Dim bSTR4
bSTR4 = ""
Dim boolean3
settingRepository1.GetAttrInfo "SameMasterSlaveAngularTol", bSTR3, bSTR4, boolean3
'--------------------------------------------------
' Parameter 1 : (String) "SameMasterSlaveAngularTol"
' Parameter 2 : (String) "Default value"
' Parameter 3 : (String) "Unlocked"
' Parameter 4 : (Boolean) False
'--------------------------------------------------

double2 = settingRepository1.GetAttr("DefaultSlaveAngularTol")
'--------------------------------------------------
' Parameter 1 : (String) "DefaultSlaveAngularTol"
' Returned value : (Variant) (Double) 0.000000
'--------------------------------------------------

Dim bSTR5
bSTR5 = ""
Dim bSTR6
bSTR6 = ""
Dim boolean4
settingRepository1.GetAttrInfo "DefaultSlaveAngularTol", bSTR5, bSTR6, boolean4
'--------------------------------------------------
' Parameter 1 : (String) "DefaultSlaveAngularTol"
' Parameter 2 : (String) "Default value"
' Parameter 3 : (String) "Unlocked"
' Parameter 4 : (Boolean) False
'--------------------------------------------------

double3 = settingRepository1.GetAttr("DefaultFarOffsetForBox")
'--------------------------------------------------
' Parameter 1 : (String) "DefaultFarOffsetForBox"
' Returned value : (Variant) (Double) 100.000000
'--------------------------------------------------

Dim bSTR7
bSTR7 = ""
Dim bSTR8
bSTR8 = ""
Dim boolean5
settingRepository1.GetAttrInfo "DefaultFarOffsetForBox", bSTR7, bSTR8, boolean5
'--------------------------------------------------
' Parameter 1 : (String) "DefaultFarOffsetForBox"
' Parameter 2 : (String) "Default value"
' Parameter 3 : (String) "Unlocked"
' Parameter 4 : (Boolean) False
'--------------------------------------------------

double4 = settingRepository1.GetAttr("DefaultNearOffsetForBox")
'--------------------------------------------------
' Parameter 1 : (String) "DefaultNearOffsetForBox"
' Returned value : (Variant) (Double) 100.000000
'--------------------------------------------------

Dim bSTR9
bSTR9 = ""
Dim bSTR10
bSTR10 = ""
Dim boolean6
settingRepository1.GetAttrInfo "DefaultNearOffsetForBox", bSTR9, bSTR10, boolean6
'--------------------------------------------------
' Parameter 1 : (String) "DefaultNearOffsetForBox"
' Parameter 2 : (String) "Default value"
' Parameter 3 : (String) "Unlocked"
' Parameter 4 : (Boolean) False
'--------------------------------------------------

boolean7 = settingRepository1.GetAttr("viewer-use-perspective")
'--------------------------------------------------
' Parameter 1 : (String) "viewer-use-perspective"
' Returned value : (Variant) (Boolean) True
'--------------------------------------------------

Dim bSTR11
bSTR11 = ""
Dim bSTR12
bSTR12 = ""
Dim boolean8
settingRepository1.GetAttrInfo "viewer-use-perspective", bSTR11, bSTR12, boolean8
'--------------------------------------------------
' Parameter 1 : (String) "viewer-use-perspective"
' Parameter 2 : (String) "Default value"
' Parameter 3 : (String) "Unlocked"
' Parameter 4 : (Boolean) False
'--------------------------------------------------

double5 = settingRepository1.GetAttr("AnnotNodeSize")
'--------------------------------------------------
' Parameter 1 : (String) "AnnotNodeSize"
' Returned value : (Variant) (Double) 3.300000
'--------------------------------------------------

Dim bSTR13
bSTR13 = ""
Dim bSTR14
bSTR14 = ""
Dim boolean9
settingRepository1.GetAttrInfo "AnnotNodeSize", bSTR13, bSTR14, boolean9
'--------------------------------------------------
' Parameter 1 : (String) "AnnotNodeSize"
' Parameter 2 : (String) "Default value"
' Parameter 3 : (String) "Unlocked"
' Parameter 4 : (Boolean) False
'--------------------------------------------------

Dim arrayOfVariantOfULong1
arrayOfVariantOfULong1 = settingRepository1.GetAttrArray("AnnotNodeColor")
'--------------------------------------------------
' Parameter 1 : (String) "AnnotNodeColor"
' Returned value : (Array) 
'    Array[0] : (Variant) (Unsigned Long) 75
'    Array[1] : (Variant) (Unsigned Long) 130
'    Array[2] : (Variant) (Unsigned Long) 160
'--------------------------------------------------

Dim bSTR15
bSTR15 = ""
Dim bSTR16
bSTR16 = ""
Dim boolean10
settingRepository1.GetAttrInfo "AnnotNodeColor", bSTR15, bSTR16, boolean10
'--------------------------------------------------
' Parameter 1 : (String) "AnnotNodeColor"
' Parameter 2 : (String) "Default value"
' Parameter 3 : (String) "Unlocked"
' Parameter 4 : (Boolean) False
'--------------------------------------------------

boolean11 = settingRepository1.GetAttr("AnnotDiagnostic")
'--------------------------------------------------
' Parameter 1 : (String) "AnnotDiagnostic"
' Returned value : (Variant) (Boolean) True
'--------------------------------------------------

Dim bSTR17
bSTR17 = ""
Dim bSTR18
bSTR18 = ""
Dim boolean12
settingRepository1.GetAttrInfo "AnnotDiagnostic", bSTR17, bSTR18, boolean12
'--------------------------------------------------
' Parameter 1 : (String) "AnnotDiagnostic"
' Parameter 2 : (String) "Default value"
' Parameter 3 : (String) "Unlocked"
' Parameter 4 : (Boolean) False
'--------------------------------------------------

bSTR19 = settingRepository1.GetAttr("DefaultTopForXP")
'--------------------------------------------------
' Parameter 1 : (String) "DefaultTopForXP"
' Returned value : (Variant) (String) "AITStandardOrientation_ZP"
'--------------------------------------------------

Dim bSTR20
bSTR20 = ""
Dim bSTR21
bSTR21 = ""
Dim boolean13
settingRepository1.GetAttrInfo "DefaultTopForXP", bSTR20, bSTR21, boolean13
'--------------------------------------------------
' Parameter 1 : (String) "DefaultTopForXP"
' Parameter 2 : (String) "Default value"
' Parameter 3 : (String) "Unlocked"
' Parameter 4 : (Boolean) False
'--------------------------------------------------

bSTR22 = settingRepository1.GetAttr("DefaultTopForXM")
'--------------------------------------------------
' Parameter 1 : (String) "DefaultTopForXM"
' Returned value : (Variant) (String) "AITStandardOrientation_ZP"
'--------------------------------------------------

Dim bSTR23
bSTR23 = ""
Dim bSTR24
bSTR24 = ""
Dim boolean14
settingRepository1.GetAttrInfo "DefaultTopForXM", bSTR23, bSTR24, boolean14
'--------------------------------------------------
' Parameter 1 : (String) "DefaultTopForXM"
' Parameter 2 : (String) "Default value"
' Parameter 3 : (String) "Unlocked"
' Parameter 4 : (Boolean) False
'--------------------------------------------------

bSTR25 = settingRepository1.GetAttr("DefaultTopForYP")
'--------------------------------------------------
' Parameter 1 : (String) "DefaultTopForYP"
' Returned value : (Variant) (String) "AITStandardOrientation_ZP"
'--------------------------------------------------

Dim bSTR26
bSTR26 = ""
Dim bSTR27
bSTR27 = ""
Dim boolean15
settingRepository1.GetAttrInfo "DefaultTopForYP", bSTR26, bSTR27, boolean15
'--------------------------------------------------
' Parameter 1 : (String) "DefaultTopForYP"
' Parameter 2 : (String) "Default value"
' Parameter 3 : (String) "Unlocked"
' Parameter 4 : (Boolean) False
'--------------------------------------------------

bSTR28 = settingRepository1.GetAttr("DefaultTopForYM")
'--------------------------------------------------
' Parameter 1 : (String) "DefaultTopForYM"
' Returned value : (Variant) (String) "AITStandardOrientation_ZP"
'--------------------------------------------------

Dim bSTR29
bSTR29 = ""
Dim bSTR30
bSTR30 = ""
Dim boolean16
settingRepository1.GetAttrInfo "DefaultTopForYM", bSTR29, bSTR30, boolean16
'--------------------------------------------------
' Parameter 1 : (String) "DefaultTopForYM"
' Parameter 2 : (String) "Default value"
' Parameter 3 : (String) "Unlocked"
' Parameter 4 : (Boolean) False
'--------------------------------------------------

bSTR31 = settingRepository1.GetAttr("DefaultTopForZP")
'--------------------------------------------------
' Parameter 1 : (String) "DefaultTopForZP"
' Returned value : (Variant) (String) "AITStandardOrientation_YM"
'--------------------------------------------------

Dim bSTR32
bSTR32 = ""
Dim bSTR33
bSTR33 = ""
Dim boolean17
settingRepository1.GetAttrInfo "DefaultTopForZP", bSTR32, bSTR33, boolean17
'--------------------------------------------------
' Parameter 1 : (String) "DefaultTopForZP"
' Parameter 2 : (String) "Default value"
' Parameter 3 : (String) "Unlocked"
' Parameter 4 : (Boolean) False
'--------------------------------------------------

bSTR34 = settingRepository1.GetAttr("DefaultTopForZM")
'--------------------------------------------------
' Parameter 1 : (String) "DefaultTopForZM"
' Returned value : (Variant) (String) "AITStandardOrientation_YP"
'--------------------------------------------------

Dim bSTR35
bSTR35 = ""
Dim bSTR36
bSTR36 = ""
Dim boolean18
settingRepository1.GetAttrInfo "DefaultTopForZM", bSTR35, bSTR36, boolean18
'--------------------------------------------------
' Parameter 1 : (String) "DefaultTopForZM"
' Parameter 2 : (String) "Default value"
' Parameter 3 : (String) "Unlocked"
' Parameter 4 : (Boolean) False
'--------------------------------------------------

long1 = settingRepository1.GetAttr("DefaultSlaveRepWeldedStiffener")
'--------------------------------------------------
' Parameter 1 : (String) "DefaultSlaveRepWeldedStiffener"
' Returned value : (Variant) (Long) 1
'--------------------------------------------------

Dim bSTR37
bSTR37 = ""
Dim bSTR38
bSTR38 = ""
Dim boolean19
settingRepository1.GetAttrInfo "DefaultSlaveRepWeldedStiffener", bSTR37, bSTR38, boolean19
'--------------------------------------------------
' Parameter 1 : (String) "DefaultSlaveRepWeldedStiffener"
' Parameter 2 : (String) "Default value"
' Parameter 3 : (String) "Unlocked"
' Parameter 4 : (Boolean) False
'--------------------------------------------------

long2 = settingRepository1.GetAttr("DefaultViewLookingDirX")
'--------------------------------------------------
' Parameter 1 : (String) "DefaultViewLookingDirX"
' Returned value : (Variant) (Long) 0
'--------------------------------------------------

Dim bSTR39
bSTR39 = ""
Dim bSTR40
bSTR40 = ""
Dim boolean20
settingRepository1.GetAttrInfo "DefaultViewLookingDirX", bSTR39, bSTR40, boolean20
'--------------------------------------------------
' Parameter 1 : (String) "DefaultViewLookingDirX"
' Parameter 2 : (String) "Default value"
' Parameter 3 : (String) "Unlocked"
' Parameter 4 : (Boolean) False
'--------------------------------------------------

long3 = settingRepository1.GetAttr("DefaultViewLookingDirY")
'--------------------------------------------------
' Parameter 1 : (String) "DefaultViewLookingDirY"
' Returned value : (Variant) (Long) 2
'--------------------------------------------------

Dim bSTR41
bSTR41 = ""
Dim bSTR42
bSTR42 = ""
Dim boolean21
settingRepository1.GetAttrInfo "DefaultViewLookingDirY", bSTR41, bSTR42, boolean21
'--------------------------------------------------
' Parameter 1 : (String) "DefaultViewLookingDirY"
' Parameter 2 : (String) "Default value"
' Parameter 3 : (String) "Unlocked"
' Parameter 4 : (Boolean) False
'--------------------------------------------------

long4 = settingRepository1.GetAttr("DefaultViewLookingDirZ")
'--------------------------------------------------
' Parameter 1 : (String) "DefaultViewLookingDirZ"
' Returned value : (Variant) (Long) 5
'--------------------------------------------------

Dim bSTR43
bSTR43 = ""
Dim bSTR44
bSTR44 = ""
Dim boolean22
settingRepository1.GetAttrInfo "DefaultViewLookingDirZ", bSTR43, bSTR44, boolean22
'--------------------------------------------------
' Parameter 1 : (String) "DefaultViewLookingDirZ"
' Parameter 2 : (String) "Default value"
' Parameter 3 : (String) "Unlocked"
' Parameter 4 : (Boolean) False
'--------------------------------------------------

long5 = settingRepository1.GetAttr("DefaultSlaveRepPanelBelowTol")
'--------------------------------------------------
' Parameter 1 : (String) "DefaultSlaveRepPanelBelowTol"
' Returned value : (Variant) (Long) 1
'--------------------------------------------------

Dim bSTR45
bSTR45 = ""
Dim bSTR46
bSTR46 = ""
Dim boolean23
settingRepository1.GetAttrInfo "DefaultSlaveRepPanelBelowTol", bSTR45, bSTR46, boolean23
'--------------------------------------------------
' Parameter 1 : (String) "DefaultSlaveRepPanelBelowTol"
' Parameter 2 : (String) "Default value"
' Parameter 3 : (String) "Unlocked"
' Parameter 4 : (Boolean) False
'--------------------------------------------------

long6 = settingRepository1.GetAttr("DefaultSlaveRepPanelAboveTol")
'--------------------------------------------------
' Parameter 1 : (String) "DefaultSlaveRepPanelAboveTol"
' Returned value : (Variant) (Long) 0
'--------------------------------------------------

Dim bSTR47
bSTR47 = ""
Dim bSTR48
bSTR48 = ""
Dim boolean24
settingRepository1.GetAttrInfo "DefaultSlaveRepPanelAboveTol", bSTR47, bSTR48, boolean24
'--------------------------------------------------
' Parameter 1 : (String) "DefaultSlaveRepPanelAboveTol"
' Parameter 2 : (String) "Default value"
' Parameter 3 : (String) "Unlocked"
' Parameter 4 : (Boolean) False
'--------------------------------------------------

long7 = settingRepository1.GetAttr("DefaultSlaveRepCrossingStiffenerBelowTol")
'--------------------------------------------------
' Parameter 1 : (String) "DefaultSlaveRepCrossingStiffenerBelowTol"
' Returned value : (Variant) (Long) 1
'--------------------------------------------------

Dim bSTR49
bSTR49 = ""
Dim bSTR50
bSTR50 = ""
Dim boolean25
settingRepository1.GetAttrInfo "DefaultSlaveRepCrossingStiffenerBelowTol", bSTR49, bSTR50, boolean25
'--------------------------------------------------
' Parameter 1 : (String) "DefaultSlaveRepCrossingStiffenerBelowTol"
' Parameter 2 : (String) "Default value"
' Parameter 3 : (String) "Unlocked"
' Parameter 4 : (Boolean) False
'--------------------------------------------------

long8 = settingRepository1.GetAttr("DefaultSlaveRepCrossingStiffenerAboveTol")
'--------------------------------------------------
' Parameter 1 : (String) "DefaultSlaveRepCrossingStiffenerAboveTol"
' Returned value : (Variant) (Long) 1
'--------------------------------------------------

Dim bSTR51
bSTR51 = ""
Dim bSTR52
bSTR52 = ""
Dim boolean26
settingRepository1.GetAttrInfo "DefaultSlaveRepCrossingStiffenerAboveTol", bSTR51, bSTR52, boolean26
'--------------------------------------------------
' Parameter 1 : (String) "DefaultSlaveRepCrossingStiffenerAboveTol"
' Parameter 2 : (String) "Default value"
' Parameter 3 : (String) "Unlocked"
' Parameter 4 : (Boolean) False
'--------------------------------------------------

Dim arrayOfVariantOfULong2
arrayOfVariantOfULong2 = settingRepository1.GetAttrArray("AnnotUpdateFailureColor")
'--------------------------------------------------
' Parameter 1 : (String) "AnnotUpdateFailureColor"
' Returned value : (Array) 
'    Array[0] : (Variant) (Unsigned Long) 255
'    Array[1] : (Variant) (Unsigned Long) 0
'    Array[2] : (Variant) (Unsigned Long) 128
'--------------------------------------------------

Dim bSTR53
bSTR53 = ""
Dim bSTR54
bSTR54 = ""
Dim boolean27
settingRepository1.GetAttrInfo "AnnotUpdateFailureColor", bSTR53, bSTR54, boolean27
'--------------------------------------------------
' Parameter 1 : (String) "AnnotUpdateFailureColor"
' Parameter 2 : (String) "Default value"
' Parameter 3 : (String) "Unlocked"
' Parameter 4 : (Boolean) False
'--------------------------------------------------

End Sub
