Language="VBSCRIPT"

Sub CATMain()

Set settingControllers1 = CATIA.SettingControllers

Set settingRepository1 = settingControllers1.Item("cke")

long1 = settingRepository1.GetAttr("LENGTH")
'--------------------------------------------------
' Parameter 1 : (String) "LENGTH"
' Returned value : (Variant) (Long) 1
'--------------------------------------------------

Dim bSTR1
bSTR1 = ""
Dim bSTR2
bSTR2 = ""
Dim boolean1
settingRepository1.GetAttrInfo "LENGTH", bSTR1, bSTR2, boolean1
'--------------------------------------------------
' Parameter 1 : (String) "LENGTH"
' Parameter 2 : (String) "Default value"
' Parameter 3 : (String) "Unlocked"
' Parameter 4 : (Boolean) False
'--------------------------------------------------

long2 = settingRepository1.GetAttr("LENGTH_Large")
'--------------------------------------------------
' Parameter 1 : (String) "LENGTH_Large"
' Returned value : (Variant) (Long) 1
'--------------------------------------------------

Dim bSTR3
bSTR3 = ""
Dim bSTR4
bSTR4 = ""
Dim boolean2
settingRepository1.GetAttrInfo "LENGTH_Large", bSTR3, bSTR4, boolean2
'--------------------------------------------------
' Parameter 1 : (String) "LENGTH_Large"
' Parameter 2 : (String) "Default value"
' Parameter 3 : (String) "Unlocked"
' Parameter 4 : (Boolean) False
'--------------------------------------------------

long3 = settingRepository1.GetAttr("LENGTH_ExtraLarge")
'--------------------------------------------------
' Parameter 1 : (String) "LENGTH_ExtraLarge"
' Returned value : (Variant) (Long) 1
'--------------------------------------------------

Dim bSTR5
bSTR5 = ""
Dim bSTR6
bSTR6 = ""
Dim boolean3
settingRepository1.GetAttrInfo "LENGTH_ExtraLarge", bSTR5, bSTR6, boolean3
'--------------------------------------------------
' Parameter 1 : (String) "LENGTH_ExtraLarge"
' Parameter 2 : (String) "Default value"
' Parameter 3 : (String) "Unlocked"
' Parameter 4 : (Boolean) False
'--------------------------------------------------

long4 = settingRepository1.GetAttr("LENGTH_Small")
'--------------------------------------------------
' Parameter 1 : (String) "LENGTH_Small"
' Returned value : (Variant) (Long) 1
'--------------------------------------------------

Dim bSTR7
bSTR7 = ""
Dim bSTR8
bSTR8 = ""
Dim boolean4
settingRepository1.GetAttrInfo "LENGTH_Small", bSTR7, bSTR8, boolean4
'--------------------------------------------------
' Parameter 1 : (String) "LENGTH_Small"
' Parameter 2 : (String) "Default value"
' Parameter 3 : (String) "Unlocked"
' Parameter 4 : (Boolean) False
'--------------------------------------------------

long5 = settingRepository1.GetAttr("LENGTH_ExtraSmall")
'--------------------------------------------------
' Parameter 1 : (String) "LENGTH_ExtraSmall"
' Returned value : (Variant) (Long) 1
'--------------------------------------------------

Dim bSTR9
bSTR9 = ""
Dim bSTR10
bSTR10 = ""
Dim boolean5
settingRepository1.GetAttrInfo "LENGTH_ExtraSmall", bSTR9, bSTR10, boolean5
'--------------------------------------------------
' Parameter 1 : (String) "LENGTH_ExtraSmall"
' Parameter 2 : (String) "Default value"
' Parameter 3 : (String) "Unlocked"
' Parameter 4 : (Boolean) False
'--------------------------------------------------

long6 = settingRepository1.GetAttr("LENGTH_Nanometric")
'--------------------------------------------------
' Parameter 1 : (String) "LENGTH_Nanometric"
' Returned value : (Variant) (Long) 1
'--------------------------------------------------

Dim bSTR11
bSTR11 = ""
Dim bSTR12
bSTR12 = ""
Dim boolean6
settingRepository1.GetAttrInfo "LENGTH_Nanometric", bSTR11, bSTR12, boolean6
'--------------------------------------------------
' Parameter 1 : (String) "LENGTH_Nanometric"
' Parameter 2 : (String) "Default value"
' Parameter 3 : (String) "Unlocked"
' Parameter 4 : (Boolean) False
'--------------------------------------------------

long7 = settingRepository1.GetAttr("ANGLE")
'--------------------------------------------------
' Parameter 1 : (String) "ANGLE"
' Returned value : (Variant) (Long) 1
'--------------------------------------------------

Dim bSTR13
bSTR13 = ""
Dim bSTR14
bSTR14 = ""
Dim boolean7
settingRepository1.GetAttrInfo "ANGLE", bSTR13, bSTR14, boolean7
'--------------------------------------------------
' Parameter 1 : (String) "ANGLE"
' Parameter 2 : (String) "Default value"
' Parameter 3 : (String) "Unlocked"
' Parameter 4 : (Boolean) False
'--------------------------------------------------

long8 = settingRepository1.GetAttr("ANGLE_Large")
'--------------------------------------------------
' Parameter 1 : (String) "ANGLE_Large"
' Returned value : (Variant) (Long) 1
'--------------------------------------------------

Dim bSTR15
bSTR15 = ""
Dim bSTR16
bSTR16 = ""
Dim boolean8
settingRepository1.GetAttrInfo "ANGLE_Large", bSTR15, bSTR16, boolean8
'--------------------------------------------------
' Parameter 1 : (String) "ANGLE_Large"
' Parameter 2 : (String) "Default value"
' Parameter 3 : (String) "Unlocked"
' Parameter 4 : (Boolean) False
'--------------------------------------------------

long9 = settingRepository1.GetAttr("ANGLE_ExtraLarge")
'--------------------------------------------------
' Parameter 1 : (String) "ANGLE_ExtraLarge"
' Returned value : (Variant) (Long) 1
'--------------------------------------------------

Dim bSTR17
bSTR17 = ""
Dim bSTR18
bSTR18 = ""
Dim boolean9
settingRepository1.GetAttrInfo "ANGLE_ExtraLarge", bSTR17, bSTR18, boolean9
'--------------------------------------------------
' Parameter 1 : (String) "ANGLE_ExtraLarge"
' Parameter 2 : (String) "Default value"
' Parameter 3 : (String) "Unlocked"
' Parameter 4 : (Boolean) False
'--------------------------------------------------

long10 = settingRepository1.GetAttr("ANGLE_Small")
'--------------------------------------------------
' Parameter 1 : (String) "ANGLE_Small"
' Returned value : (Variant) (Long) 1
'--------------------------------------------------

Dim bSTR19
bSTR19 = ""
Dim bSTR20
bSTR20 = ""
Dim boolean10
settingRepository1.GetAttrInfo "ANGLE_Small", bSTR19, bSTR20, boolean10
'--------------------------------------------------
' Parameter 1 : (String) "ANGLE_Small"
' Parameter 2 : (String) "Default value"
' Parameter 3 : (String) "Unlocked"
' Parameter 4 : (Boolean) False
'--------------------------------------------------

long11 = settingRepository1.GetAttr("ANGLE_ExtraSmall")
'--------------------------------------------------
' Parameter 1 : (String) "ANGLE_ExtraSmall"
' Returned value : (Variant) (Long) 1
'--------------------------------------------------

Dim bSTR21
bSTR21 = ""
Dim bSTR22
bSTR22 = ""
Dim boolean11
settingRepository1.GetAttrInfo "ANGLE_ExtraSmall", bSTR21, bSTR22, boolean11
'--------------------------------------------------
' Parameter 1 : (String) "ANGLE_ExtraSmall"
' Parameter 2 : (String) "Default value"
' Parameter 3 : (String) "Unlocked"
' Parameter 4 : (Boolean) False
'--------------------------------------------------

long12 = settingRepository1.GetAttr("ANGLE_Nanometric")
'--------------------------------------------------
' Parameter 1 : (String) "ANGLE_Nanometric"
' Returned value : (Variant) (Long) 1
'--------------------------------------------------

Dim bSTR23
bSTR23 = ""
Dim bSTR24
bSTR24 = ""
Dim boolean12
settingRepository1.GetAttrInfo "ANGLE_Nanometric", bSTR23, bSTR24, boolean12
'--------------------------------------------------
' Parameter 1 : (String) "ANGLE_Nanometric"
' Parameter 2 : (String) "Default value"
' Parameter 3 : (String) "Unlocked"
' Parameter 4 : (Boolean) False
'--------------------------------------------------

long13 = settingRepository1.GetAttr("TIME")
'--------------------------------------------------
' Parameter 1 : (String) "TIME"
' Returned value : (Variant) (Long) 1
'--------------------------------------------------

Dim bSTR25
bSTR25 = ""
Dim bSTR26
bSTR26 = ""
Dim boolean13
settingRepository1.GetAttrInfo "TIME", bSTR25, bSTR26, boolean13
'--------------------------------------------------
' Parameter 1 : (String) "TIME"
' Parameter 2 : (String) "Default value"
' Parameter 3 : (String) "Unlocked"
' Parameter 4 : (Boolean) False
'--------------------------------------------------

long14 = settingRepository1.GetAttr("TIME_Large")
'--------------------------------------------------
' Parameter 1 : (String) "TIME_Large"
' Returned value : (Variant) (Long) 1
'--------------------------------------------------

Dim bSTR27
bSTR27 = ""
Dim bSTR28
bSTR28 = ""
Dim boolean14
settingRepository1.GetAttrInfo "TIME_Large", bSTR27, bSTR28, boolean14
'--------------------------------------------------
' Parameter 1 : (String) "TIME_Large"
' Parameter 2 : (String) "Default value"
' Parameter 3 : (String) "Unlocked"
' Parameter 4 : (Boolean) False
'--------------------------------------------------

long15 = settingRepository1.GetAttr("TIME_ExtraLarge")
'--------------------------------------------------
' Parameter 1 : (String) "TIME_ExtraLarge"
' Returned value : (Variant) (Long) 1
'--------------------------------------------------

Dim bSTR29
bSTR29 = ""
Dim bSTR30
bSTR30 = ""
Dim boolean15
settingRepository1.GetAttrInfo "TIME_ExtraLarge", bSTR29, bSTR30, boolean15
'--------------------------------------------------
' Parameter 1 : (String) "TIME_ExtraLarge"
' Parameter 2 : (String) "Default value"
' Parameter 3 : (String) "Unlocked"
' Parameter 4 : (Boolean) False
'--------------------------------------------------

long16 = settingRepository1.GetAttr("TIME_Small")
'--------------------------------------------------
' Parameter 1 : (String) "TIME_Small"
' Returned value : (Variant) (Long) 1
'--------------------------------------------------

Dim bSTR31
bSTR31 = ""
Dim bSTR32
bSTR32 = ""
Dim boolean16
settingRepository1.GetAttrInfo "TIME_Small", bSTR31, bSTR32, boolean16
'--------------------------------------------------
' Parameter 1 : (String) "TIME_Small"
' Parameter 2 : (String) "Default value"
' Parameter 3 : (String) "Unlocked"
' Parameter 4 : (Boolean) False
'--------------------------------------------------

long17 = settingRepository1.GetAttr("TIME_ExtraSmall")
'--------------------------------------------------
' Parameter 1 : (String) "TIME_ExtraSmall"
' Returned value : (Variant) (Long) 1
'--------------------------------------------------

Dim bSTR33
bSTR33 = ""
Dim bSTR34
bSTR34 = ""
Dim boolean17
settingRepository1.GetAttrInfo "TIME_ExtraSmall", bSTR33, bSTR34, boolean17
'--------------------------------------------------
' Parameter 1 : (String) "TIME_ExtraSmall"
' Parameter 2 : (String) "Default value"
' Parameter 3 : (String) "Unlocked"
' Parameter 4 : (Boolean) False
'--------------------------------------------------

long18 = settingRepository1.GetAttr("TIME_Nanometric")
'--------------------------------------------------
' Parameter 1 : (String) "TIME_Nanometric"
' Returned value : (Variant) (Long) 1
'--------------------------------------------------

Dim bSTR35
bSTR35 = ""
Dim bSTR36
bSTR36 = ""
Dim boolean18
settingRepository1.GetAttrInfo "TIME_Nanometric", bSTR35, bSTR36, boolean18
'--------------------------------------------------
' Parameter 1 : (String) "TIME_Nanometric"
' Parameter 2 : (String) "Default value"
' Parameter 3 : (String) "Unlocked"
' Parameter 4 : (Boolean) False
'--------------------------------------------------

long19 = settingRepository1.GetAttr("MASS")
'--------------------------------------------------
' Parameter 1 : (String) "MASS"
' Returned value : (Variant) (Long) 1
'--------------------------------------------------

Dim bSTR37
bSTR37 = ""
Dim bSTR38
bSTR38 = ""
Dim boolean19
settingRepository1.GetAttrInfo "MASS", bSTR37, bSTR38, boolean19
'--------------------------------------------------
' Parameter 1 : (String) "MASS"
' Parameter 2 : (String) "Default value"
' Parameter 3 : (String) "Unlocked"
' Parameter 4 : (Boolean) False
'--------------------------------------------------

long20 = settingRepository1.GetAttr("MASS_Large")
'--------------------------------------------------
' Parameter 1 : (String) "MASS_Large"
' Returned value : (Variant) (Long) 1
'--------------------------------------------------

Dim bSTR39
bSTR39 = ""
Dim bSTR40
bSTR40 = ""
Dim boolean20
settingRepository1.GetAttrInfo "MASS_Large", bSTR39, bSTR40, boolean20
'--------------------------------------------------
' Parameter 1 : (String) "MASS_Large"
' Parameter 2 : (String) "Default value"
' Parameter 3 : (String) "Unlocked"
' Parameter 4 : (Boolean) False
'--------------------------------------------------

long21 = settingRepository1.GetAttr("MASS_ExtraLarge")
'--------------------------------------------------
' Parameter 1 : (String) "MASS_ExtraLarge"
' Returned value : (Variant) (Long) 1
'--------------------------------------------------

Dim bSTR41
bSTR41 = ""
Dim bSTR42
bSTR42 = ""
Dim boolean21
settingRepository1.GetAttrInfo "MASS_ExtraLarge", bSTR41, bSTR42, boolean21
'--------------------------------------------------
' Parameter 1 : (String) "MASS_ExtraLarge"
' Parameter 2 : (String) "Default value"
' Parameter 3 : (String) "Unlocked"
' Parameter 4 : (Boolean) False
'--------------------------------------------------

long22 = settingRepository1.GetAttr("MASS_Small")
'--------------------------------------------------
' Parameter 1 : (String) "MASS_Small"
' Returned value : (Variant) (Long) 1
'--------------------------------------------------

Dim bSTR43
bSTR43 = ""
Dim bSTR44
bSTR44 = ""
Dim boolean22
settingRepository1.GetAttrInfo "MASS_Small", bSTR43, bSTR44, boolean22
'--------------------------------------------------
' Parameter 1 : (String) "MASS_Small"
' Parameter 2 : (String) "Default value"
' Parameter 3 : (String) "Unlocked"
' Parameter 4 : (Boolean) False
'--------------------------------------------------

long23 = settingRepository1.GetAttr("MASS_ExtraSmall")
'--------------------------------------------------
' Parameter 1 : (String) "MASS_ExtraSmall"
' Returned value : (Variant) (Long) 1
'--------------------------------------------------

Dim bSTR45
bSTR45 = ""
Dim bSTR46
bSTR46 = ""
Dim boolean23
settingRepository1.GetAttrInfo "MASS_ExtraSmall", bSTR45, bSTR46, boolean23
'--------------------------------------------------
' Parameter 1 : (String) "MASS_ExtraSmall"
' Parameter 2 : (String) "Default value"
' Parameter 3 : (String) "Unlocked"
' Parameter 4 : (Boolean) False
'--------------------------------------------------

long24 = settingRepository1.GetAttr("MASS_Nanometric")
'--------------------------------------------------
' Parameter 1 : (String) "MASS_Nanometric"
' Returned value : (Variant) (Long) 1
'--------------------------------------------------

Dim bSTR47
bSTR47 = ""
Dim bSTR48
bSTR48 = ""
Dim boolean24
settingRepository1.GetAttrInfo "MASS_Nanometric", bSTR47, bSTR48, boolean24
'--------------------------------------------------
' Parameter 1 : (String) "MASS_Nanometric"
' Parameter 2 : (String) "Default value"
' Parameter 3 : (String) "Unlocked"
' Parameter 4 : (Boolean) False
'--------------------------------------------------

long25 = settingRepository1.GetAttr("VOLUME")
'--------------------------------------------------
' Parameter 1 : (String) "VOLUME"
' Returned value : (Variant) (Long) 1
'--------------------------------------------------

Dim bSTR49
bSTR49 = ""
Dim bSTR50
bSTR50 = ""
Dim boolean25
settingRepository1.GetAttrInfo "VOLUME", bSTR49, bSTR50, boolean25
'--------------------------------------------------
' Parameter 1 : (String) "VOLUME"
' Parameter 2 : (String) "Default value"
' Parameter 3 : (String) "Unlocked"
' Parameter 4 : (Boolean) False
'--------------------------------------------------

long26 = settingRepository1.GetAttr("VOLUME_Large")
'--------------------------------------------------
' Parameter 1 : (String) "VOLUME_Large"
' Returned value : (Variant) (Long) 1
'--------------------------------------------------

Dim bSTR51
bSTR51 = ""
Dim bSTR52
bSTR52 = ""
Dim boolean26
settingRepository1.GetAttrInfo "VOLUME_Large", bSTR51, bSTR52, boolean26
'--------------------------------------------------
' Parameter 1 : (String) "VOLUME_Large"
' Parameter 2 : (String) "Default value"
' Parameter 3 : (String) "Unlocked"
' Parameter 4 : (Boolean) False
'--------------------------------------------------

long27 = settingRepository1.GetAttr("VOLUME_ExtraLarge")
'--------------------------------------------------
' Parameter 1 : (String) "VOLUME_ExtraLarge"
' Returned value : (Variant) (Long) 1
'--------------------------------------------------

Dim bSTR53
bSTR53 = ""
Dim bSTR54
bSTR54 = ""
Dim boolean27
settingRepository1.GetAttrInfo "VOLUME_ExtraLarge", bSTR53, bSTR54, boolean27
'--------------------------------------------------
' Parameter 1 : (String) "VOLUME_ExtraLarge"
' Parameter 2 : (String) "Default value"
' Parameter 3 : (String) "Unlocked"
' Parameter 4 : (Boolean) False
'--------------------------------------------------

long28 = settingRepository1.GetAttr("VOLUME_Small")
'--------------------------------------------------
' Parameter 1 : (String) "VOLUME_Small"
' Returned value : (Variant) (Long) 1
'--------------------------------------------------

Dim bSTR55
bSTR55 = ""
Dim bSTR56
bSTR56 = ""
Dim boolean28
settingRepository1.GetAttrInfo "VOLUME_Small", bSTR55, bSTR56, boolean28
'--------------------------------------------------
' Parameter 1 : (String) "VOLUME_Small"
' Parameter 2 : (String) "Default value"
' Parameter 3 : (String) "Unlocked"
' Parameter 4 : (Boolean) False
'--------------------------------------------------

long29 = settingRepository1.GetAttr("VOLUME_ExtraSmall")
'--------------------------------------------------
' Parameter 1 : (String) "VOLUME_ExtraSmall"
' Returned value : (Variant) (Long) 1
'--------------------------------------------------

Dim bSTR57
bSTR57 = ""
Dim bSTR58
bSTR58 = ""
Dim boolean29
settingRepository1.GetAttrInfo "VOLUME_ExtraSmall", bSTR57, bSTR58, boolean29
'--------------------------------------------------
' Parameter 1 : (String) "VOLUME_ExtraSmall"
' Parameter 2 : (String) "Default value"
' Parameter 3 : (String) "Unlocked"
' Parameter 4 : (Boolean) False
'--------------------------------------------------

long30 = settingRepository1.GetAttr("VOLUME_Nanometric")
'--------------------------------------------------
' Parameter 1 : (String) "VOLUME_Nanometric"
' Returned value : (Variant) (Long) 1
'--------------------------------------------------

Dim bSTR59
bSTR59 = ""
Dim bSTR60
bSTR60 = ""
Dim boolean30
settingRepository1.GetAttrInfo "VOLUME_Nanometric", bSTR59, bSTR60, boolean30
'--------------------------------------------------
' Parameter 1 : (String) "VOLUME_Nanometric"
' Parameter 2 : (String) "Default value"
' Parameter 3 : (String) "Unlocked"
' Parameter 4 : (Boolean) False
'--------------------------------------------------

long31 = settingRepository1.GetAttr("DENSITY")
'--------------------------------------------------
' Parameter 1 : (String) "DENSITY"
' Returned value : (Variant) (Long) 1
'--------------------------------------------------

Dim bSTR61
bSTR61 = ""
Dim bSTR62
bSTR62 = ""
Dim boolean31
settingRepository1.GetAttrInfo "DENSITY", bSTR61, bSTR62, boolean31
'--------------------------------------------------
' Parameter 1 : (String) "DENSITY"
' Parameter 2 : (String) "Default value"
' Parameter 3 : (String) "Unlocked"
' Parameter 4 : (Boolean) False
'--------------------------------------------------

long32 = settingRepository1.GetAttr("DENSITY_Large")
'--------------------------------------------------
' Parameter 1 : (String) "DENSITY_Large"
' Returned value : (Variant) (Long) 1
'--------------------------------------------------

Dim bSTR63
bSTR63 = ""
Dim bSTR64
bSTR64 = ""
Dim boolean32
settingRepository1.GetAttrInfo "DENSITY_Large", bSTR63, bSTR64, boolean32
'--------------------------------------------------
' Parameter 1 : (String) "DENSITY_Large"
' Parameter 2 : (String) "Default value"
' Parameter 3 : (String) "Unlocked"
' Parameter 4 : (Boolean) False
'--------------------------------------------------

long33 = settingRepository1.GetAttr("DENSITY_ExtraLarge")
'--------------------------------------------------
' Parameter 1 : (String) "DENSITY_ExtraLarge"
' Returned value : (Variant) (Long) 1
'--------------------------------------------------

Dim bSTR65
bSTR65 = ""
Dim bSTR66
bSTR66 = ""
Dim boolean33
settingRepository1.GetAttrInfo "DENSITY_ExtraLarge", bSTR65, bSTR66, boolean33
'--------------------------------------------------
' Parameter 1 : (String) "DENSITY_ExtraLarge"
' Parameter 2 : (String) "Default value"
' Parameter 3 : (String) "Unlocked"
' Parameter 4 : (Boolean) False
'--------------------------------------------------

long34 = settingRepository1.GetAttr("DENSITY_Small")
'--------------------------------------------------
' Parameter 1 : (String) "DENSITY_Small"
' Returned value : (Variant) (Long) 1
'--------------------------------------------------

Dim bSTR67
bSTR67 = ""
Dim bSTR68
bSTR68 = ""
Dim boolean34
settingRepository1.GetAttrInfo "DENSITY_Small", bSTR67, bSTR68, boolean34
'--------------------------------------------------
' Parameter 1 : (String) "DENSITY_Small"
' Parameter 2 : (String) "Default value"
' Parameter 3 : (String) "Unlocked"
' Parameter 4 : (Boolean) False
'--------------------------------------------------

long35 = settingRepository1.GetAttr("DENSITY_ExtraSmall")
'--------------------------------------------------
' Parameter 1 : (String) "DENSITY_ExtraSmall"
' Returned value : (Variant) (Long) 1
'--------------------------------------------------

Dim bSTR69
bSTR69 = ""
Dim bSTR70
bSTR70 = ""
Dim boolean35
settingRepository1.GetAttrInfo "DENSITY_ExtraSmall", bSTR69, bSTR70, boolean35
'--------------------------------------------------
' Parameter 1 : (String) "DENSITY_ExtraSmall"
' Parameter 2 : (String) "Default value"
' Parameter 3 : (String) "Unlocked"
' Parameter 4 : (Boolean) False
'--------------------------------------------------

long36 = settingRepository1.GetAttr("DENSITY_Nanometric")
'--------------------------------------------------
' Parameter 1 : (String) "DENSITY_Nanometric"
' Returned value : (Variant) (Long) 1
'--------------------------------------------------

Dim bSTR71
bSTR71 = ""
Dim bSTR72
bSTR72 = ""
Dim boolean36
settingRepository1.GetAttrInfo "DENSITY_Nanometric", bSTR71, bSTR72, boolean36
'--------------------------------------------------
' Parameter 1 : (String) "DENSITY_Nanometric"
' Parameter 2 : (String) "Default value"
' Parameter 3 : (String) "Unlocked"
' Parameter 4 : (Boolean) False
'--------------------------------------------------

long37 = settingRepository1.GetAttr("AREA")
'--------------------------------------------------
' Parameter 1 : (String) "AREA"
' Returned value : (Variant) (Long) 1
'--------------------------------------------------

Dim bSTR73
bSTR73 = ""
Dim bSTR74
bSTR74 = ""
Dim boolean37
settingRepository1.GetAttrInfo "AREA", bSTR73, bSTR74, boolean37
'--------------------------------------------------
' Parameter 1 : (String) "AREA"
' Parameter 2 : (String) "Default value"
' Parameter 3 : (String) "Unlocked"
' Parameter 4 : (Boolean) False
'--------------------------------------------------

long38 = settingRepository1.GetAttr("AREA_Large")
'--------------------------------------------------
' Parameter 1 : (String) "AREA_Large"
' Returned value : (Variant) (Long) 1
'--------------------------------------------------

Dim bSTR75
bSTR75 = ""
Dim bSTR76
bSTR76 = ""
Dim boolean38
settingRepository1.GetAttrInfo "AREA_Large", bSTR75, bSTR76, boolean38
'--------------------------------------------------
' Parameter 1 : (String) "AREA_Large"
' Parameter 2 : (String) "Default value"
' Parameter 3 : (String) "Unlocked"
' Parameter 4 : (Boolean) False
'--------------------------------------------------

long39 = settingRepository1.GetAttr("AREA_ExtraLarge")
'--------------------------------------------------
' Parameter 1 : (String) "AREA_ExtraLarge"
' Returned value : (Variant) (Long) 1
'--------------------------------------------------

Dim bSTR77
bSTR77 = ""
Dim bSTR78
bSTR78 = ""
Dim boolean39
settingRepository1.GetAttrInfo "AREA_ExtraLarge", bSTR77, bSTR78, boolean39
'--------------------------------------------------
' Parameter 1 : (String) "AREA_ExtraLarge"
' Parameter 2 : (String) "Default value"
' Parameter 3 : (String) "Unlocked"
' Parameter 4 : (Boolean) False
'--------------------------------------------------

long40 = settingRepository1.GetAttr("AREA_Small")
'--------------------------------------------------
' Parameter 1 : (String) "AREA_Small"
' Returned value : (Variant) (Long) 1
'--------------------------------------------------

Dim bSTR79
bSTR79 = ""
Dim bSTR80
bSTR80 = ""
Dim boolean40
settingRepository1.GetAttrInfo "AREA_Small", bSTR79, bSTR80, boolean40
'--------------------------------------------------
' Parameter 1 : (String) "AREA_Small"
' Parameter 2 : (String) "Default value"
' Parameter 3 : (String) "Unlocked"
' Parameter 4 : (Boolean) False
'--------------------------------------------------

long41 = settingRepository1.GetAttr("AREA_ExtraSmall")
'--------------------------------------------------
' Parameter 1 : (String) "AREA_ExtraSmall"
' Returned value : (Variant) (Long) 1
'--------------------------------------------------

Dim bSTR81
bSTR81 = ""
Dim bSTR82
bSTR82 = ""
Dim boolean41
settingRepository1.GetAttrInfo "AREA_ExtraSmall", bSTR81, bSTR82, boolean41
'--------------------------------------------------
' Parameter 1 : (String) "AREA_ExtraSmall"
' Parameter 2 : (String) "Default value"
' Parameter 3 : (String) "Unlocked"
' Parameter 4 : (Boolean) False
'--------------------------------------------------

long42 = settingRepository1.GetAttr("AREA_Nanometric")
'--------------------------------------------------
' Parameter 1 : (String) "AREA_Nanometric"
' Returned value : (Variant) (Long) 1
'--------------------------------------------------

Dim bSTR83
bSTR83 = ""
Dim bSTR84
bSTR84 = ""
Dim boolean42
settingRepository1.GetAttrInfo "AREA_Nanometric", bSTR83, bSTR84, boolean42
'--------------------------------------------------
' Parameter 1 : (String) "AREA_Nanometric"
' Parameter 2 : (String) "Default value"
' Parameter 3 : (String) "Unlocked"
' Parameter 4 : (Boolean) False
'--------------------------------------------------

long43 = settingRepository1.GetAttr("INERTIAMOMENT")
'--------------------------------------------------
' Parameter 1 : (String) "INERTIAMOMENT"
' Returned value : (Variant) (Long) 1
'--------------------------------------------------

Dim bSTR85
bSTR85 = ""
Dim bSTR86
bSTR86 = ""
Dim boolean43
settingRepository1.GetAttrInfo "INERTIAMOMENT", bSTR85, bSTR86, boolean43
'--------------------------------------------------
' Parameter 1 : (String) "INERTIAMOMENT"
' Parameter 2 : (String) "Default value"
' Parameter 3 : (String) "Unlocked"
' Parameter 4 : (Boolean) False
'--------------------------------------------------

long44 = settingRepository1.GetAttr("INERTIAMOMENT_Large")
'--------------------------------------------------
' Parameter 1 : (String) "INERTIAMOMENT_Large"
' Returned value : (Variant) (Long) 1
'--------------------------------------------------

Dim bSTR87
bSTR87 = ""
Dim bSTR88
bSTR88 = ""
Dim boolean44
settingRepository1.GetAttrInfo "INERTIAMOMENT_Large", bSTR87, bSTR88, boolean44
'--------------------------------------------------
' Parameter 1 : (String) "INERTIAMOMENT_Large"
' Parameter 2 : (String) "Default value"
' Parameter 3 : (String) "Unlocked"
' Parameter 4 : (Boolean) False
'--------------------------------------------------

long45 = settingRepository1.GetAttr("INERTIAMOMENT_ExtraLarge")
'--------------------------------------------------
' Parameter 1 : (String) "INERTIAMOMENT_ExtraLarge"
' Returned value : (Variant) (Long) 1
'--------------------------------------------------

Dim bSTR89
bSTR89 = ""
Dim bSTR90
bSTR90 = ""
Dim boolean45
settingRepository1.GetAttrInfo "INERTIAMOMENT_ExtraLarge", bSTR89, bSTR90, boolean45
'--------------------------------------------------
' Parameter 1 : (String) "INERTIAMOMENT_ExtraLarge"
' Parameter 2 : (String) "Default value"
' Parameter 3 : (String) "Unlocked"
' Parameter 4 : (Boolean) False
'--------------------------------------------------

long46 = settingRepository1.GetAttr("INERTIAMOMENT_Small")
'--------------------------------------------------
' Parameter 1 : (String) "INERTIAMOMENT_Small"
' Returned value : (Variant) (Long) 1
'--------------------------------------------------

Dim bSTR91
bSTR91 = ""
Dim bSTR92
bSTR92 = ""
Dim boolean46
settingRepository1.GetAttrInfo "INERTIAMOMENT_Small", bSTR91, bSTR92, boolean46
'--------------------------------------------------
' Parameter 1 : (String) "INERTIAMOMENT_Small"
' Parameter 2 : (String) "Default value"
' Parameter 3 : (String) "Unlocked"
' Parameter 4 : (Boolean) False
'--------------------------------------------------

long47 = settingRepository1.GetAttr("INERTIAMOMENT_ExtraSmall")
'--------------------------------------------------
' Parameter 1 : (String) "INERTIAMOMENT_ExtraSmall"
' Returned value : (Variant) (Long) 1
'--------------------------------------------------

Dim bSTR93
bSTR93 = ""
Dim bSTR94
bSTR94 = ""
Dim boolean47
settingRepository1.GetAttrInfo "INERTIAMOMENT_ExtraSmall", bSTR93, bSTR94, boolean47
'--------------------------------------------------
' Parameter 1 : (String) "INERTIAMOMENT_ExtraSmall"
' Parameter 2 : (String) "Default value"
' Parameter 3 : (String) "Unlocked"
' Parameter 4 : (Boolean) False
'--------------------------------------------------

long48 = settingRepository1.GetAttr("INERTIAMOMENT_Nanometric")
'--------------------------------------------------
' Parameter 1 : (String) "INERTIAMOMENT_Nanometric"
' Returned value : (Variant) (Long) 1
'--------------------------------------------------

Dim bSTR95
bSTR95 = ""
Dim bSTR96
bSTR96 = ""
Dim boolean48
settingRepository1.GetAttrInfo "INERTIAMOMENT_Nanometric", bSTR95, bSTR96, boolean48
'--------------------------------------------------
' Parameter 1 : (String) "INERTIAMOMENT_Nanometric"
' Parameter 2 : (String) "Default value"
' Parameter 3 : (String) "Unlocked"
' Parameter 4 : (Boolean) False
'--------------------------------------------------

long49 = settingRepository1.GetAttr("ENERGY")
'--------------------------------------------------
' Parameter 1 : (String) "ENERGY"
' Returned value : (Variant) (Long) 1
'--------------------------------------------------

Dim bSTR97
bSTR97 = ""
Dim bSTR98
bSTR98 = ""
Dim boolean49
settingRepository1.GetAttrInfo "ENERGY", bSTR97, bSTR98, boolean49
'--------------------------------------------------
' Parameter 1 : (String) "ENERGY"
' Parameter 2 : (String) "Default value"
' Parameter 3 : (String) "Unlocked"
' Parameter 4 : (Boolean) False
'--------------------------------------------------

long50 = settingRepository1.GetAttr("ENERGY_Large")
'--------------------------------------------------
' Parameter 1 : (String) "ENERGY_Large"
' Returned value : (Variant) (Long) 1
'--------------------------------------------------

Dim bSTR99
bSTR99 = ""
Dim bSTR100
bSTR100 = ""
Dim boolean50
settingRepository1.GetAttrInfo "ENERGY_Large", bSTR99, bSTR100, boolean50
'--------------------------------------------------
' Parameter 1 : (String) "ENERGY_Large"
' Parameter 2 : (String) "Default value"
' Parameter 3 : (String) "Unlocked"
' Parameter 4 : (Boolean) False
'--------------------------------------------------

long51 = settingRepository1.GetAttr("ENERGY_ExtraLarge")
'--------------------------------------------------
' Parameter 1 : (String) "ENERGY_ExtraLarge"
' Returned value : (Variant) (Long) 1
'--------------------------------------------------

Dim bSTR101
bSTR101 = ""
Dim bSTR102
bSTR102 = ""
Dim boolean51
settingRepository1.GetAttrInfo "ENERGY_ExtraLarge", bSTR101, bSTR102, boolean51
'--------------------------------------------------
' Parameter 1 : (String) "ENERGY_ExtraLarge"
' Parameter 2 : (String) "Default value"
' Parameter 3 : (String) "Unlocked"
' Parameter 4 : (Boolean) False
'--------------------------------------------------

long52 = settingRepository1.GetAttr("ENERGY_Small")
'--------------------------------------------------
' Parameter 1 : (String) "ENERGY_Small"
' Returned value : (Variant) (Long) 1
'--------------------------------------------------

Dim bSTR103
bSTR103 = ""
Dim bSTR104
bSTR104 = ""
Dim boolean52
settingRepository1.GetAttrInfo "ENERGY_Small", bSTR103, bSTR104, boolean52
'--------------------------------------------------
' Parameter 1 : (String) "ENERGY_Small"
' Parameter 2 : (String) "Default value"
' Parameter 3 : (String) "Unlocked"
' Parameter 4 : (Boolean) False
'--------------------------------------------------

long53 = settingRepository1.GetAttr("ENERGY_ExtraSmall")
'--------------------------------------------------
' Parameter 1 : (String) "ENERGY_ExtraSmall"
' Returned value : (Variant) (Long) 1
'--------------------------------------------------

Dim bSTR105
bSTR105 = ""
Dim bSTR106
bSTR106 = ""
Dim boolean53
settingRepository1.GetAttrInfo "ENERGY_ExtraSmall", bSTR105, bSTR106, boolean53
'--------------------------------------------------
' Parameter 1 : (String) "ENERGY_ExtraSmall"
' Parameter 2 : (String) "Default value"
' Parameter 3 : (String) "Unlocked"
' Parameter 4 : (Boolean) False
'--------------------------------------------------

long54 = settingRepository1.GetAttr("ENERGY_Nanometric")
'--------------------------------------------------
' Parameter 1 : (String) "ENERGY_Nanometric"
' Returned value : (Variant) (Long) 1
'--------------------------------------------------

Dim bSTR107
bSTR107 = ""
Dim bSTR108
bSTR108 = ""
Dim boolean54
settingRepository1.GetAttrInfo "ENERGY_Nanometric", bSTR107, bSTR108, boolean54
'--------------------------------------------------
' Parameter 1 : (String) "ENERGY_Nanometric"
' Parameter 2 : (String) "Default value"
' Parameter 3 : (String) "Unlocked"
' Parameter 4 : (Boolean) False
'--------------------------------------------------

long55 = settingRepository1.GetAttr("FORCE")
'--------------------------------------------------
' Parameter 1 : (String) "FORCE"
' Returned value : (Variant) (Long) 1
'--------------------------------------------------

Dim bSTR109
bSTR109 = ""
Dim bSTR110
bSTR110 = ""
Dim boolean55
settingRepository1.GetAttrInfo "FORCE", bSTR109, bSTR110, boolean55
'--------------------------------------------------
' Parameter 1 : (String) "FORCE"
' Parameter 2 : (String) "Default value"
' Parameter 3 : (String) "Unlocked"
' Parameter 4 : (Boolean) False
'--------------------------------------------------

long56 = settingRepository1.GetAttr("FORCE_Large")
'--------------------------------------------------
' Parameter 1 : (String) "FORCE_Large"
' Returned value : (Variant) (Long) 1
'--------------------------------------------------

Dim bSTR111
bSTR111 = ""
Dim bSTR112
bSTR112 = ""
Dim boolean56
settingRepository1.GetAttrInfo "FORCE_Large", bSTR111, bSTR112, boolean56
'--------------------------------------------------
' Parameter 1 : (String) "FORCE_Large"
' Parameter 2 : (String) "Default value"
' Parameter 3 : (String) "Unlocked"
' Parameter 4 : (Boolean) False
'--------------------------------------------------

long57 = settingRepository1.GetAttr("FORCE_ExtraLarge")
'--------------------------------------------------
' Parameter 1 : (String) "FORCE_ExtraLarge"
' Returned value : (Variant) (Long) 1
'--------------------------------------------------

Dim bSTR113
bSTR113 = ""
Dim bSTR114
bSTR114 = ""
Dim boolean57
settingRepository1.GetAttrInfo "FORCE_ExtraLarge", bSTR113, bSTR114, boolean57
'--------------------------------------------------
' Parameter 1 : (String) "FORCE_ExtraLarge"
' Parameter 2 : (String) "Default value"
' Parameter 3 : (String) "Unlocked"
' Parameter 4 : (Boolean) False
'--------------------------------------------------

long58 = settingRepository1.GetAttr("FORCE_Small")
'--------------------------------------------------
' Parameter 1 : (String) "FORCE_Small"
' Returned value : (Variant) (Long) 1
'--------------------------------------------------

Dim bSTR115
bSTR115 = ""
Dim bSTR116
bSTR116 = ""
Dim boolean58
settingRepository1.GetAttrInfo "FORCE_Small", bSTR115, bSTR116, boolean58
'--------------------------------------------------
' Parameter 1 : (String) "FORCE_Small"
' Parameter 2 : (String) "Default value"
' Parameter 3 : (String) "Unlocked"
' Parameter 4 : (Boolean) False
'--------------------------------------------------

long59 = settingRepository1.GetAttr("FORCE_ExtraSmall")
'--------------------------------------------------
' Parameter 1 : (String) "FORCE_ExtraSmall"
' Returned value : (Variant) (Long) 1
'--------------------------------------------------

Dim bSTR117
bSTR117 = ""
Dim bSTR118
bSTR118 = ""
Dim boolean59
settingRepository1.GetAttrInfo "FORCE_ExtraSmall", bSTR117, bSTR118, boolean59
'--------------------------------------------------
' Parameter 1 : (String) "FORCE_ExtraSmall"
' Parameter 2 : (String) "Default value"
' Parameter 3 : (String) "Unlocked"
' Parameter 4 : (Boolean) False
'--------------------------------------------------

long60 = settingRepository1.GetAttr("FORCE_Nanometric")
'--------------------------------------------------
' Parameter 1 : (String) "FORCE_Nanometric"
' Returned value : (Variant) (Long) 1
'--------------------------------------------------

Dim bSTR119
bSTR119 = ""
Dim bSTR120
bSTR120 = ""
Dim boolean60
settingRepository1.GetAttrInfo "FORCE_Nanometric", bSTR119, bSTR120, boolean60
'--------------------------------------------------
' Parameter 1 : (String) "FORCE_Nanometric"
' Parameter 2 : (String) "Default value"
' Parameter 3 : (String) "Unlocked"
' Parameter 4 : (Boolean) False
'--------------------------------------------------

long61 = settingRepository1.GetAttr("INERTIA")
'--------------------------------------------------
' Parameter 1 : (String) "INERTIA"
' Returned value : (Variant) (Long) 1
'--------------------------------------------------

Dim bSTR121
bSTR121 = ""
Dim bSTR122
bSTR122 = ""
Dim boolean61
settingRepository1.GetAttrInfo "INERTIA", bSTR121, bSTR122, boolean61
'--------------------------------------------------
' Parameter 1 : (String) "INERTIA"
' Parameter 2 : (String) "Default value"
' Parameter 3 : (String) "Unlocked"
' Parameter 4 : (Boolean) False
'--------------------------------------------------

long62 = settingRepository1.GetAttr("INERTIA_Large")
'--------------------------------------------------
' Parameter 1 : (String) "INERTIA_Large"
' Returned value : (Variant) (Long) 1
'--------------------------------------------------

Dim bSTR123
bSTR123 = ""
Dim bSTR124
bSTR124 = ""
Dim boolean62
settingRepository1.GetAttrInfo "INERTIA_Large", bSTR123, bSTR124, boolean62
'--------------------------------------------------
' Parameter 1 : (String) "INERTIA_Large"
' Parameter 2 : (String) "Default value"
' Parameter 3 : (String) "Unlocked"
' Parameter 4 : (Boolean) False
'--------------------------------------------------

long63 = settingRepository1.GetAttr("INERTIA_ExtraLarge")
'--------------------------------------------------
' Parameter 1 : (String) "INERTIA_ExtraLarge"
' Returned value : (Variant) (Long) 1
'--------------------------------------------------

Dim bSTR125
bSTR125 = ""
Dim bSTR126
bSTR126 = ""
Dim boolean63
settingRepository1.GetAttrInfo "INERTIA_ExtraLarge", bSTR125, bSTR126, boolean63
'--------------------------------------------------
' Parameter 1 : (String) "INERTIA_ExtraLarge"
' Parameter 2 : (String) "Default value"
' Parameter 3 : (String) "Unlocked"
' Parameter 4 : (Boolean) False
'--------------------------------------------------

long64 = settingRepository1.GetAttr("INERTIA_Small")
'--------------------------------------------------
' Parameter 1 : (String) "INERTIA_Small"
' Returned value : (Variant) (Long) 1
'--------------------------------------------------

Dim bSTR127
bSTR127 = ""
Dim bSTR128
bSTR128 = ""
Dim boolean64
settingRepository1.GetAttrInfo "INERTIA_Small", bSTR127, bSTR128, boolean64
'--------------------------------------------------
' Parameter 1 : (String) "INERTIA_Small"
' Parameter 2 : (String) "Default value"
' Parameter 3 : (String) "Unlocked"
' Parameter 4 : (Boolean) False
'--------------------------------------------------

long65 = settingRepository1.GetAttr("INERTIA_ExtraSmall")
'--------------------------------------------------
' Parameter 1 : (String) "INERTIA_ExtraSmall"
' Returned value : (Variant) (Long) 1
'--------------------------------------------------

Dim bSTR129
bSTR129 = ""
Dim bSTR130
bSTR130 = ""
Dim boolean65
settingRepository1.GetAttrInfo "INERTIA_ExtraSmall", bSTR129, bSTR130, boolean65
'--------------------------------------------------
' Parameter 1 : (String) "INERTIA_ExtraSmall"
' Parameter 2 : (String) "Default value"
' Parameter 3 : (String) "Unlocked"
' Parameter 4 : (Boolean) False
'--------------------------------------------------

long66 = settingRepository1.GetAttr("INERTIA_Nanometric")
'--------------------------------------------------
' Parameter 1 : (String) "INERTIA_Nanometric"
' Returned value : (Variant) (Long) 1
'--------------------------------------------------

Dim bSTR131
bSTR131 = ""
Dim bSTR132
bSTR132 = ""
Dim boolean66
settingRepository1.GetAttrInfo "INERTIA_Nanometric", bSTR131, bSTR132, boolean66
'--------------------------------------------------
' Parameter 1 : (String) "INERTIA_Nanometric"
' Parameter 2 : (String) "Default value"
' Parameter 3 : (String) "Unlocked"
' Parameter 4 : (Boolean) False
'--------------------------------------------------

long67 = settingRepository1.GetAttr("MASSFLOW")
'--------------------------------------------------
' Parameter 1 : (String) "MASSFLOW"
' Returned value : (Variant) (Long) 1
'--------------------------------------------------

Dim bSTR133
bSTR133 = ""
Dim bSTR134
bSTR134 = ""
Dim boolean67
settingRepository1.GetAttrInfo "MASSFLOW", bSTR133, bSTR134, boolean67
'--------------------------------------------------
' Parameter 1 : (String) "MASSFLOW"
' Parameter 2 : (String) "Default value"
' Parameter 3 : (String) "Unlocked"
' Parameter 4 : (Boolean) False
'--------------------------------------------------

long68 = settingRepository1.GetAttr("MASSFLOW_Large")
'--------------------------------------------------
' Parameter 1 : (String) "MASSFLOW_Large"
' Returned value : (Variant) (Long) 1
'--------------------------------------------------

Dim bSTR135
bSTR135 = ""
Dim bSTR136
bSTR136 = ""
Dim boolean68
settingRepository1.GetAttrInfo "MASSFLOW_Large", bSTR135, bSTR136, boolean68
'--------------------------------------------------
' Parameter 1 : (String) "MASSFLOW_Large"
' Parameter 2 : (String) "Default value"
' Parameter 3 : (String) "Unlocked"
' Parameter 4 : (Boolean) False
'--------------------------------------------------

long69 = settingRepository1.GetAttr("MASSFLOW_ExtraLarge")
'--------------------------------------------------
' Parameter 1 : (String) "MASSFLOW_ExtraLarge"
' Returned value : (Variant) (Long) 1
'--------------------------------------------------

Dim bSTR137
bSTR137 = ""
Dim bSTR138
bSTR138 = ""
Dim boolean69
settingRepository1.GetAttrInfo "MASSFLOW_ExtraLarge", bSTR137, bSTR138, boolean69
'--------------------------------------------------
' Parameter 1 : (String) "MASSFLOW_ExtraLarge"
' Parameter 2 : (String) "Default value"
' Parameter 3 : (String) "Unlocked"
' Parameter 4 : (Boolean) False
'--------------------------------------------------

long70 = settingRepository1.GetAttr("MASSFLOW_Small")
'--------------------------------------------------
' Parameter 1 : (String) "MASSFLOW_Small"
' Returned value : (Variant) (Long) 1
'--------------------------------------------------

Dim bSTR139
bSTR139 = ""
Dim bSTR140
bSTR140 = ""
Dim boolean70
settingRepository1.GetAttrInfo "MASSFLOW_Small", bSTR139, bSTR140, boolean70
'--------------------------------------------------
' Parameter 1 : (String) "MASSFLOW_Small"
' Parameter 2 : (String) "Default value"
' Parameter 3 : (String) "Unlocked"
' Parameter 4 : (Boolean) False
'--------------------------------------------------

long71 = settingRepository1.GetAttr("MASSFLOW_ExtraSmall")
'--------------------------------------------------
' Parameter 1 : (String) "MASSFLOW_ExtraSmall"
' Returned value : (Variant) (Long) 1
'--------------------------------------------------

Dim bSTR141
bSTR141 = ""
Dim bSTR142
bSTR142 = ""
Dim boolean71
settingRepository1.GetAttrInfo "MASSFLOW_ExtraSmall", bSTR141, bSTR142, boolean71
'--------------------------------------------------
' Parameter 1 : (String) "MASSFLOW_ExtraSmall"
' Parameter 2 : (String) "Default value"
' Parameter 3 : (String) "Unlocked"
' Parameter 4 : (Boolean) False
'--------------------------------------------------

long72 = settingRepository1.GetAttr("MASSFLOW_Nanometric")
'--------------------------------------------------
' Parameter 1 : (String) "MASSFLOW_Nanometric"
' Returned value : (Variant) (Long) 1
'--------------------------------------------------

Dim bSTR143
bSTR143 = ""
Dim bSTR144
bSTR144 = ""
Dim boolean72
settingRepository1.GetAttrInfo "MASSFLOW_Nanometric", bSTR143, bSTR144, boolean72
'--------------------------------------------------
' Parameter 1 : (String) "MASSFLOW_Nanometric"
' Parameter 2 : (String) "Default value"
' Parameter 3 : (String) "Unlocked"
' Parameter 4 : (Boolean) False
'--------------------------------------------------

long73 = settingRepository1.GetAttr("MOMENT")
'--------------------------------------------------
' Parameter 1 : (String) "MOMENT"
' Returned value : (Variant) (Long) 1
'--------------------------------------------------

Dim bSTR145
bSTR145 = ""
Dim bSTR146
bSTR146 = ""
Dim boolean73
settingRepository1.GetAttrInfo "MOMENT", bSTR145, bSTR146, boolean73
'--------------------------------------------------
' Parameter 1 : (String) "MOMENT"
' Parameter 2 : (String) "Default value"
' Parameter 3 : (String) "Unlocked"
' Parameter 4 : (Boolean) False
'--------------------------------------------------

long74 = settingRepository1.GetAttr("MOMENT_Large")
'--------------------------------------------------
' Parameter 1 : (String) "MOMENT_Large"
' Returned value : (Variant) (Long) 1
'--------------------------------------------------

Dim bSTR147
bSTR147 = ""
Dim bSTR148
bSTR148 = ""
Dim boolean74
settingRepository1.GetAttrInfo "MOMENT_Large", bSTR147, bSTR148, boolean74
'--------------------------------------------------
' Parameter 1 : (String) "MOMENT_Large"
' Parameter 2 : (String) "Default value"
' Parameter 3 : (String) "Unlocked"
' Parameter 4 : (Boolean) False
'--------------------------------------------------

long75 = settingRepository1.GetAttr("MOMENT_ExtraLarge")
'--------------------------------------------------
' Parameter 1 : (String) "MOMENT_ExtraLarge"
' Returned value : (Variant) (Long) 1
'--------------------------------------------------

Dim bSTR149
bSTR149 = ""
Dim bSTR150
bSTR150 = ""
Dim boolean75
settingRepository1.GetAttrInfo "MOMENT_ExtraLarge", bSTR149, bSTR150, boolean75
'--------------------------------------------------
' Parameter 1 : (String) "MOMENT_ExtraLarge"
' Parameter 2 : (String) "Default value"
' Parameter 3 : (String) "Unlocked"
' Parameter 4 : (Boolean) False
'--------------------------------------------------

long76 = settingRepository1.GetAttr("MOMENT_Small")
'--------------------------------------------------
' Parameter 1 : (String) "MOMENT_Small"
' Returned value : (Variant) (Long) 1
'--------------------------------------------------

Dim bSTR151
bSTR151 = ""
Dim bSTR152
bSTR152 = ""
Dim boolean76
settingRepository1.GetAttrInfo "MOMENT_Small", bSTR151, bSTR152, boolean76
'--------------------------------------------------
' Parameter 1 : (String) "MOMENT_Small"
' Parameter 2 : (String) "Default value"
' Parameter 3 : (String) "Unlocked"
' Parameter 4 : (Boolean) False
'--------------------------------------------------

long77 = settingRepository1.GetAttr("MOMENT_ExtraSmall")
'--------------------------------------------------
' Parameter 1 : (String) "MOMENT_ExtraSmall"
' Returned value : (Variant) (Long) 1
'--------------------------------------------------

Dim bSTR153
bSTR153 = ""
Dim bSTR154
bSTR154 = ""
Dim boolean77
settingRepository1.GetAttrInfo "MOMENT_ExtraSmall", bSTR153, bSTR154, boolean77
'--------------------------------------------------
' Parameter 1 : (String) "MOMENT_ExtraSmall"
' Parameter 2 : (String) "Default value"
' Parameter 3 : (String) "Unlocked"
' Parameter 4 : (Boolean) False
'--------------------------------------------------

long78 = settingRepository1.GetAttr("MOMENT_Nanometric")
'--------------------------------------------------
' Parameter 1 : (String) "MOMENT_Nanometric"
' Returned value : (Variant) (Long) 1
'--------------------------------------------------

Dim bSTR155
bSTR155 = ""
Dim bSTR156
bSTR156 = ""
Dim boolean78
settingRepository1.GetAttrInfo "MOMENT_Nanometric", bSTR155, bSTR156, boolean78
'--------------------------------------------------
' Parameter 1 : (String) "MOMENT_Nanometric"
' Parameter 2 : (String) "Default value"
' Parameter 3 : (String) "Unlocked"
' Parameter 4 : (Boolean) False
'--------------------------------------------------

long79 = settingRepository1.GetAttr("PRESSURE")
'--------------------------------------------------
' Parameter 1 : (String) "PRESSURE"
' Returned value : (Variant) (Long) 1
'--------------------------------------------------

Dim bSTR157
bSTR157 = ""
Dim bSTR158
bSTR158 = ""
Dim boolean79
settingRepository1.GetAttrInfo "PRESSURE", bSTR157, bSTR158, boolean79
'--------------------------------------------------
' Parameter 1 : (String) "PRESSURE"
' Parameter 2 : (String) "Default value"
' Parameter 3 : (String) "Unlocked"
' Parameter 4 : (Boolean) False
'--------------------------------------------------

long80 = settingRepository1.GetAttr("PRESSURE_Large")
'--------------------------------------------------
' Parameter 1 : (String) "PRESSURE_Large"
' Returned value : (Variant) (Long) 1
'--------------------------------------------------

Dim bSTR159
bSTR159 = ""
Dim bSTR160
bSTR160 = ""
Dim boolean80
settingRepository1.GetAttrInfo "PRESSURE_Large", bSTR159, bSTR160, boolean80
'--------------------------------------------------
' Parameter 1 : (String) "PRESSURE_Large"
' Parameter 2 : (String) "Default value"
' Parameter 3 : (String) "Unlocked"
' Parameter 4 : (Boolean) False
'--------------------------------------------------

long81 = settingRepository1.GetAttr("PRESSURE_ExtraLarge")
'--------------------------------------------------
' Parameter 1 : (String) "PRESSURE_ExtraLarge"
' Returned value : (Variant) (Long) 1
'--------------------------------------------------

Dim bSTR161
bSTR161 = ""
Dim bSTR162
bSTR162 = ""
Dim boolean81
settingRepository1.GetAttrInfo "PRESSURE_ExtraLarge", bSTR161, bSTR162, boolean81
'--------------------------------------------------
' Parameter 1 : (String) "PRESSURE_ExtraLarge"
' Parameter 2 : (String) "Default value"
' Parameter 3 : (String) "Unlocked"
' Parameter 4 : (Boolean) False
'--------------------------------------------------

long82 = settingRepository1.GetAttr("PRESSURE_Small")
'--------------------------------------------------
' Parameter 1 : (String) "PRESSURE_Small"
' Returned value : (Variant) (Long) 1
'--------------------------------------------------

Dim bSTR163
bSTR163 = ""
Dim bSTR164
bSTR164 = ""
Dim boolean82
settingRepository1.GetAttrInfo "PRESSURE_Small", bSTR163, bSTR164, boolean82
'--------------------------------------------------
' Parameter 1 : (String) "PRESSURE_Small"
' Parameter 2 : (String) "Default value"
' Parameter 3 : (String) "Unlocked"
' Parameter 4 : (Boolean) False
'--------------------------------------------------

long83 = settingRepository1.GetAttr("PRESSURE_ExtraSmall")
'--------------------------------------------------
' Parameter 1 : (String) "PRESSURE_ExtraSmall"
' Returned value : (Variant) (Long) 1
'--------------------------------------------------

Dim bSTR165
bSTR165 = ""
Dim bSTR166
bSTR166 = ""
Dim boolean83
settingRepository1.GetAttrInfo "PRESSURE_ExtraSmall", bSTR165, bSTR166, boolean83
'--------------------------------------------------
' Parameter 1 : (String) "PRESSURE_ExtraSmall"
' Parameter 2 : (String) "Default value"
' Parameter 3 : (String) "Unlocked"
' Parameter 4 : (Boolean) False
'--------------------------------------------------

long84 = settingRepository1.GetAttr("PRESSURE_Nanometric")
'--------------------------------------------------
' Parameter 1 : (String) "PRESSURE_Nanometric"
' Returned value : (Variant) (Long) 1
'--------------------------------------------------

Dim bSTR167
bSTR167 = ""
Dim bSTR168
bSTR168 = ""
Dim boolean84
settingRepository1.GetAttrInfo "PRESSURE_Nanometric", bSTR167, bSTR168, boolean84
'--------------------------------------------------
' Parameter 1 : (String) "PRESSURE_Nanometric"
' Parameter 2 : (String) "Default value"
' Parameter 3 : (String) "Unlocked"
' Parameter 4 : (Boolean) False
'--------------------------------------------------

long85 = settingRepository1.GetAttr("RSTIFNES")
'--------------------------------------------------
' Parameter 1 : (String) "RSTIFNES"
' Returned value : (Variant) (Long) 1
'--------------------------------------------------

Dim bSTR169
bSTR169 = ""
Dim bSTR170
bSTR170 = ""
Dim boolean85
settingRepository1.GetAttrInfo "RSTIFNES", bSTR169, bSTR170, boolean85
'--------------------------------------------------
' Parameter 1 : (String) "RSTIFNES"
' Parameter 2 : (String) "Default value"
' Parameter 3 : (String) "Unlocked"
' Parameter 4 : (Boolean) False
'--------------------------------------------------

long86 = settingRepository1.GetAttr("RSTIFNES_Large")
'--------------------------------------------------
' Parameter 1 : (String) "RSTIFNES_Large"
' Returned value : (Variant) (Long) 1
'--------------------------------------------------

Dim bSTR171
bSTR171 = ""
Dim bSTR172
bSTR172 = ""
Dim boolean86
settingRepository1.GetAttrInfo "RSTIFNES_Large", bSTR171, bSTR172, boolean86
'--------------------------------------------------
' Parameter 1 : (String) "RSTIFNES_Large"
' Parameter 2 : (String) "Default value"
' Parameter 3 : (String) "Unlocked"
' Parameter 4 : (Boolean) False
'--------------------------------------------------

long87 = settingRepository1.GetAttr("RSTIFNES_ExtraLarge")
'--------------------------------------------------
' Parameter 1 : (String) "RSTIFNES_ExtraLarge"
' Returned value : (Variant) (Long) 1
'--------------------------------------------------

Dim bSTR173
bSTR173 = ""
Dim bSTR174
bSTR174 = ""
Dim boolean87
settingRepository1.GetAttrInfo "RSTIFNES_ExtraLarge", bSTR173, bSTR174, boolean87
'--------------------------------------------------
' Parameter 1 : (String) "RSTIFNES_ExtraLarge"
' Parameter 2 : (String) "Default value"
' Parameter 3 : (String) "Unlocked"
' Parameter 4 : (Boolean) False
'--------------------------------------------------

long88 = settingRepository1.GetAttr("RSTIFNES_Small")
'--------------------------------------------------
' Parameter 1 : (String) "RSTIFNES_Small"
' Returned value : (Variant) (Long) 1
'--------------------------------------------------

Dim bSTR175
bSTR175 = ""
Dim bSTR176
bSTR176 = ""
Dim boolean88
settingRepository1.GetAttrInfo "RSTIFNES_Small", bSTR175, bSTR176, boolean88
'--------------------------------------------------
' Parameter 1 : (String) "RSTIFNES_Small"
' Parameter 2 : (String) "Default value"
' Parameter 3 : (String) "Unlocked"
' Parameter 4 : (Boolean) False
'--------------------------------------------------

long89 = settingRepository1.GetAttr("RSTIFNES_ExtraSmall")
'--------------------------------------------------
' Parameter 1 : (String) "RSTIFNES_ExtraSmall"
' Returned value : (Variant) (Long) 1
'--------------------------------------------------

Dim bSTR177
bSTR177 = ""
Dim bSTR178
bSTR178 = ""
Dim boolean89
settingRepository1.GetAttrInfo "RSTIFNES_ExtraSmall", bSTR177, bSTR178, boolean89
'--------------------------------------------------
' Parameter 1 : (String) "RSTIFNES_ExtraSmall"
' Parameter 2 : (String) "Default value"
' Parameter 3 : (String) "Unlocked"
' Parameter 4 : (Boolean) False
'--------------------------------------------------

long90 = settingRepository1.GetAttr("RSTIFNES_Nanometric")
'--------------------------------------------------
' Parameter 1 : (String) "RSTIFNES_Nanometric"
' Returned value : (Variant) (Long) 1
'--------------------------------------------------

Dim bSTR179
bSTR179 = ""
Dim bSTR180
bSTR180 = ""
Dim boolean90
settingRepository1.GetAttrInfo "RSTIFNES_Nanometric", bSTR179, bSTR180, boolean90
'--------------------------------------------------
' Parameter 1 : (String) "RSTIFNES_Nanometric"
' Parameter 2 : (String) "Default value"
' Parameter 3 : (String) "Unlocked"
' Parameter 4 : (Boolean) False
'--------------------------------------------------

long91 = settingRepository1.GetAttr("TEMPRTRE")
'--------------------------------------------------
' Parameter 1 : (String) "TEMPRTRE"
' Returned value : (Variant) (Long) 1
'--------------------------------------------------

Dim bSTR181
bSTR181 = ""
Dim bSTR182
bSTR182 = ""
Dim boolean91
settingRepository1.GetAttrInfo "TEMPRTRE", bSTR181, bSTR182, boolean91
'--------------------------------------------------
' Parameter 1 : (String) "TEMPRTRE"
' Parameter 2 : (String) "Default value"
' Parameter 3 : (String) "Unlocked"
' Parameter 4 : (Boolean) False
'--------------------------------------------------

long92 = settingRepository1.GetAttr("TEMPRTRE_Large")
'--------------------------------------------------
' Parameter 1 : (String) "TEMPRTRE_Large"
' Returned value : (Variant) (Long) 1
'--------------------------------------------------

Dim bSTR183
bSTR183 = ""
Dim bSTR184
bSTR184 = ""
Dim boolean92
settingRepository1.GetAttrInfo "TEMPRTRE_Large", bSTR183, bSTR184, boolean92
'--------------------------------------------------
' Parameter 1 : (String) "TEMPRTRE_Large"
' Parameter 2 : (String) "Default value"
' Parameter 3 : (String) "Unlocked"
' Parameter 4 : (Boolean) False
'--------------------------------------------------

long93 = settingRepository1.GetAttr("TEMPRTRE_ExtraLarge")
'--------------------------------------------------
' Parameter 1 : (String) "TEMPRTRE_ExtraLarge"
' Returned value : (Variant) (Long) 1
'--------------------------------------------------

Dim bSTR185
bSTR185 = ""
Dim bSTR186
bSTR186 = ""
Dim boolean93
settingRepository1.GetAttrInfo "TEMPRTRE_ExtraLarge", bSTR185, bSTR186, boolean93
'--------------------------------------------------
' Parameter 1 : (String) "TEMPRTRE_ExtraLarge"
' Parameter 2 : (String) "Default value"
' Parameter 3 : (String) "Unlocked"
' Parameter 4 : (Boolean) False
'--------------------------------------------------

long94 = settingRepository1.GetAttr("TEMPRTRE_Small")
'--------------------------------------------------
' Parameter 1 : (String) "TEMPRTRE_Small"
' Returned value : (Variant) (Long) 1
'--------------------------------------------------

Dim bSTR187
bSTR187 = ""
Dim bSTR188
bSTR188 = ""
Dim boolean94
settingRepository1.GetAttrInfo "TEMPRTRE_Small", bSTR187, bSTR188, boolean94
'--------------------------------------------------
' Parameter 1 : (String) "TEMPRTRE_Small"
' Parameter 2 : (String) "Default value"
' Parameter 3 : (String) "Unlocked"
' Parameter 4 : (Boolean) False
'--------------------------------------------------

long95 = settingRepository1.GetAttr("TEMPRTRE_ExtraSmall")
'--------------------------------------------------
' Parameter 1 : (String) "TEMPRTRE_ExtraSmall"
' Returned value : (Variant) (Long) 1
'--------------------------------------------------

Dim bSTR189
bSTR189 = ""
Dim bSTR190
bSTR190 = ""
Dim boolean95
settingRepository1.GetAttrInfo "TEMPRTRE_ExtraSmall", bSTR189, bSTR190, boolean95
'--------------------------------------------------
' Parameter 1 : (String) "TEMPRTRE_ExtraSmall"
' Parameter 2 : (String) "Default value"
' Parameter 3 : (String) "Unlocked"
' Parameter 4 : (Boolean) False
'--------------------------------------------------

long96 = settingRepository1.GetAttr("TEMPRTRE_Nanometric")
'--------------------------------------------------
' Parameter 1 : (String) "TEMPRTRE_Nanometric"
' Returned value : (Variant) (Long) 1
'--------------------------------------------------

Dim bSTR191
bSTR191 = ""
Dim bSTR192
bSTR192 = ""
Dim boolean96
settingRepository1.GetAttrInfo "TEMPRTRE_Nanometric", bSTR191, bSTR192, boolean96
'--------------------------------------------------
' Parameter 1 : (String) "TEMPRTRE_Nanometric"
' Parameter 2 : (String) "Default value"
' Parameter 3 : (String) "Unlocked"
' Parameter 4 : (Boolean) False
'--------------------------------------------------

long97 = settingRepository1.GetAttr("LINEMASS")
'--------------------------------------------------
' Parameter 1 : (String) "LINEMASS"
' Returned value : (Variant) (Long) 1
'--------------------------------------------------

Dim bSTR193
bSTR193 = ""
Dim bSTR194
bSTR194 = ""
Dim boolean97
settingRepository1.GetAttrInfo "LINEMASS", bSTR193, bSTR194, boolean97
'--------------------------------------------------
' Parameter 1 : (String) "LINEMASS"
' Parameter 2 : (String) "Default value"
' Parameter 3 : (String) "Unlocked"
' Parameter 4 : (Boolean) False
'--------------------------------------------------

long98 = settingRepository1.GetAttr("LINEMASS_Large")
'--------------------------------------------------
' Parameter 1 : (String) "LINEMASS_Large"
' Returned value : (Variant) (Long) 1
'--------------------------------------------------

Dim bSTR195
bSTR195 = ""
Dim bSTR196
bSTR196 = ""
Dim boolean98
settingRepository1.GetAttrInfo "LINEMASS_Large", bSTR195, bSTR196, boolean98
'--------------------------------------------------
' Parameter 1 : (String) "LINEMASS_Large"
' Parameter 2 : (String) "Default value"
' Parameter 3 : (String) "Unlocked"
' Parameter 4 : (Boolean) False
'--------------------------------------------------

long99 = settingRepository1.GetAttr("LINEMASS_ExtraLarge")
'--------------------------------------------------
' Parameter 1 : (String) "LINEMASS_ExtraLarge"
' Returned value : (Variant) (Long) 1
'--------------------------------------------------

Dim bSTR197
bSTR197 = ""
Dim bSTR198
bSTR198 = ""
Dim boolean99
settingRepository1.GetAttrInfo "LINEMASS_ExtraLarge", bSTR197, bSTR198, boolean99
'--------------------------------------------------
' Parameter 1 : (String) "LINEMASS_ExtraLarge"
' Parameter 2 : (String) "Default value"
' Parameter 3 : (String) "Unlocked"
' Parameter 4 : (Boolean) False
'--------------------------------------------------

long100 = settingRepository1.GetAttr("LINEMASS_Small")
'--------------------------------------------------
' Parameter 1 : (String) "LINEMASS_Small"
' Returned value : (Variant) (Long) 1
'--------------------------------------------------

Dim bSTR199
bSTR199 = ""
Dim bSTR200
bSTR200 = ""
Dim boolean100
settingRepository1.GetAttrInfo "LINEMASS_Small", bSTR199, bSTR200, boolean100
'--------------------------------------------------
' Parameter 1 : (String) "LINEMASS_Small"
' Parameter 2 : (String) "Default value"
' Parameter 3 : (String) "Unlocked"
' Parameter 4 : (Boolean) False
'--------------------------------------------------

long101 = settingRepository1.GetAttr("LINEMASS_ExtraSmall")
'--------------------------------------------------
' Parameter 1 : (String) "LINEMASS_ExtraSmall"
' Returned value : (Variant) (Long) 1
'--------------------------------------------------

Dim bSTR201
bSTR201 = ""
Dim bSTR202
bSTR202 = ""
Dim boolean101
settingRepository1.GetAttrInfo "LINEMASS_ExtraSmall", bSTR201, bSTR202, boolean101
'--------------------------------------------------
' Parameter 1 : (String) "LINEMASS_ExtraSmall"
' Parameter 2 : (String) "Default value"
' Parameter 3 : (String) "Unlocked"
' Parameter 4 : (Boolean) False
'--------------------------------------------------

long102 = settingRepository1.GetAttr("LINEMASS_Nanometric")
'--------------------------------------------------
' Parameter 1 : (String) "LINEMASS_Nanometric"
' Returned value : (Variant) (Long) 1
'--------------------------------------------------

Dim bSTR203
bSTR203 = ""
Dim bSTR204
bSTR204 = ""
Dim boolean102
settingRepository1.GetAttrInfo "LINEMASS_Nanometric", bSTR203, bSTR204, boolean102
'--------------------------------------------------
' Parameter 1 : (String) "LINEMASS_Nanometric"
' Parameter 2 : (String) "Default value"
' Parameter 3 : (String) "Unlocked"
' Parameter 4 : (Boolean) False
'--------------------------------------------------

long103 = settingRepository1.GetAttr("TSTIFNES")
'--------------------------------------------------
' Parameter 1 : (String) "TSTIFNES"
' Returned value : (Variant) (Long) 1
'--------------------------------------------------

Dim bSTR205
bSTR205 = ""
Dim bSTR206
bSTR206 = ""
Dim boolean103
settingRepository1.GetAttrInfo "TSTIFNES", bSTR205, bSTR206, boolean103
'--------------------------------------------------
' Parameter 1 : (String) "TSTIFNES"
' Parameter 2 : (String) "Default value"
' Parameter 3 : (String) "Unlocked"
' Parameter 4 : (Boolean) False
'--------------------------------------------------

long104 = settingRepository1.GetAttr("TSTIFNES_Large")
'--------------------------------------------------
' Parameter 1 : (String) "TSTIFNES_Large"
' Returned value : (Variant) (Long) 1
'--------------------------------------------------

Dim bSTR207
bSTR207 = ""
Dim bSTR208
bSTR208 = ""
Dim boolean104
settingRepository1.GetAttrInfo "TSTIFNES_Large", bSTR207, bSTR208, boolean104
'--------------------------------------------------
' Parameter 1 : (String) "TSTIFNES_Large"
' Parameter 2 : (String) "Default value"
' Parameter 3 : (String) "Unlocked"
' Parameter 4 : (Boolean) False
'--------------------------------------------------

long105 = settingRepository1.GetAttr("TSTIFNES_ExtraLarge")
'--------------------------------------------------
' Parameter 1 : (String) "TSTIFNES_ExtraLarge"
' Returned value : (Variant) (Long) 1
'--------------------------------------------------

Dim bSTR209
bSTR209 = ""
Dim bSTR210
bSTR210 = ""
Dim boolean105
settingRepository1.GetAttrInfo "TSTIFNES_ExtraLarge", bSTR209, bSTR210, boolean105
'--------------------------------------------------
' Parameter 1 : (String) "TSTIFNES_ExtraLarge"
' Parameter 2 : (String) "Default value"
' Parameter 3 : (String) "Unlocked"
' Parameter 4 : (Boolean) False
'--------------------------------------------------

long106 = settingRepository1.GetAttr("TSTIFNES_Small")
'--------------------------------------------------
' Parameter 1 : (String) "TSTIFNES_Small"
' Returned value : (Variant) (Long) 1
'--------------------------------------------------

Dim bSTR211
bSTR211 = ""
Dim bSTR212
bSTR212 = ""
Dim boolean106
settingRepository1.GetAttrInfo "TSTIFNES_Small", bSTR211, bSTR212, boolean106
'--------------------------------------------------
' Parameter 1 : (String) "TSTIFNES_Small"
' Parameter 2 : (String) "Default value"
' Parameter 3 : (String) "Unlocked"
' Parameter 4 : (Boolean) False
'--------------------------------------------------

long107 = settingRepository1.GetAttr("TSTIFNES_ExtraSmall")
'--------------------------------------------------
' Parameter 1 : (String) "TSTIFNES_ExtraSmall"
' Returned value : (Variant) (Long) 1
'--------------------------------------------------

Dim bSTR213
bSTR213 = ""
Dim bSTR214
bSTR214 = ""
Dim boolean107
settingRepository1.GetAttrInfo "TSTIFNES_ExtraSmall", bSTR213, bSTR214, boolean107
'--------------------------------------------------
' Parameter 1 : (String) "TSTIFNES_ExtraSmall"
' Parameter 2 : (String) "Default value"
' Parameter 3 : (String) "Unlocked"
' Parameter 4 : (Boolean) False
'--------------------------------------------------

long108 = settingRepository1.GetAttr("TSTIFNES_Nanometric")
'--------------------------------------------------
' Parameter 1 : (String) "TSTIFNES_Nanometric"
' Returned value : (Variant) (Long) 1
'--------------------------------------------------

Dim bSTR215
bSTR215 = ""
Dim bSTR216
bSTR216 = ""
Dim boolean108
settingRepository1.GetAttrInfo "TSTIFNES_Nanometric", bSTR215, bSTR216, boolean108
'--------------------------------------------------
' Parameter 1 : (String) "TSTIFNES_Nanometric"
' Parameter 2 : (String) "Default value"
' Parameter 3 : (String) "Unlocked"
' Parameter 4 : (Boolean) False
'--------------------------------------------------

long109 = settingRepository1.GetAttr("VOL_FLOW")
'--------------------------------------------------
' Parameter 1 : (String) "VOL_FLOW"
' Returned value : (Variant) (Long) 1
'--------------------------------------------------

Dim bSTR217
bSTR217 = ""
Dim bSTR218
bSTR218 = ""
Dim boolean109
settingRepository1.GetAttrInfo "VOL_FLOW", bSTR217, bSTR218, boolean109
'--------------------------------------------------
' Parameter 1 : (String) "VOL_FLOW"
' Parameter 2 : (String) "Default value"
' Parameter 3 : (String) "Unlocked"
' Parameter 4 : (Boolean) False
'--------------------------------------------------

long110 = settingRepository1.GetAttr("VOL_FLOW_Large")
'--------------------------------------------------
' Parameter 1 : (String) "VOL_FLOW_Large"
' Returned value : (Variant) (Long) 1
'--------------------------------------------------

Dim bSTR219
bSTR219 = ""
Dim bSTR220
bSTR220 = ""
Dim boolean110
settingRepository1.GetAttrInfo "VOL_FLOW_Large", bSTR219, bSTR220, boolean110
'--------------------------------------------------
' Parameter 1 : (String) "VOL_FLOW_Large"
' Parameter 2 : (String) "Default value"
' Parameter 3 : (String) "Unlocked"
' Parameter 4 : (Boolean) False
'--------------------------------------------------

long111 = settingRepository1.GetAttr("VOL_FLOW_ExtraLarge")
'--------------------------------------------------
' Parameter 1 : (String) "VOL_FLOW_ExtraLarge"
' Returned value : (Variant) (Long) 1
'--------------------------------------------------

Dim bSTR221
bSTR221 = ""
Dim bSTR222
bSTR222 = ""
Dim boolean111
settingRepository1.GetAttrInfo "VOL_FLOW_ExtraLarge", bSTR221, bSTR222, boolean111
'--------------------------------------------------
' Parameter 1 : (String) "VOL_FLOW_ExtraLarge"
' Parameter 2 : (String) "Default value"
' Parameter 3 : (String) "Unlocked"
' Parameter 4 : (Boolean) False
'--------------------------------------------------

long112 = settingRepository1.GetAttr("VOL_FLOW_Small")
'--------------------------------------------------
' Parameter 1 : (String) "VOL_FLOW_Small"
' Returned value : (Variant) (Long) 1
'--------------------------------------------------

Dim bSTR223
bSTR223 = ""
Dim bSTR224
bSTR224 = ""
Dim boolean112
settingRepository1.GetAttrInfo "VOL_FLOW_Small", bSTR223, bSTR224, boolean112
'--------------------------------------------------
' Parameter 1 : (String) "VOL_FLOW_Small"
' Parameter 2 : (String) "Default value"
' Parameter 3 : (String) "Unlocked"
' Parameter 4 : (Boolean) False
'--------------------------------------------------

long113 = settingRepository1.GetAttr("VOL_FLOW_ExtraSmall")
'--------------------------------------------------
' Parameter 1 : (String) "VOL_FLOW_ExtraSmall"
' Returned value : (Variant) (Long) 1
'--------------------------------------------------

Dim bSTR225
bSTR225 = ""
Dim bSTR226
bSTR226 = ""
Dim boolean113
settingRepository1.GetAttrInfo "VOL_FLOW_ExtraSmall", bSTR225, bSTR226, boolean113
'--------------------------------------------------
' Parameter 1 : (String) "VOL_FLOW_ExtraSmall"
' Parameter 2 : (String) "Default value"
' Parameter 3 : (String) "Unlocked"
' Parameter 4 : (Boolean) False
'--------------------------------------------------

long114 = settingRepository1.GetAttr("VOL_FLOW_Nanometric")
'--------------------------------------------------
' Parameter 1 : (String) "VOL_FLOW_Nanometric"
' Returned value : (Variant) (Long) 1
'--------------------------------------------------

Dim bSTR227
bSTR227 = ""
Dim bSTR228
bSTR228 = ""
Dim boolean114
settingRepository1.GetAttrInfo "VOL_FLOW_Nanometric", bSTR227, bSTR228, boolean114
'--------------------------------------------------
' Parameter 1 : (String) "VOL_FLOW_Nanometric"
' Parameter 2 : (String) "Default value"
' Parameter 3 : (String) "Unlocked"
' Parameter 4 : (Boolean) False
'--------------------------------------------------

long115 = settingRepository1.GetAttr("FREQUENCY")
'--------------------------------------------------
' Parameter 1 : (String) "FREQUENCY"
' Returned value : (Variant) (Long) 1
'--------------------------------------------------

Dim bSTR229
bSTR229 = ""
Dim bSTR230
bSTR230 = ""
Dim boolean115
settingRepository1.GetAttrInfo "FREQUENCY", bSTR229, bSTR230, boolean115
'--------------------------------------------------
' Parameter 1 : (String) "FREQUENCY"
' Parameter 2 : (String) "Default value"
' Parameter 3 : (String) "Unlocked"
' Parameter 4 : (Boolean) False
'--------------------------------------------------

long116 = settingRepository1.GetAttr("FREQUENCY_Large")
'--------------------------------------------------
' Parameter 1 : (String) "FREQUENCY_Large"
' Returned value : (Variant) (Long) 1
'--------------------------------------------------

Dim bSTR231
bSTR231 = ""
Dim bSTR232
bSTR232 = ""
Dim boolean116
settingRepository1.GetAttrInfo "FREQUENCY_Large", bSTR231, bSTR232, boolean116
'--------------------------------------------------
' Parameter 1 : (String) "FREQUENCY_Large"
' Parameter 2 : (String) "Default value"
' Parameter 3 : (String) "Unlocked"
' Parameter 4 : (Boolean) False
'--------------------------------------------------

long117 = settingRepository1.GetAttr("FREQUENCY_ExtraLarge")
'--------------------------------------------------
' Parameter 1 : (String) "FREQUENCY_ExtraLarge"
' Returned value : (Variant) (Long) 1
'--------------------------------------------------

Dim bSTR233
bSTR233 = ""
Dim bSTR234
bSTR234 = ""
Dim boolean117
settingRepository1.GetAttrInfo "FREQUENCY_ExtraLarge", bSTR233, bSTR234, boolean117
'--------------------------------------------------
' Parameter 1 : (String) "FREQUENCY_ExtraLarge"
' Parameter 2 : (String) "Default value"
' Parameter 3 : (String) "Unlocked"
' Parameter 4 : (Boolean) False
'--------------------------------------------------

long118 = settingRepository1.GetAttr("FREQUENCY_Small")
'--------------------------------------------------
' Parameter 1 : (String) "FREQUENCY_Small"
' Returned value : (Variant) (Long) 1
'--------------------------------------------------

Dim bSTR235
bSTR235 = ""
Dim bSTR236
bSTR236 = ""
Dim boolean118
settingRepository1.GetAttrInfo "FREQUENCY_Small", bSTR235, bSTR236, boolean118
'--------------------------------------------------
' Parameter 1 : (String) "FREQUENCY_Small"
' Parameter 2 : (String) "Default value"
' Parameter 3 : (String) "Unlocked"
' Parameter 4 : (Boolean) False
'--------------------------------------------------

long119 = settingRepository1.GetAttr("FREQUENCY_ExtraSmall")
'--------------------------------------------------
' Parameter 1 : (String) "FREQUENCY_ExtraSmall"
' Returned value : (Variant) (Long) 1
'--------------------------------------------------

Dim bSTR237
bSTR237 = ""
Dim bSTR238
bSTR238 = ""
Dim boolean119
settingRepository1.GetAttrInfo "FREQUENCY_ExtraSmall", bSTR237, bSTR238, boolean119
'--------------------------------------------------
' Parameter 1 : (String) "FREQUENCY_ExtraSmall"
' Parameter 2 : (String) "Default value"
' Parameter 3 : (String) "Unlocked"
' Parameter 4 : (Boolean) False
'--------------------------------------------------

long120 = settingRepository1.GetAttr("FREQUENCY_Nanometric")
'--------------------------------------------------
' Parameter 1 : (String) "FREQUENCY_Nanometric"
' Returned value : (Variant) (Long) 1
'--------------------------------------------------

Dim bSTR239
bSTR239 = ""
Dim bSTR240
bSTR240 = ""
Dim boolean120
settingRepository1.GetAttrInfo "FREQUENCY_Nanometric", bSTR239, bSTR240, boolean120
'--------------------------------------------------
' Parameter 1 : (String) "FREQUENCY_Nanometric"
' Parameter 2 : (String) "Default value"
' Parameter 3 : (String) "Unlocked"
' Parameter 4 : (Boolean) False
'--------------------------------------------------

long121 = settingRepository1.GetAttr("POWER")
'--------------------------------------------------
' Parameter 1 : (String) "POWER"
' Returned value : (Variant) (Long) 1
'--------------------------------------------------

Dim bSTR241
bSTR241 = ""
Dim bSTR242
bSTR242 = ""
Dim boolean121
settingRepository1.GetAttrInfo "POWER", bSTR241, bSTR242, boolean121
'--------------------------------------------------
' Parameter 1 : (String) "POWER"
' Parameter 2 : (String) "Default value"
' Parameter 3 : (String) "Unlocked"
' Parameter 4 : (Boolean) False
'--------------------------------------------------

long122 = settingRepository1.GetAttr("POWER_Large")
'--------------------------------------------------
' Parameter 1 : (String) "POWER_Large"
' Returned value : (Variant) (Long) 1
'--------------------------------------------------

Dim bSTR243
bSTR243 = ""
Dim bSTR244
bSTR244 = ""
Dim boolean122
settingRepository1.GetAttrInfo "POWER_Large", bSTR243, bSTR244, boolean122
'--------------------------------------------------
' Parameter 1 : (String) "POWER_Large"
' Parameter 2 : (String) "Default value"
' Parameter 3 : (String) "Unlocked"
' Parameter 4 : (Boolean) False
'--------------------------------------------------

long123 = settingRepository1.GetAttr("POWER_ExtraLarge")
'--------------------------------------------------
' Parameter 1 : (String) "POWER_ExtraLarge"
' Returned value : (Variant) (Long) 1
'--------------------------------------------------

Dim bSTR245
bSTR245 = ""
Dim bSTR246
bSTR246 = ""
Dim boolean123
settingRepository1.GetAttrInfo "POWER_ExtraLarge", bSTR245, bSTR246, boolean123
'--------------------------------------------------
' Parameter 1 : (String) "POWER_ExtraLarge"
' Parameter 2 : (String) "Default value"
' Parameter 3 : (String) "Unlocked"
' Parameter 4 : (Boolean) False
'--------------------------------------------------

long124 = settingRepository1.GetAttr("POWER_Small")
'--------------------------------------------------
' Parameter 1 : (String) "POWER_Small"
' Returned value : (Variant) (Long) 1
'--------------------------------------------------

Dim bSTR247
bSTR247 = ""
Dim bSTR248
bSTR248 = ""
Dim boolean124
settingRepository1.GetAttrInfo "POWER_Small", bSTR247, bSTR248, boolean124
'--------------------------------------------------
' Parameter 1 : (String) "POWER_Small"
' Parameter 2 : (String) "Default value"
' Parameter 3 : (String) "Unlocked"
' Parameter 4 : (Boolean) False
'--------------------------------------------------

long125 = settingRepository1.GetAttr("POWER_ExtraSmall")
'--------------------------------------------------
' Parameter 1 : (String) "POWER_ExtraSmall"
' Returned value : (Variant) (Long) 1
'--------------------------------------------------

Dim bSTR249
bSTR249 = ""
Dim bSTR250
bSTR250 = ""
Dim boolean125
settingRepository1.GetAttrInfo "POWER_ExtraSmall", bSTR249, bSTR250, boolean125
'--------------------------------------------------
' Parameter 1 : (String) "POWER_ExtraSmall"
' Parameter 2 : (String) "Default value"
' Parameter 3 : (String) "Unlocked"
' Parameter 4 : (Boolean) False
'--------------------------------------------------

long126 = settingRepository1.GetAttr("POWER_Nanometric")
'--------------------------------------------------
' Parameter 1 : (String) "POWER_Nanometric"
' Returned value : (Variant) (Long) 1
'--------------------------------------------------

Dim bSTR251
bSTR251 = ""
Dim bSTR252
bSTR252 = ""
Dim boolean126
settingRepository1.GetAttrInfo "POWER_Nanometric", bSTR251, bSTR252, boolean126
'--------------------------------------------------
' Parameter 1 : (String) "POWER_Nanometric"
' Parameter 2 : (String) "Default value"
' Parameter 3 : (String) "Unlocked"
' Parameter 4 : (Boolean) False
'--------------------------------------------------

long127 = settingRepository1.GetAttr("VOLTAGE")
'--------------------------------------------------
' Parameter 1 : (String) "VOLTAGE"
' Returned value : (Variant) (Long) 1
'--------------------------------------------------

Dim bSTR253
bSTR253 = ""
Dim bSTR254
bSTR254 = ""
Dim boolean127
settingRepository1.GetAttrInfo "VOLTAGE", bSTR253, bSTR254, boolean127
'--------------------------------------------------
' Parameter 1 : (String) "VOLTAGE"
' Parameter 2 : (String) "Default value"
' Parameter 3 : (String) "Unlocked"
' Parameter 4 : (Boolean) False
'--------------------------------------------------

long128 = settingRepository1.GetAttr("VOLTAGE_Large")
'--------------------------------------------------
' Parameter 1 : (String) "VOLTAGE_Large"
' Returned value : (Variant) (Long) 1
'--------------------------------------------------

Dim bSTR255
bSTR255 = ""
Dim bSTR256
bSTR256 = ""
Dim boolean128
settingRepository1.GetAttrInfo "VOLTAGE_Large", bSTR255, bSTR256, boolean128
'--------------------------------------------------
' Parameter 1 : (String) "VOLTAGE_Large"
' Parameter 2 : (String) "Default value"
' Parameter 3 : (String) "Unlocked"
' Parameter 4 : (Boolean) False
'--------------------------------------------------

long129 = settingRepository1.GetAttr("VOLTAGE_ExtraLarge")
'--------------------------------------------------
' Parameter 1 : (String) "VOLTAGE_ExtraLarge"
' Returned value : (Variant) (Long) 1
'--------------------------------------------------

Dim bSTR257
bSTR257 = ""
Dim bSTR258
bSTR258 = ""
Dim boolean129
settingRepository1.GetAttrInfo "VOLTAGE_ExtraLarge", bSTR257, bSTR258, boolean129
'--------------------------------------------------
' Parameter 1 : (String) "VOLTAGE_ExtraLarge"
' Parameter 2 : (String) "Default value"
' Parameter 3 : (String) "Unlocked"
' Parameter 4 : (Boolean) False
'--------------------------------------------------

long130 = settingRepository1.GetAttr("VOLTAGE_Small")
'--------------------------------------------------
' Parameter 1 : (String) "VOLTAGE_Small"
' Returned value : (Variant) (Long) 1
'--------------------------------------------------

Dim bSTR259
bSTR259 = ""
Dim bSTR260
bSTR260 = ""
Dim boolean130
settingRepository1.GetAttrInfo "VOLTAGE_Small", bSTR259, bSTR260, boolean130
'--------------------------------------------------
' Parameter 1 : (String) "VOLTAGE_Small"
' Parameter 2 : (String) "Default value"
' Parameter 3 : (String) "Unlocked"
' Parameter 4 : (Boolean) False
'--------------------------------------------------

long131 = settingRepository1.GetAttr("VOLTAGE_ExtraSmall")
'--------------------------------------------------
' Parameter 1 : (String) "VOLTAGE_ExtraSmall"
' Returned value : (Variant) (Long) 1
'--------------------------------------------------

Dim bSTR261
bSTR261 = ""
Dim bSTR262
bSTR262 = ""
Dim boolean131
settingRepository1.GetAttrInfo "VOLTAGE_ExtraSmall", bSTR261, bSTR262, boolean131
'--------------------------------------------------
' Parameter 1 : (String) "VOLTAGE_ExtraSmall"
' Parameter 2 : (String) "Default value"
' Parameter 3 : (String) "Unlocked"
' Parameter 4 : (Boolean) False
'--------------------------------------------------

long132 = settingRepository1.GetAttr("VOLTAGE_Nanometric")
'--------------------------------------------------
' Parameter 1 : (String) "VOLTAGE_Nanometric"
' Returned value : (Variant) (Long) 1
'--------------------------------------------------

Dim bSTR263
bSTR263 = ""
Dim bSTR264
bSTR264 = ""
Dim boolean132
settingRepository1.GetAttrInfo "VOLTAGE_Nanometric", bSTR263, bSTR264, boolean132
'--------------------------------------------------
' Parameter 1 : (String) "VOLTAGE_Nanometric"
' Parameter 2 : (String) "Default value"
' Parameter 3 : (String) "Unlocked"
' Parameter 4 : (Boolean) False
'--------------------------------------------------

long133 = settingRepository1.GetAttr("RESISTANCE")
'--------------------------------------------------
' Parameter 1 : (String) "RESISTANCE"
' Returned value : (Variant) (Long) 1
'--------------------------------------------------

Dim bSTR265
bSTR265 = ""
Dim bSTR266
bSTR266 = ""
Dim boolean133
settingRepository1.GetAttrInfo "RESISTANCE", bSTR265, bSTR266, boolean133
'--------------------------------------------------
' Parameter 1 : (String) "RESISTANCE"
' Parameter 2 : (String) "Default value"
' Parameter 3 : (String) "Unlocked"
' Parameter 4 : (Boolean) False
'--------------------------------------------------

long134 = settingRepository1.GetAttr("RESISTANCE_Large")
'--------------------------------------------------
' Parameter 1 : (String) "RESISTANCE_Large"
' Returned value : (Variant) (Long) 1
'--------------------------------------------------

Dim bSTR267
bSTR267 = ""
Dim bSTR268
bSTR268 = ""
Dim boolean134
settingRepository1.GetAttrInfo "RESISTANCE_Large", bSTR267, bSTR268, boolean134
'--------------------------------------------------
' Parameter 1 : (String) "RESISTANCE_Large"
' Parameter 2 : (String) "Default value"
' Parameter 3 : (String) "Unlocked"
' Parameter 4 : (Boolean) False
'--------------------------------------------------

long135 = settingRepository1.GetAttr("RESISTANCE_ExtraLarge")
'--------------------------------------------------
' Parameter 1 : (String) "RESISTANCE_ExtraLarge"
' Returned value : (Variant) (Long) 1
'--------------------------------------------------

Dim bSTR269
bSTR269 = ""
Dim bSTR270
bSTR270 = ""
Dim boolean135
settingRepository1.GetAttrInfo "RESISTANCE_ExtraLarge", bSTR269, bSTR270, boolean135
'--------------------------------------------------
' Parameter 1 : (String) "RESISTANCE_ExtraLarge"
' Parameter 2 : (String) "Default value"
' Parameter 3 : (String) "Unlocked"
' Parameter 4 : (Boolean) False
'--------------------------------------------------

long136 = settingRepository1.GetAttr("RESISTANCE_Small")
'--------------------------------------------------
' Parameter 1 : (String) "RESISTANCE_Small"
' Returned value : (Variant) (Long) 1
'--------------------------------------------------

Dim bSTR271
bSTR271 = ""
Dim bSTR272
bSTR272 = ""
Dim boolean136
settingRepository1.GetAttrInfo "RESISTANCE_Small", bSTR271, bSTR272, boolean136
'--------------------------------------------------
' Parameter 1 : (String) "RESISTANCE_Small"
' Parameter 2 : (String) "Default value"
' Parameter 3 : (String) "Unlocked"
' Parameter 4 : (Boolean) False
'--------------------------------------------------

long137 = settingRepository1.GetAttr("RESISTANCE_ExtraSmall")
'--------------------------------------------------
' Parameter 1 : (String) "RESISTANCE_ExtraSmall"
' Returned value : (Variant) (Long) 1
'--------------------------------------------------

Dim bSTR273
bSTR273 = ""
Dim bSTR274
bSTR274 = ""
Dim boolean137
settingRepository1.GetAttrInfo "RESISTANCE_ExtraSmall", bSTR273, bSTR274, boolean137
'--------------------------------------------------
' Parameter 1 : (String) "RESISTANCE_ExtraSmall"
' Parameter 2 : (String) "Default value"
' Parameter 3 : (String) "Unlocked"
' Parameter 4 : (Boolean) False
'--------------------------------------------------

long138 = settingRepository1.GetAttr("RESISTANCE_Nanometric")
'--------------------------------------------------
' Parameter 1 : (String) "RESISTANCE_Nanometric"
' Returned value : (Variant) (Long) 1
'--------------------------------------------------

Dim bSTR275
bSTR275 = ""
Dim bSTR276
bSTR276 = ""
Dim boolean138
settingRepository1.GetAttrInfo "RESISTANCE_Nanometric", bSTR275, bSTR276, boolean138
'--------------------------------------------------
' Parameter 1 : (String) "RESISTANCE_Nanometric"
' Parameter 2 : (String) "Default value"
' Parameter 3 : (String) "Unlocked"
' Parameter 4 : (Boolean) False
'--------------------------------------------------

long139 = settingRepository1.GetAttr("COURANT")
'--------------------------------------------------
' Parameter 1 : (String) "COURANT"
' Returned value : (Variant) (Long) 1
'--------------------------------------------------

Dim bSTR277
bSTR277 = ""
Dim bSTR278
bSTR278 = ""
Dim boolean139
settingRepository1.GetAttrInfo "COURANT", bSTR277, bSTR278, boolean139
'--------------------------------------------------
' Parameter 1 : (String) "COURANT"
' Parameter 2 : (String) "Default value"
' Parameter 3 : (String) "Unlocked"
' Parameter 4 : (Boolean) False
'--------------------------------------------------

long140 = settingRepository1.GetAttr("COURANT_Large")
'--------------------------------------------------
' Parameter 1 : (String) "COURANT_Large"
' Returned value : (Variant) (Long) 1
'--------------------------------------------------

Dim bSTR279
bSTR279 = ""
Dim bSTR280
bSTR280 = ""
Dim boolean140
settingRepository1.GetAttrInfo "COURANT_Large", bSTR279, bSTR280, boolean140
'--------------------------------------------------
' Parameter 1 : (String) "COURANT_Large"
' Parameter 2 : (String) "Default value"
' Parameter 3 : (String) "Unlocked"
' Parameter 4 : (Boolean) False
'--------------------------------------------------

long141 = settingRepository1.GetAttr("COURANT_ExtraLarge")
'--------------------------------------------------
' Parameter 1 : (String) "COURANT_ExtraLarge"
' Returned value : (Variant) (Long) 1
'--------------------------------------------------

Dim bSTR281
bSTR281 = ""
Dim bSTR282
bSTR282 = ""
Dim boolean141
settingRepository1.GetAttrInfo "COURANT_ExtraLarge", bSTR281, bSTR282, boolean141
'--------------------------------------------------
' Parameter 1 : (String) "COURANT_ExtraLarge"
' Parameter 2 : (String) "Default value"
' Parameter 3 : (String) "Unlocked"
' Parameter 4 : (Boolean) False
'--------------------------------------------------

long142 = settingRepository1.GetAttr("COURANT_Small")
'--------------------------------------------------
' Parameter 1 : (String) "COURANT_Small"
' Returned value : (Variant) (Long) 1
'--------------------------------------------------

Dim bSTR283
bSTR283 = ""
Dim bSTR284
bSTR284 = ""
Dim boolean142
settingRepository1.GetAttrInfo "COURANT_Small", bSTR283, bSTR284, boolean142
'--------------------------------------------------
' Parameter 1 : (String) "COURANT_Small"
' Parameter 2 : (String) "Default value"
' Parameter 3 : (String) "Unlocked"
' Parameter 4 : (Boolean) False
'--------------------------------------------------

long143 = settingRepository1.GetAttr("COURANT_ExtraSmall")
'--------------------------------------------------
' Parameter 1 : (String) "COURANT_ExtraSmall"
' Returned value : (Variant) (Long) 1
'--------------------------------------------------

Dim bSTR285
bSTR285 = ""
Dim bSTR286
bSTR286 = ""
Dim boolean143
settingRepository1.GetAttrInfo "COURANT_ExtraSmall", bSTR285, bSTR286, boolean143
'--------------------------------------------------
' Parameter 1 : (String) "COURANT_ExtraSmall"
' Parameter 2 : (String) "Default value"
' Parameter 3 : (String) "Unlocked"
' Parameter 4 : (Boolean) False
'--------------------------------------------------

long144 = settingRepository1.GetAttr("COURANT_Nanometric")
'--------------------------------------------------
' Parameter 1 : (String) "COURANT_Nanometric"
' Returned value : (Variant) (Long) 1
'--------------------------------------------------

Dim bSTR287
bSTR287 = ""
Dim bSTR288
bSTR288 = ""
Dim boolean144
settingRepository1.GetAttrInfo "COURANT_Nanometric", bSTR287, bSTR288, boolean144
'--------------------------------------------------
' Parameter 1 : (String) "COURANT_Nanometric"
' Parameter 2 : (String) "Default value"
' Parameter 3 : (String) "Unlocked"
' Parameter 4 : (Boolean) False
'--------------------------------------------------

long145 = settingRepository1.GetAttr("ACCELRTN")
'--------------------------------------------------
' Parameter 1 : (String) "ACCELRTN"
' Returned value : (Variant) (Long) 1
'--------------------------------------------------

Dim bSTR289
bSTR289 = ""
Dim bSTR290
bSTR290 = ""
Dim boolean145
settingRepository1.GetAttrInfo "ACCELRTN", bSTR289, bSTR290, boolean145
'--------------------------------------------------
' Parameter 1 : (String) "ACCELRTN"
' Parameter 2 : (String) "Default value"
' Parameter 3 : (String) "Unlocked"
' Parameter 4 : (Boolean) False
'--------------------------------------------------

long146 = settingRepository1.GetAttr("ACCELRTN_Large")
'--------------------------------------------------
' Parameter 1 : (String) "ACCELRTN_Large"
' Returned value : (Variant) (Long) 1
'--------------------------------------------------

Dim bSTR291
bSTR291 = ""
Dim bSTR292
bSTR292 = ""
Dim boolean146
settingRepository1.GetAttrInfo "ACCELRTN_Large", bSTR291, bSTR292, boolean146
'--------------------------------------------------
' Parameter 1 : (String) "ACCELRTN_Large"
' Parameter 2 : (String) "Default value"
' Parameter 3 : (String) "Unlocked"
' Parameter 4 : (Boolean) False
'--------------------------------------------------

long147 = settingRepository1.GetAttr("ACCELRTN_ExtraLarge")
'--------------------------------------------------
' Parameter 1 : (String) "ACCELRTN_ExtraLarge"
' Returned value : (Variant) (Long) 1
'--------------------------------------------------

Dim bSTR293
bSTR293 = ""
Dim bSTR294
bSTR294 = ""
Dim boolean147
settingRepository1.GetAttrInfo "ACCELRTN_ExtraLarge", bSTR293, bSTR294, boolean147
'--------------------------------------------------
' Parameter 1 : (String) "ACCELRTN_ExtraLarge"
' Parameter 2 : (String) "Default value"
' Parameter 3 : (String) "Unlocked"
' Parameter 4 : (Boolean) False
'--------------------------------------------------

long148 = settingRepository1.GetAttr("ACCELRTN_Small")
'--------------------------------------------------
' Parameter 1 : (String) "ACCELRTN_Small"
' Returned value : (Variant) (Long) 1
'--------------------------------------------------

Dim bSTR295
bSTR295 = ""
Dim bSTR296
bSTR296 = ""
Dim boolean148
settingRepository1.GetAttrInfo "ACCELRTN_Small", bSTR295, bSTR296, boolean148
'--------------------------------------------------
' Parameter 1 : (String) "ACCELRTN_Small"
' Parameter 2 : (String) "Default value"
' Parameter 3 : (String) "Unlocked"
' Parameter 4 : (Boolean) False
'--------------------------------------------------

long149 = settingRepository1.GetAttr("ACCELRTN_ExtraSmall")
'--------------------------------------------------
' Parameter 1 : (String) "ACCELRTN_ExtraSmall"
' Returned value : (Variant) (Long) 1
'--------------------------------------------------

Dim bSTR297
bSTR297 = ""
Dim bSTR298
bSTR298 = ""
Dim boolean149
settingRepository1.GetAttrInfo "ACCELRTN_ExtraSmall", bSTR297, bSTR298, boolean149
'--------------------------------------------------
' Parameter 1 : (String) "ACCELRTN_ExtraSmall"
' Parameter 2 : (String) "Default value"
' Parameter 3 : (String) "Unlocked"
' Parameter 4 : (Boolean) False
'--------------------------------------------------

long150 = settingRepository1.GetAttr("ACCELRTN_Nanometric")
'--------------------------------------------------
' Parameter 1 : (String) "ACCELRTN_Nanometric"
' Returned value : (Variant) (Long) 1
'--------------------------------------------------

Dim bSTR299
bSTR299 = ""
Dim bSTR300
bSTR300 = ""
Dim boolean150
settingRepository1.GetAttrInfo "ACCELRTN_Nanometric", bSTR299, bSTR300, boolean150
'--------------------------------------------------
' Parameter 1 : (String) "ACCELRTN_Nanometric"
' Parameter 2 : (String) "Default value"
' Parameter 3 : (String) "Unlocked"
' Parameter 4 : (Boolean) False
'--------------------------------------------------

long151 = settingRepository1.GetAttr("ANGACCELRTN")
'--------------------------------------------------
' Parameter 1 : (String) "ANGACCELRTN"
' Returned value : (Variant) (Long) 1
'--------------------------------------------------

Dim bSTR301
bSTR301 = ""
Dim bSTR302
bSTR302 = ""
Dim boolean151
settingRepository1.GetAttrInfo "ANGACCELRTN", bSTR301, bSTR302, boolean151
'--------------------------------------------------
' Parameter 1 : (String) "ANGACCELRTN"
' Parameter 2 : (String) "Default value"
' Parameter 3 : (String) "Unlocked"
' Parameter 4 : (Boolean) False
'--------------------------------------------------

long152 = settingRepository1.GetAttr("ANGACCELRTN_Large")
'--------------------------------------------------
' Parameter 1 : (String) "ANGACCELRTN_Large"
' Returned value : (Variant) (Long) 1
'--------------------------------------------------

Dim bSTR303
bSTR303 = ""
Dim bSTR304
bSTR304 = ""
Dim boolean152
settingRepository1.GetAttrInfo "ANGACCELRTN_Large", bSTR303, bSTR304, boolean152
'--------------------------------------------------
' Parameter 1 : (String) "ANGACCELRTN_Large"
' Parameter 2 : (String) "Default value"
' Parameter 3 : (String) "Unlocked"
' Parameter 4 : (Boolean) False
'--------------------------------------------------

long153 = settingRepository1.GetAttr("ANGACCELRTN_ExtraLarge")
'--------------------------------------------------
' Parameter 1 : (String) "ANGACCELRTN_ExtraLarge"
' Returned value : (Variant) (Long) 1
'--------------------------------------------------

Dim bSTR305
bSTR305 = ""
Dim bSTR306
bSTR306 = ""
Dim boolean153
settingRepository1.GetAttrInfo "ANGACCELRTN_ExtraLarge", bSTR305, bSTR306, boolean153
'--------------------------------------------------
' Parameter 1 : (String) "ANGACCELRTN_ExtraLarge"
' Parameter 2 : (String) "Default value"
' Parameter 3 : (String) "Unlocked"
' Parameter 4 : (Boolean) False
'--------------------------------------------------

long154 = settingRepository1.GetAttr("ANGACCELRTN_Small")
'--------------------------------------------------
' Parameter 1 : (String) "ANGACCELRTN_Small"
' Returned value : (Variant) (Long) 1
'--------------------------------------------------

Dim bSTR307
bSTR307 = ""
Dim bSTR308
bSTR308 = ""
Dim boolean154
settingRepository1.GetAttrInfo "ANGACCELRTN_Small", bSTR307, bSTR308, boolean154
'--------------------------------------------------
' Parameter 1 : (String) "ANGACCELRTN_Small"
' Parameter 2 : (String) "Default value"
' Parameter 3 : (String) "Unlocked"
' Parameter 4 : (Boolean) False
'--------------------------------------------------

long155 = settingRepository1.GetAttr("ANGACCELRTN_ExtraSmall")
'--------------------------------------------------
' Parameter 1 : (String) "ANGACCELRTN_ExtraSmall"
' Returned value : (Variant) (Long) 1
'--------------------------------------------------

Dim bSTR309
bSTR309 = ""
Dim bSTR310
bSTR310 = ""
Dim boolean155
settingRepository1.GetAttrInfo "ANGACCELRTN_ExtraSmall", bSTR309, bSTR310, boolean155
'--------------------------------------------------
' Parameter 1 : (String) "ANGACCELRTN_ExtraSmall"
' Parameter 2 : (String) "Default value"
' Parameter 3 : (String) "Unlocked"
' Parameter 4 : (Boolean) False
'--------------------------------------------------

long156 = settingRepository1.GetAttr("ANGACCELRTN_Nanometric")
'--------------------------------------------------
' Parameter 1 : (String) "ANGACCELRTN_Nanometric"
' Returned value : (Variant) (Long) 1
'--------------------------------------------------

Dim bSTR311
bSTR311 = ""
Dim bSTR312
bSTR312 = ""
Dim boolean156
settingRepository1.GetAttrInfo "ANGACCELRTN_Nanometric", bSTR311, bSTR312, boolean156
'--------------------------------------------------
' Parameter 1 : (String) "ANGACCELRTN_Nanometric"
' Parameter 2 : (String) "Default value"
' Parameter 3 : (String) "Unlocked"
' Parameter 4 : (Boolean) False
'--------------------------------------------------

long157 = settingRepository1.GetAttr("ENERGYMEC")
'--------------------------------------------------
' Parameter 1 : (String) "ENERGYMEC"
' Returned value : (Variant) (Long) 1
'--------------------------------------------------

Dim bSTR313
bSTR313 = ""
Dim bSTR314
bSTR314 = ""
Dim boolean157
settingRepository1.GetAttrInfo "ENERGYMEC", bSTR313, bSTR314, boolean157
'--------------------------------------------------
' Parameter 1 : (String) "ENERGYMEC"
' Parameter 2 : (String) "Default value"
' Parameter 3 : (String) "Unlocked"
' Parameter 4 : (Boolean) False
'--------------------------------------------------

long158 = settingRepository1.GetAttr("ENERGYMEC_Large")
'--------------------------------------------------
' Parameter 1 : (String) "ENERGYMEC_Large"
' Returned value : (Variant) (Long) 1
'--------------------------------------------------

Dim bSTR315
bSTR315 = ""
Dim bSTR316
bSTR316 = ""
Dim boolean158
settingRepository1.GetAttrInfo "ENERGYMEC_Large", bSTR315, bSTR316, boolean158
'--------------------------------------------------
' Parameter 1 : (String) "ENERGYMEC_Large"
' Parameter 2 : (String) "Default value"
' Parameter 3 : (String) "Unlocked"
' Parameter 4 : (Boolean) False
'--------------------------------------------------

long159 = settingRepository1.GetAttr("ENERGYMEC_ExtraLarge")
'--------------------------------------------------
' Parameter 1 : (String) "ENERGYMEC_ExtraLarge"
' Returned value : (Variant) (Long) 1
'--------------------------------------------------

Dim bSTR317
bSTR317 = ""
Dim bSTR318
bSTR318 = ""
Dim boolean159
settingRepository1.GetAttrInfo "ENERGYMEC_ExtraLarge", bSTR317, bSTR318, boolean159
'--------------------------------------------------
' Parameter 1 : (String) "ENERGYMEC_ExtraLarge"
' Parameter 2 : (String) "Default value"
' Parameter 3 : (String) "Unlocked"
' Parameter 4 : (Boolean) False
'--------------------------------------------------

long160 = settingRepository1.GetAttr("ENERGYMEC_Small")
'--------------------------------------------------
' Parameter 1 : (String) "ENERGYMEC_Small"
' Returned value : (Variant) (Long) 1
'--------------------------------------------------

Dim bSTR319
bSTR319 = ""
Dim bSTR320
bSTR320 = ""
Dim boolean160
settingRepository1.GetAttrInfo "ENERGYMEC_Small", bSTR319, bSTR320, boolean160
'--------------------------------------------------
' Parameter 1 : (String) "ENERGYMEC_Small"
' Parameter 2 : (String) "Default value"
' Parameter 3 : (String) "Unlocked"
' Parameter 4 : (Boolean) False
'--------------------------------------------------

long161 = settingRepository1.GetAttr("ENERGYMEC_ExtraSmall")
'--------------------------------------------------
' Parameter 1 : (String) "ENERGYMEC_ExtraSmall"
' Returned value : (Variant) (Long) 1
'--------------------------------------------------

Dim bSTR321
bSTR321 = ""
Dim bSTR322
bSTR322 = ""
Dim boolean161
settingRepository1.GetAttrInfo "ENERGYMEC_ExtraSmall", bSTR321, bSTR322, boolean161
'--------------------------------------------------
' Parameter 1 : (String) "ENERGYMEC_ExtraSmall"
' Parameter 2 : (String) "Default value"
' Parameter 3 : (String) "Unlocked"
' Parameter 4 : (Boolean) False
'--------------------------------------------------

long162 = settingRepository1.GetAttr("ENERGYMEC_Nanometric")
'--------------------------------------------------
' Parameter 1 : (String) "ENERGYMEC_Nanometric"
' Returned value : (Variant) (Long) 1
'--------------------------------------------------

Dim bSTR323
bSTR323 = ""
Dim bSTR324
bSTR324 = ""
Dim boolean162
settingRepository1.GetAttrInfo "ENERGYMEC_Nanometric", bSTR323, bSTR324, boolean162
'--------------------------------------------------
' Parameter 1 : (String) "ENERGYMEC_Nanometric"
' Parameter 2 : (String) "Default value"
' Parameter 3 : (String) "Unlocked"
' Parameter 4 : (Boolean) False
'--------------------------------------------------

long163 = settingRepository1.GetAttr("VOLFORCE")
'--------------------------------------------------
' Parameter 1 : (String) "VOLFORCE"
' Returned value : (Variant) (Long) 1
'--------------------------------------------------

Dim bSTR325
bSTR325 = ""
Dim bSTR326
bSTR326 = ""
Dim boolean163
settingRepository1.GetAttrInfo "VOLFORCE", bSTR325, bSTR326, boolean163
'--------------------------------------------------
' Parameter 1 : (String) "VOLFORCE"
' Parameter 2 : (String) "Default value"
' Parameter 3 : (String) "Unlocked"
' Parameter 4 : (Boolean) False
'--------------------------------------------------

long164 = settingRepository1.GetAttr("VOLFORCE_Large")
'--------------------------------------------------
' Parameter 1 : (String) "VOLFORCE_Large"
' Returned value : (Variant) (Long) 1
'--------------------------------------------------

Dim bSTR327
bSTR327 = ""
Dim bSTR328
bSTR328 = ""
Dim boolean164
settingRepository1.GetAttrInfo "VOLFORCE_Large", bSTR327, bSTR328, boolean164
'--------------------------------------------------
' Parameter 1 : (String) "VOLFORCE_Large"
' Parameter 2 : (String) "Default value"
' Parameter 3 : (String) "Unlocked"
' Parameter 4 : (Boolean) False
'--------------------------------------------------

long165 = settingRepository1.GetAttr("VOLFORCE_ExtraLarge")
'--------------------------------------------------
' Parameter 1 : (String) "VOLFORCE_ExtraLarge"
' Returned value : (Variant) (Long) 1
'--------------------------------------------------

Dim bSTR329
bSTR329 = ""
Dim bSTR330
bSTR330 = ""
Dim boolean165
settingRepository1.GetAttrInfo "VOLFORCE_ExtraLarge", bSTR329, bSTR330, boolean165
'--------------------------------------------------
' Parameter 1 : (String) "VOLFORCE_ExtraLarge"
' Parameter 2 : (String) "Default value"
' Parameter 3 : (String) "Unlocked"
' Parameter 4 : (Boolean) False
'--------------------------------------------------

long166 = settingRepository1.GetAttr("VOLFORCE_Small")
'--------------------------------------------------
' Parameter 1 : (String) "VOLFORCE_Small"
' Returned value : (Variant) (Long) 1
'--------------------------------------------------

Dim bSTR331
bSTR331 = ""
Dim bSTR332
bSTR332 = ""
Dim boolean166
settingRepository1.GetAttrInfo "VOLFORCE_Small", bSTR331, bSTR332, boolean166
'--------------------------------------------------
' Parameter 1 : (String) "VOLFORCE_Small"
' Parameter 2 : (String) "Default value"
' Parameter 3 : (String) "Unlocked"
' Parameter 4 : (Boolean) False
'--------------------------------------------------

long167 = settingRepository1.GetAttr("VOLFORCE_ExtraSmall")
'--------------------------------------------------
' Parameter 1 : (String) "VOLFORCE_ExtraSmall"
' Returned value : (Variant) (Long) 1
'--------------------------------------------------

Dim bSTR333
bSTR333 = ""
Dim bSTR334
bSTR334 = ""
Dim boolean167
settingRepository1.GetAttrInfo "VOLFORCE_ExtraSmall", bSTR333, bSTR334, boolean167
'--------------------------------------------------
' Parameter 1 : (String) "VOLFORCE_ExtraSmall"
' Parameter 2 : (String) "Default value"
' Parameter 3 : (String) "Unlocked"
' Parameter 4 : (Boolean) False
'--------------------------------------------------

long168 = settingRepository1.GetAttr("VOLFORCE_Nanometric")
'--------------------------------------------------
' Parameter 1 : (String) "VOLFORCE_Nanometric"
' Returned value : (Variant) (Long) 1
'--------------------------------------------------

Dim bSTR335
bSTR335 = ""
Dim bSTR336
bSTR336 = ""
Dim boolean168
settingRepository1.GetAttrInfo "VOLFORCE_Nanometric", bSTR335, bSTR336, boolean168
'--------------------------------------------------
' Parameter 1 : (String) "VOLFORCE_Nanometric"
' Parameter 2 : (String) "Default value"
' Parameter 3 : (String) "Unlocked"
' Parameter 4 : (Boolean) False
'--------------------------------------------------

long169 = settingRepository1.GetAttr("SURFACICMASS")
'--------------------------------------------------
' Parameter 1 : (String) "SURFACICMASS"
' Returned value : (Variant) (Long) 1
'--------------------------------------------------

Dim bSTR337
bSTR337 = ""
Dim bSTR338
bSTR338 = ""
Dim boolean169
settingRepository1.GetAttrInfo "SURFACICMASS", bSTR337, bSTR338, boolean169
'--------------------------------------------------
' Parameter 1 : (String) "SURFACICMASS"
' Parameter 2 : (String) "Default value"
' Parameter 3 : (String) "Unlocked"
' Parameter 4 : (Boolean) False
'--------------------------------------------------

long170 = settingRepository1.GetAttr("SURFACICMASS_Large")
'--------------------------------------------------
' Parameter 1 : (String) "SURFACICMASS_Large"
' Returned value : (Variant) (Long) 1
'--------------------------------------------------

Dim bSTR339
bSTR339 = ""
Dim bSTR340
bSTR340 = ""
Dim boolean170
settingRepository1.GetAttrInfo "SURFACICMASS_Large", bSTR339, bSTR340, boolean170
'--------------------------------------------------
' Parameter 1 : (String) "SURFACICMASS_Large"
' Parameter 2 : (String) "Default value"
' Parameter 3 : (String) "Unlocked"
' Parameter 4 : (Boolean) False
'--------------------------------------------------

long171 = settingRepository1.GetAttr("SURFACICMASS_ExtraLarge")
'--------------------------------------------------
' Parameter 1 : (String) "SURFACICMASS_ExtraLarge"
' Returned value : (Variant) (Long) 1
'--------------------------------------------------

Dim bSTR341
bSTR341 = ""
Dim bSTR342
bSTR342 = ""
Dim boolean171
settingRepository1.GetAttrInfo "SURFACICMASS_ExtraLarge", bSTR341, bSTR342, boolean171
'--------------------------------------------------
' Parameter 1 : (String) "SURFACICMASS_ExtraLarge"
' Parameter 2 : (String) "Default value"
' Parameter 3 : (String) "Unlocked"
' Parameter 4 : (Boolean) False
'--------------------------------------------------

long172 = settingRepository1.GetAttr("SURFACICMASS_Small")
'--------------------------------------------------
' Parameter 1 : (String) "SURFACICMASS_Small"
' Returned value : (Variant) (Long) 1
'--------------------------------------------------

Dim bSTR343
bSTR343 = ""
Dim bSTR344
bSTR344 = ""
Dim boolean172
settingRepository1.GetAttrInfo "SURFACICMASS_Small", bSTR343, bSTR344, boolean172
'--------------------------------------------------
' Parameter 1 : (String) "SURFACICMASS_Small"
' Parameter 2 : (String) "Default value"
' Parameter 3 : (String) "Unlocked"
' Parameter 4 : (Boolean) False
'--------------------------------------------------

long173 = settingRepository1.GetAttr("SURFACICMASS_ExtraSmall")
'--------------------------------------------------
' Parameter 1 : (String) "SURFACICMASS_ExtraSmall"
' Returned value : (Variant) (Long) 1
'--------------------------------------------------

Dim bSTR345
bSTR345 = ""
Dim bSTR346
bSTR346 = ""
Dim boolean173
settingRepository1.GetAttrInfo "SURFACICMASS_ExtraSmall", bSTR345, bSTR346, boolean173
'--------------------------------------------------
' Parameter 1 : (String) "SURFACICMASS_ExtraSmall"
' Parameter 2 : (String) "Default value"
' Parameter 3 : (String) "Unlocked"
' Parameter 4 : (Boolean) False
'--------------------------------------------------

long174 = settingRepository1.GetAttr("SURFACICMASS_Nanometric")
'--------------------------------------------------
' Parameter 1 : (String) "SURFACICMASS_Nanometric"
' Returned value : (Variant) (Long) 1
'--------------------------------------------------

Dim bSTR347
bSTR347 = ""
Dim bSTR348
bSTR348 = ""
Dim boolean174
settingRepository1.GetAttrInfo "SURFACICMASS_Nanometric", bSTR347, bSTR348, boolean174
'--------------------------------------------------
' Parameter 1 : (String) "SURFACICMASS_Nanometric"
' Parameter 2 : (String) "Default value"
' Parameter 3 : (String) "Unlocked"
' Parameter 4 : (Boolean) False
'--------------------------------------------------

long175 = settingRepository1.GetAttr("SPEED")
'--------------------------------------------------
' Parameter 1 : (String) "SPEED"
' Returned value : (Variant) (Long) 1
'--------------------------------------------------

Dim bSTR349
bSTR349 = ""
Dim bSTR350
bSTR350 = ""
Dim boolean175
settingRepository1.GetAttrInfo "SPEED", bSTR349, bSTR350, boolean175
'--------------------------------------------------
' Parameter 1 : (String) "SPEED"
' Parameter 2 : (String) "Default value"
' Parameter 3 : (String) "Unlocked"
' Parameter 4 : (Boolean) False
'--------------------------------------------------

long176 = settingRepository1.GetAttr("SPEED_Large")
'--------------------------------------------------
' Parameter 1 : (String) "SPEED_Large"
' Returned value : (Variant) (Long) 1
'--------------------------------------------------

Dim bSTR351
bSTR351 = ""
Dim bSTR352
bSTR352 = ""
Dim boolean176
settingRepository1.GetAttrInfo "SPEED_Large", bSTR351, bSTR352, boolean176
'--------------------------------------------------
' Parameter 1 : (String) "SPEED_Large"
' Parameter 2 : (String) "Default value"
' Parameter 3 : (String) "Unlocked"
' Parameter 4 : (Boolean) False
'--------------------------------------------------

long177 = settingRepository1.GetAttr("SPEED_ExtraLarge")
'--------------------------------------------------
' Parameter 1 : (String) "SPEED_ExtraLarge"
' Returned value : (Variant) (Long) 1
'--------------------------------------------------

Dim bSTR353
bSTR353 = ""
Dim bSTR354
bSTR354 = ""
Dim boolean177
settingRepository1.GetAttrInfo "SPEED_ExtraLarge", bSTR353, bSTR354, boolean177
'--------------------------------------------------
' Parameter 1 : (String) "SPEED_ExtraLarge"
' Parameter 2 : (String) "Default value"
' Parameter 3 : (String) "Unlocked"
' Parameter 4 : (Boolean) False
'--------------------------------------------------

long178 = settingRepository1.GetAttr("SPEED_Small")
'--------------------------------------------------
' Parameter 1 : (String) "SPEED_Small"
' Returned value : (Variant) (Long) 1
'--------------------------------------------------

Dim bSTR355
bSTR355 = ""
Dim bSTR356
bSTR356 = ""
Dim boolean178
settingRepository1.GetAttrInfo "SPEED_Small", bSTR355, bSTR356, boolean178
'--------------------------------------------------
' Parameter 1 : (String) "SPEED_Small"
' Parameter 2 : (String) "Default value"
' Parameter 3 : (String) "Unlocked"
' Parameter 4 : (Boolean) False
'--------------------------------------------------

long179 = settingRepository1.GetAttr("SPEED_ExtraSmall")
'--------------------------------------------------
' Parameter 1 : (String) "SPEED_ExtraSmall"
' Returned value : (Variant) (Long) 1
'--------------------------------------------------

Dim bSTR357
bSTR357 = ""
Dim bSTR358
bSTR358 = ""
Dim boolean179
settingRepository1.GetAttrInfo "SPEED_ExtraSmall", bSTR357, bSTR358, boolean179
'--------------------------------------------------
' Parameter 1 : (String) "SPEED_ExtraSmall"
' Parameter 2 : (String) "Default value"
' Parameter 3 : (String) "Unlocked"
' Parameter 4 : (Boolean) False
'--------------------------------------------------

long180 = settingRepository1.GetAttr("SPEED_Nanometric")
'--------------------------------------------------
' Parameter 1 : (String) "SPEED_Nanometric"
' Returned value : (Variant) (Long) 1
'--------------------------------------------------

Dim bSTR359
bSTR359 = ""
Dim bSTR360
bSTR360 = ""
Dim boolean180
settingRepository1.GetAttrInfo "SPEED_Nanometric", bSTR359, bSTR360, boolean180
'--------------------------------------------------
' Parameter 1 : (String) "SPEED_Nanometric"
' Parameter 2 : (String) "Default value"
' Parameter 3 : (String) "Unlocked"
' Parameter 4 : (Boolean) False
'--------------------------------------------------

long181 = settingRepository1.GetAttr("LINEARFEEDRATE")
'--------------------------------------------------
' Parameter 1 : (String) "LINEARFEEDRATE"
' Returned value : (Variant) (Long) 1
'--------------------------------------------------

Dim bSTR361
bSTR361 = ""
Dim bSTR362
bSTR362 = ""
Dim boolean181
settingRepository1.GetAttrInfo "LINEARFEEDRATE", bSTR361, bSTR362, boolean181
'--------------------------------------------------
' Parameter 1 : (String) "LINEARFEEDRATE"
' Parameter 2 : (String) "Default value"
' Parameter 3 : (String) "Unlocked"
' Parameter 4 : (Boolean) False
'--------------------------------------------------

long182 = settingRepository1.GetAttr("LINEARFEEDRATE_Large")
'--------------------------------------------------
' Parameter 1 : (String) "LINEARFEEDRATE_Large"
' Returned value : (Variant) (Long) 1
'--------------------------------------------------

Dim bSTR363
bSTR363 = ""
Dim bSTR364
bSTR364 = ""
Dim boolean182
settingRepository1.GetAttrInfo "LINEARFEEDRATE_Large", bSTR363, bSTR364, boolean182
'--------------------------------------------------
' Parameter 1 : (String) "LINEARFEEDRATE_Large"
' Parameter 2 : (String) "Default value"
' Parameter 3 : (String) "Unlocked"
' Parameter 4 : (Boolean) False
'--------------------------------------------------

long183 = settingRepository1.GetAttr("LINEARFEEDRATE_ExtraLarge")
'--------------------------------------------------
' Parameter 1 : (String) "LINEARFEEDRATE_ExtraLarge"
' Returned value : (Variant) (Long) 1
'--------------------------------------------------

Dim bSTR365
bSTR365 = ""
Dim bSTR366
bSTR366 = ""
Dim boolean183
settingRepository1.GetAttrInfo "LINEARFEEDRATE_ExtraLarge", bSTR365, bSTR366, boolean183
'--------------------------------------------------
' Parameter 1 : (String) "LINEARFEEDRATE_ExtraLarge"
' Parameter 2 : (String) "Default value"
' Parameter 3 : (String) "Unlocked"
' Parameter 4 : (Boolean) False
'--------------------------------------------------

long184 = settingRepository1.GetAttr("LINEARFEEDRATE_Small")
'--------------------------------------------------
' Parameter 1 : (String) "LINEARFEEDRATE_Small"
' Returned value : (Variant) (Long) 1
'--------------------------------------------------

Dim bSTR367
bSTR367 = ""
Dim bSTR368
bSTR368 = ""
Dim boolean184
settingRepository1.GetAttrInfo "LINEARFEEDRATE_Small", bSTR367, bSTR368, boolean184
'--------------------------------------------------
' Parameter 1 : (String) "LINEARFEEDRATE_Small"
' Parameter 2 : (String) "Default value"
' Parameter 3 : (String) "Unlocked"
' Parameter 4 : (Boolean) False
'--------------------------------------------------

long185 = settingRepository1.GetAttr("LINEARFEEDRATE_ExtraSmall")
'--------------------------------------------------
' Parameter 1 : (String) "LINEARFEEDRATE_ExtraSmall"
' Returned value : (Variant) (Long) 1
'--------------------------------------------------

Dim bSTR369
bSTR369 = ""
Dim bSTR370
bSTR370 = ""
Dim boolean185
settingRepository1.GetAttrInfo "LINEARFEEDRATE_ExtraSmall", bSTR369, bSTR370, boolean185
'--------------------------------------------------
' Parameter 1 : (String) "LINEARFEEDRATE_ExtraSmall"
' Parameter 2 : (String) "Default value"
' Parameter 3 : (String) "Unlocked"
' Parameter 4 : (Boolean) False
'--------------------------------------------------

long186 = settingRepository1.GetAttr("LINEARFEEDRATE_Nanometric")
'--------------------------------------------------
' Parameter 1 : (String) "LINEARFEEDRATE_Nanometric"
' Returned value : (Variant) (Long) 1
'--------------------------------------------------

Dim bSTR371
bSTR371 = ""
Dim bSTR372
bSTR372 = ""
Dim boolean186
settingRepository1.GetAttrInfo "LINEARFEEDRATE_Nanometric", bSTR371, bSTR372, boolean186
'--------------------------------------------------
' Parameter 1 : (String) "LINEARFEEDRATE_Nanometric"
' Parameter 2 : (String) "Default value"
' Parameter 3 : (String) "Unlocked"
' Parameter 4 : (Boolean) False
'--------------------------------------------------

long187 = settingRepository1.GetAttr("ANGULARFEEDRATE")
'--------------------------------------------------
' Parameter 1 : (String) "ANGULARFEEDRATE"
' Returned value : (Variant) (Long) 1
'--------------------------------------------------

Dim bSTR373
bSTR373 = ""
Dim bSTR374
bSTR374 = ""
Dim boolean187
settingRepository1.GetAttrInfo "ANGULARFEEDRATE", bSTR373, bSTR374, boolean187
'--------------------------------------------------
' Parameter 1 : (String) "ANGULARFEEDRATE"
' Parameter 2 : (String) "Default value"
' Parameter 3 : (String) "Unlocked"
' Parameter 4 : (Boolean) False
'--------------------------------------------------

long188 = settingRepository1.GetAttr("ANGULARFEEDRATE_Large")
'--------------------------------------------------
' Parameter 1 : (String) "ANGULARFEEDRATE_Large"
' Returned value : (Variant) (Long) 1
'--------------------------------------------------

Dim bSTR375
bSTR375 = ""
Dim bSTR376
bSTR376 = ""
Dim boolean188
settingRepository1.GetAttrInfo "ANGULARFEEDRATE_Large", bSTR375, bSTR376, boolean188
'--------------------------------------------------
' Parameter 1 : (String) "ANGULARFEEDRATE_Large"
' Parameter 2 : (String) "Default value"
' Parameter 3 : (String) "Unlocked"
' Parameter 4 : (Boolean) False
'--------------------------------------------------

long189 = settingRepository1.GetAttr("ANGULARFEEDRATE_ExtraLarge")
'--------------------------------------------------
' Parameter 1 : (String) "ANGULARFEEDRATE_ExtraLarge"
' Returned value : (Variant) (Long) 1
'--------------------------------------------------

Dim bSTR377
bSTR377 = ""
Dim bSTR378
bSTR378 = ""
Dim boolean189
settingRepository1.GetAttrInfo "ANGULARFEEDRATE_ExtraLarge", bSTR377, bSTR378, boolean189
'--------------------------------------------------
' Parameter 1 : (String) "ANGULARFEEDRATE_ExtraLarge"
' Parameter 2 : (String) "Default value"
' Parameter 3 : (String) "Unlocked"
' Parameter 4 : (Boolean) False
'--------------------------------------------------

long190 = settingRepository1.GetAttr("ANGULARFEEDRATE_Small")
'--------------------------------------------------
' Parameter 1 : (String) "ANGULARFEEDRATE_Small"
' Returned value : (Variant) (Long) 1
'--------------------------------------------------

Dim bSTR379
bSTR379 = ""
Dim bSTR380
bSTR380 = ""
Dim boolean190
settingRepository1.GetAttrInfo "ANGULARFEEDRATE_Small", bSTR379, bSTR380, boolean190
'--------------------------------------------------
' Parameter 1 : (String) "ANGULARFEEDRATE_Small"
' Parameter 2 : (String) "Default value"
' Parameter 3 : (String) "Unlocked"
' Parameter 4 : (Boolean) False
'--------------------------------------------------

long191 = settingRepository1.GetAttr("ANGULARFEEDRATE_ExtraSmall")
'--------------------------------------------------
' Parameter 1 : (String) "ANGULARFEEDRATE_ExtraSmall"
' Returned value : (Variant) (Long) 1
'--------------------------------------------------

Dim bSTR381
bSTR381 = ""
Dim bSTR382
bSTR382 = ""
Dim boolean191
settingRepository1.GetAttrInfo "ANGULARFEEDRATE_ExtraSmall", bSTR381, bSTR382, boolean191
'--------------------------------------------------
' Parameter 1 : (String) "ANGULARFEEDRATE_ExtraSmall"
' Parameter 2 : (String) "Default value"
' Parameter 3 : (String) "Unlocked"
' Parameter 4 : (Boolean) False
'--------------------------------------------------

long192 = settingRepository1.GetAttr("ANGULARFEEDRATE_Nanometric")
'--------------------------------------------------
' Parameter 1 : (String) "ANGULARFEEDRATE_Nanometric"
' Returned value : (Variant) (Long) 1
'--------------------------------------------------

Dim bSTR383
bSTR383 = ""
Dim bSTR384
bSTR384 = ""
Dim boolean192
settingRepository1.GetAttrInfo "ANGULARFEEDRATE_Nanometric", bSTR383, bSTR384, boolean192
'--------------------------------------------------
' Parameter 1 : (String) "ANGULARFEEDRATE_Nanometric"
' Parameter 2 : (String) "Default value"
' Parameter 3 : (String) "Unlocked"
' Parameter 4 : (Boolean) False
'--------------------------------------------------

long193 = settingRepository1.GetAttr("LINEARSPINDLESPEED")
'--------------------------------------------------
' Parameter 1 : (String) "LINEARSPINDLESPEED"
' Returned value : (Variant) (Long) 1
'--------------------------------------------------

Dim bSTR385
bSTR385 = ""
Dim bSTR386
bSTR386 = ""
Dim boolean193
settingRepository1.GetAttrInfo "LINEARSPINDLESPEED", bSTR385, bSTR386, boolean193
'--------------------------------------------------
' Parameter 1 : (String) "LINEARSPINDLESPEED"
' Parameter 2 : (String) "Default value"
' Parameter 3 : (String) "Unlocked"
' Parameter 4 : (Boolean) False
'--------------------------------------------------

long194 = settingRepository1.GetAttr("LINEARSPINDLESPEED_Large")
'--------------------------------------------------
' Parameter 1 : (String) "LINEARSPINDLESPEED_Large"
' Returned value : (Variant) (Long) 1
'--------------------------------------------------

Dim bSTR387
bSTR387 = ""
Dim bSTR388
bSTR388 = ""
Dim boolean194
settingRepository1.GetAttrInfo "LINEARSPINDLESPEED_Large", bSTR387, bSTR388, boolean194
'--------------------------------------------------
' Parameter 1 : (String) "LINEARSPINDLESPEED_Large"
' Parameter 2 : (String) "Default value"
' Parameter 3 : (String) "Unlocked"
' Parameter 4 : (Boolean) False
'--------------------------------------------------

long195 = settingRepository1.GetAttr("LINEARSPINDLESPEED_ExtraLarge")
'--------------------------------------------------
' Parameter 1 : (String) "LINEARSPINDLESPEED_ExtraLarge"
' Returned value : (Variant) (Long) 1
'--------------------------------------------------

Dim bSTR389
bSTR389 = ""
Dim bSTR390
bSTR390 = ""
Dim boolean195
settingRepository1.GetAttrInfo "LINEARSPINDLESPEED_ExtraLarge", bSTR389, bSTR390, boolean195
'--------------------------------------------------
' Parameter 1 : (String) "LINEARSPINDLESPEED_ExtraLarge"
' Parameter 2 : (String) "Default value"
' Parameter 3 : (String) "Unlocked"
' Parameter 4 : (Boolean) False
'--------------------------------------------------

long196 = settingRepository1.GetAttr("LINEARSPINDLESPEED_Small")
'--------------------------------------------------
' Parameter 1 : (String) "LINEARSPINDLESPEED_Small"
' Returned value : (Variant) (Long) 1
'--------------------------------------------------

Dim bSTR391
bSTR391 = ""
Dim bSTR392
bSTR392 = ""
Dim boolean196
settingRepository1.GetAttrInfo "LINEARSPINDLESPEED_Small", bSTR391, bSTR392, boolean196
'--------------------------------------------------
' Parameter 1 : (String) "LINEARSPINDLESPEED_Small"
' Parameter 2 : (String) "Default value"
' Parameter 3 : (String) "Unlocked"
' Parameter 4 : (Boolean) False
'--------------------------------------------------

long197 = settingRepository1.GetAttr("LINEARSPINDLESPEED_ExtraSmall")
'--------------------------------------------------
' Parameter 1 : (String) "LINEARSPINDLESPEED_ExtraSmall"
' Returned value : (Variant) (Long) 1
'--------------------------------------------------

Dim bSTR393
bSTR393 = ""
Dim bSTR394
bSTR394 = ""
Dim boolean197
settingRepository1.GetAttrInfo "LINEARSPINDLESPEED_ExtraSmall", bSTR393, bSTR394, boolean197
'--------------------------------------------------
' Parameter 1 : (String) "LINEARSPINDLESPEED_ExtraSmall"
' Parameter 2 : (String) "Default value"
' Parameter 3 : (String) "Unlocked"
' Parameter 4 : (Boolean) False
'--------------------------------------------------

long198 = settingRepository1.GetAttr("LINEARSPINDLESPEED_Nanometric")
'--------------------------------------------------
' Parameter 1 : (String) "LINEARSPINDLESPEED_Nanometric"
' Returned value : (Variant) (Long) 1
'--------------------------------------------------

Dim bSTR395
bSTR395 = ""
Dim bSTR396
bSTR396 = ""
Dim boolean198
settingRepository1.GetAttrInfo "LINEARSPINDLESPEED_Nanometric", bSTR395, bSTR396, boolean198
'--------------------------------------------------
' Parameter 1 : (String) "LINEARSPINDLESPEED_Nanometric"
' Parameter 2 : (String) "Default value"
' Parameter 3 : (String) "Unlocked"
' Parameter 4 : (Boolean) False
'--------------------------------------------------

long199 = settingRepository1.GetAttr("ANGULARSPINDLESPEED")
'--------------------------------------------------
' Parameter 1 : (String) "ANGULARSPINDLESPEED"
' Returned value : (Variant) (Long) 1
'--------------------------------------------------

Dim bSTR397
bSTR397 = ""
Dim bSTR398
bSTR398 = ""
Dim boolean199
settingRepository1.GetAttrInfo "ANGULARSPINDLESPEED", bSTR397, bSTR398, boolean199
'--------------------------------------------------
' Parameter 1 : (String) "ANGULARSPINDLESPEED"
' Parameter 2 : (String) "Default value"
' Parameter 3 : (String) "Unlocked"
' Parameter 4 : (Boolean) False
'--------------------------------------------------

long200 = settingRepository1.GetAttr("ANGULARSPINDLESPEED_Large")
'--------------------------------------------------
' Parameter 1 : (String) "ANGULARSPINDLESPEED_Large"
' Returned value : (Variant) (Long) 1
'--------------------------------------------------

Dim bSTR399
bSTR399 = ""
Dim bSTR400
bSTR400 = ""
Dim boolean200
settingRepository1.GetAttrInfo "ANGULARSPINDLESPEED_Large", bSTR399, bSTR400, boolean200
'--------------------------------------------------
' Parameter 1 : (String) "ANGULARSPINDLESPEED_Large"
' Parameter 2 : (String) "Default value"
' Parameter 3 : (String) "Unlocked"
' Parameter 4 : (Boolean) False
'--------------------------------------------------

long201 = settingRepository1.GetAttr("ANGULARSPINDLESPEED_ExtraLarge")
'--------------------------------------------------
' Parameter 1 : (String) "ANGULARSPINDLESPEED_ExtraLarge"
' Returned value : (Variant) (Long) 1
'--------------------------------------------------

Dim bSTR401
bSTR401 = ""
Dim bSTR402
bSTR402 = ""
Dim boolean201
settingRepository1.GetAttrInfo "ANGULARSPINDLESPEED_ExtraLarge", bSTR401, bSTR402, boolean201
'--------------------------------------------------
' Parameter 1 : (String) "ANGULARSPINDLESPEED_ExtraLarge"
' Parameter 2 : (String) "Default value"
' Parameter 3 : (String) "Unlocked"
' Parameter 4 : (Boolean) False
'--------------------------------------------------

long202 = settingRepository1.GetAttr("ANGULARSPINDLESPEED_Small")
'--------------------------------------------------
' Parameter 1 : (String) "ANGULARSPINDLESPEED_Small"
' Returned value : (Variant) (Long) 1
'--------------------------------------------------

Dim bSTR403
bSTR403 = ""
Dim bSTR404
bSTR404 = ""
Dim boolean202
settingRepository1.GetAttrInfo "ANGULARSPINDLESPEED_Small", bSTR403, bSTR404, boolean202
'--------------------------------------------------
' Parameter 1 : (String) "ANGULARSPINDLESPEED_Small"
' Parameter 2 : (String) "Default value"
' Parameter 3 : (String) "Unlocked"
' Parameter 4 : (Boolean) False
'--------------------------------------------------

long203 = settingRepository1.GetAttr("ANGULARSPINDLESPEED_ExtraSmall")
'--------------------------------------------------
' Parameter 1 : (String) "ANGULARSPINDLESPEED_ExtraSmall"
' Returned value : (Variant) (Long) 1
'--------------------------------------------------

Dim bSTR405
bSTR405 = ""
Dim bSTR406
bSTR406 = ""
Dim boolean203
settingRepository1.GetAttrInfo "ANGULARSPINDLESPEED_ExtraSmall", bSTR405, bSTR406, boolean203
'--------------------------------------------------
' Parameter 1 : (String) "ANGULARSPINDLESPEED_ExtraSmall"
' Parameter 2 : (String) "Default value"
' Parameter 3 : (String) "Unlocked"
' Parameter 4 : (Boolean) False
'--------------------------------------------------

long204 = settingRepository1.GetAttr("ANGULARSPINDLESPEED_Nanometric")
'--------------------------------------------------
' Parameter 1 : (String) "ANGULARSPINDLESPEED_Nanometric"
' Returned value : (Variant) (Long) 1
'--------------------------------------------------

Dim bSTR407
bSTR407 = ""
Dim bSTR408
bSTR408 = ""
Dim boolean204
settingRepository1.GetAttrInfo "ANGULARSPINDLESPEED_Nanometric", bSTR407, bSTR408, boolean204
'--------------------------------------------------
' Parameter 1 : (String) "ANGULARSPINDLESPEED_Nanometric"
' Parameter 2 : (String) "Default value"
' Parameter 3 : (String) "Unlocked"
' Parameter 4 : (Boolean) False
'--------------------------------------------------

long205 = settingRepository1.GetAttr("SURFACICSPINDLESPEED")
'--------------------------------------------------
' Parameter 1 : (String) "SURFACICSPINDLESPEED"
' Returned value : (Variant) (Long) 1
'--------------------------------------------------

Dim bSTR409
bSTR409 = ""
Dim bSTR410
bSTR410 = ""
Dim boolean205
settingRepository1.GetAttrInfo "SURFACICSPINDLESPEED", bSTR409, bSTR410, boolean205
'--------------------------------------------------
' Parameter 1 : (String) "SURFACICSPINDLESPEED"
' Parameter 2 : (String) "Default value"
' Parameter 3 : (String) "Unlocked"
' Parameter 4 : (Boolean) False
'--------------------------------------------------

long206 = settingRepository1.GetAttr("SURFACICSPINDLESPEED_Large")
'--------------------------------------------------
' Parameter 1 : (String) "SURFACICSPINDLESPEED_Large"
' Returned value : (Variant) (Long) 1
'--------------------------------------------------

Dim bSTR411
bSTR411 = ""
Dim bSTR412
bSTR412 = ""
Dim boolean206
settingRepository1.GetAttrInfo "SURFACICSPINDLESPEED_Large", bSTR411, bSTR412, boolean206
'--------------------------------------------------
' Parameter 1 : (String) "SURFACICSPINDLESPEED_Large"
' Parameter 2 : (String) "Default value"
' Parameter 3 : (String) "Unlocked"
' Parameter 4 : (Boolean) False
'--------------------------------------------------

long207 = settingRepository1.GetAttr("SURFACICSPINDLESPEED_ExtraLarge")
'--------------------------------------------------
' Parameter 1 : (String) "SURFACICSPINDLESPEED_ExtraLarge"
' Returned value : (Variant) (Long) 1
'--------------------------------------------------

Dim bSTR413
bSTR413 = ""
Dim bSTR414
bSTR414 = ""
Dim boolean207
settingRepository1.GetAttrInfo "SURFACICSPINDLESPEED_ExtraLarge", bSTR413, bSTR414, boolean207
'--------------------------------------------------
' Parameter 1 : (String) "SURFACICSPINDLESPEED_ExtraLarge"
' Parameter 2 : (String) "Default value"
' Parameter 3 : (String) "Unlocked"
' Parameter 4 : (Boolean) False
'--------------------------------------------------

long208 = settingRepository1.GetAttr("SURFACICSPINDLESPEED_Small")
'--------------------------------------------------
' Parameter 1 : (String) "SURFACICSPINDLESPEED_Small"
' Returned value : (Variant) (Long) 1
'--------------------------------------------------

Dim bSTR415
bSTR415 = ""
Dim bSTR416
bSTR416 = ""
Dim boolean208
settingRepository1.GetAttrInfo "SURFACICSPINDLESPEED_Small", bSTR415, bSTR416, boolean208
'--------------------------------------------------
' Parameter 1 : (String) "SURFACICSPINDLESPEED_Small"
' Parameter 2 : (String) "Default value"
' Parameter 3 : (String) "Unlocked"
' Parameter 4 : (Boolean) False
'--------------------------------------------------

long209 = settingRepository1.GetAttr("SURFACICSPINDLESPEED_ExtraSmall")
'--------------------------------------------------
' Parameter 1 : (String) "SURFACICSPINDLESPEED_ExtraSmall"
' Returned value : (Variant) (Long) 1
'--------------------------------------------------

Dim bSTR417
bSTR417 = ""
Dim bSTR418
bSTR418 = ""
Dim boolean209
settingRepository1.GetAttrInfo "SURFACICSPINDLESPEED_ExtraSmall", bSTR417, bSTR418, boolean209
'--------------------------------------------------
' Parameter 1 : (String) "SURFACICSPINDLESPEED_ExtraSmall"
' Parameter 2 : (String) "Default value"
' Parameter 3 : (String) "Unlocked"
' Parameter 4 : (Boolean) False
'--------------------------------------------------

long210 = settingRepository1.GetAttr("SURFACICSPINDLESPEED_Nanometric")
'--------------------------------------------------
' Parameter 1 : (String) "SURFACICSPINDLESPEED_Nanometric"
' Returned value : (Variant) (Long) 1
'--------------------------------------------------

Dim bSTR419
bSTR419 = ""
Dim bSTR420
bSTR420 = ""
Dim boolean210
settingRepository1.GetAttrInfo "SURFACICSPINDLESPEED_Nanometric", bSTR419, bSTR420, boolean210
'--------------------------------------------------
' Parameter 1 : (String) "SURFACICSPINDLESPEED_Nanometric"
' Parameter 2 : (String) "Default value"
' Parameter 3 : (String) "Unlocked"
' Parameter 4 : (Boolean) False
'--------------------------------------------------

long211 = settingRepository1.GetAttr("MOLE")
'--------------------------------------------------
' Parameter 1 : (String) "MOLE"
' Returned value : (Variant) (Long) 1
'--------------------------------------------------

Dim bSTR421
bSTR421 = ""
Dim bSTR422
bSTR422 = ""
Dim boolean211
settingRepository1.GetAttrInfo "MOLE", bSTR421, bSTR422, boolean211
'--------------------------------------------------
' Parameter 1 : (String) "MOLE"
' Parameter 2 : (String) "Default value"
' Parameter 3 : (String) "Unlocked"
' Parameter 4 : (Boolean) False
'--------------------------------------------------

long212 = settingRepository1.GetAttr("MOLE_Large")
'--------------------------------------------------
' Parameter 1 : (String) "MOLE_Large"
' Returned value : (Variant) (Long) 1
'--------------------------------------------------

Dim bSTR423
bSTR423 = ""
Dim bSTR424
bSTR424 = ""
Dim boolean212
settingRepository1.GetAttrInfo "MOLE_Large", bSTR423, bSTR424, boolean212
'--------------------------------------------------
' Parameter 1 : (String) "MOLE_Large"
' Parameter 2 : (String) "Default value"
' Parameter 3 : (String) "Unlocked"
' Parameter 4 : (Boolean) False
'--------------------------------------------------

long213 = settingRepository1.GetAttr("MOLE_ExtraLarge")
'--------------------------------------------------
' Parameter 1 : (String) "MOLE_ExtraLarge"
' Returned value : (Variant) (Long) 1
'--------------------------------------------------

Dim bSTR425
bSTR425 = ""
Dim bSTR426
bSTR426 = ""
Dim boolean213
settingRepository1.GetAttrInfo "MOLE_ExtraLarge", bSTR425, bSTR426, boolean213
'--------------------------------------------------
' Parameter 1 : (String) "MOLE_ExtraLarge"
' Parameter 2 : (String) "Default value"
' Parameter 3 : (String) "Unlocked"
' Parameter 4 : (Boolean) False
'--------------------------------------------------

long214 = settingRepository1.GetAttr("MOLE_Small")
'--------------------------------------------------
' Parameter 1 : (String) "MOLE_Small"
' Returned value : (Variant) (Long) 1
'--------------------------------------------------

Dim bSTR427
bSTR427 = ""
Dim bSTR428
bSTR428 = ""
Dim boolean214
settingRepository1.GetAttrInfo "MOLE_Small", bSTR427, bSTR428, boolean214
'--------------------------------------------------
' Parameter 1 : (String) "MOLE_Small"
' Parameter 2 : (String) "Default value"
' Parameter 3 : (String) "Unlocked"
' Parameter 4 : (Boolean) False
'--------------------------------------------------

long215 = settingRepository1.GetAttr("MOLE_ExtraSmall")
'--------------------------------------------------
' Parameter 1 : (String) "MOLE_ExtraSmall"
' Returned value : (Variant) (Long) 1
'--------------------------------------------------

Dim bSTR429
bSTR429 = ""
Dim bSTR430
bSTR430 = ""
Dim boolean215
settingRepository1.GetAttrInfo "MOLE_ExtraSmall", bSTR429, bSTR430, boolean215
'--------------------------------------------------
' Parameter 1 : (String) "MOLE_ExtraSmall"
' Parameter 2 : (String) "Default value"
' Parameter 3 : (String) "Unlocked"
' Parameter 4 : (Boolean) False
'--------------------------------------------------

long216 = settingRepository1.GetAttr("MOLE_Nanometric")
'--------------------------------------------------
' Parameter 1 : (String) "MOLE_Nanometric"
' Returned value : (Variant) (Long) 1
'--------------------------------------------------

Dim bSTR431
bSTR431 = ""
Dim bSTR432
bSTR432 = ""
Dim boolean216
settingRepository1.GetAttrInfo "MOLE_Nanometric", bSTR431, bSTR432, boolean216
'--------------------------------------------------
' Parameter 1 : (String) "MOLE_Nanometric"
' Parameter 2 : (String) "Default value"
' Parameter 3 : (String) "Unlocked"
' Parameter 4 : (Boolean) False
'--------------------------------------------------

long217 = settingRepository1.GetAttr("HEATTRANSFERRESISTANCE")
'--------------------------------------------------
' Parameter 1 : (String) "HEATTRANSFERRESISTANCE"
' Returned value : (Variant) (Long) 1
'--------------------------------------------------

Dim bSTR433
bSTR433 = ""
Dim bSTR434
bSTR434 = ""
Dim boolean217
settingRepository1.GetAttrInfo "HEATTRANSFERRESISTANCE", bSTR433, bSTR434, boolean217
'--------------------------------------------------
' Parameter 1 : (String) "HEATTRANSFERRESISTANCE"
' Parameter 2 : (String) "Default value"
' Parameter 3 : (String) "Unlocked"
' Parameter 4 : (Boolean) False
'--------------------------------------------------

long218 = settingRepository1.GetAttr("HEATTRANSFERRESISTANCE_Large")
'--------------------------------------------------
' Parameter 1 : (String) "HEATTRANSFERRESISTANCE_Large"
' Returned value : (Variant) (Long) 1
'--------------------------------------------------

Dim bSTR435
bSTR435 = ""
Dim bSTR436
bSTR436 = ""
Dim boolean218
settingRepository1.GetAttrInfo "HEATTRANSFERRESISTANCE_Large", bSTR435, bSTR436, boolean218
'--------------------------------------------------
' Parameter 1 : (String) "HEATTRANSFERRESISTANCE_Large"
' Parameter 2 : (String) "Default value"
' Parameter 3 : (String) "Unlocked"
' Parameter 4 : (Boolean) False
'--------------------------------------------------

long219 = settingRepository1.GetAttr("HEATTRANSFERRESISTANCE_ExtraLarge")
'--------------------------------------------------
' Parameter 1 : (String) "HEATTRANSFERRESISTANCE_ExtraLarge"
' Returned value : (Variant) (Long) 1
'--------------------------------------------------

Dim bSTR437
bSTR437 = ""
Dim bSTR438
bSTR438 = ""
Dim boolean219
settingRepository1.GetAttrInfo "HEATTRANSFERRESISTANCE_ExtraLarge", bSTR437, bSTR438, boolean219
'--------------------------------------------------
' Parameter 1 : (String) "HEATTRANSFERRESISTANCE_ExtraLarge"
' Parameter 2 : (String) "Default value"
' Parameter 3 : (String) "Unlocked"
' Parameter 4 : (Boolean) False
'--------------------------------------------------

long220 = settingRepository1.GetAttr("HEATTRANSFERRESISTANCE_Small")
'--------------------------------------------------
' Parameter 1 : (String) "HEATTRANSFERRESISTANCE_Small"
' Returned value : (Variant) (Long) 1
'--------------------------------------------------

Dim bSTR439
bSTR439 = ""
Dim bSTR440
bSTR440 = ""
Dim boolean220
settingRepository1.GetAttrInfo "HEATTRANSFERRESISTANCE_Small", bSTR439, bSTR440, boolean220
'--------------------------------------------------
' Parameter 1 : (String) "HEATTRANSFERRESISTANCE_Small"
' Parameter 2 : (String) "Default value"
' Parameter 3 : (String) "Unlocked"
' Parameter 4 : (Boolean) False
'--------------------------------------------------

long221 = settingRepository1.GetAttr("HEATTRANSFERRESISTANCE_ExtraSmall")
'--------------------------------------------------
' Parameter 1 : (String) "HEATTRANSFERRESISTANCE_ExtraSmall"
' Returned value : (Variant) (Long) 1
'--------------------------------------------------

Dim bSTR441
bSTR441 = ""
Dim bSTR442
bSTR442 = ""
Dim boolean221
settingRepository1.GetAttrInfo "HEATTRANSFERRESISTANCE_ExtraSmall", bSTR441, bSTR442, boolean221
'--------------------------------------------------
' Parameter 1 : (String) "HEATTRANSFERRESISTANCE_ExtraSmall"
' Parameter 2 : (String) "Default value"
' Parameter 3 : (String) "Unlocked"
' Parameter 4 : (Boolean) False
'--------------------------------------------------

long222 = settingRepository1.GetAttr("HEATTRANSFERRESISTANCE_Nanometric")
'--------------------------------------------------
' Parameter 1 : (String) "HEATTRANSFERRESISTANCE_Nanometric"
' Returned value : (Variant) (Long) 1
'--------------------------------------------------

Dim bSTR443
bSTR443 = ""
Dim bSTR444
bSTR444 = ""
Dim boolean222
settingRepository1.GetAttrInfo "HEATTRANSFERRESISTANCE_Nanometric", bSTR443, bSTR444, boolean222
'--------------------------------------------------
' Parameter 1 : (String) "HEATTRANSFERRESISTANCE_Nanometric"
' Parameter 2 : (String) "Default value"
' Parameter 3 : (String) "Unlocked"
' Parameter 4 : (Boolean) False
'--------------------------------------------------

long223 = settingRepository1.GetAttr("HEATTRANSFER")
'--------------------------------------------------
' Parameter 1 : (String) "HEATTRANSFER"
' Returned value : (Variant) (Long) 1
'--------------------------------------------------

Dim bSTR445
bSTR445 = ""
Dim bSTR446
bSTR446 = ""
Dim boolean223
settingRepository1.GetAttrInfo "HEATTRANSFER", bSTR445, bSTR446, boolean223
'--------------------------------------------------
' Parameter 1 : (String) "HEATTRANSFER"
' Parameter 2 : (String) "Default value"
' Parameter 3 : (String) "Unlocked"
' Parameter 4 : (Boolean) False
'--------------------------------------------------

long224 = settingRepository1.GetAttr("HEATTRANSFER_Large")
'--------------------------------------------------
' Parameter 1 : (String) "HEATTRANSFER_Large"
' Returned value : (Variant) (Long) 1
'--------------------------------------------------

Dim bSTR447
bSTR447 = ""
Dim bSTR448
bSTR448 = ""
Dim boolean224
settingRepository1.GetAttrInfo "HEATTRANSFER_Large", bSTR447, bSTR448, boolean224
'--------------------------------------------------
' Parameter 1 : (String) "HEATTRANSFER_Large"
' Parameter 2 : (String) "Default value"
' Parameter 3 : (String) "Unlocked"
' Parameter 4 : (Boolean) False
'--------------------------------------------------

long225 = settingRepository1.GetAttr("HEATTRANSFER_ExtraLarge")
'--------------------------------------------------
' Parameter 1 : (String) "HEATTRANSFER_ExtraLarge"
' Returned value : (Variant) (Long) 1
'--------------------------------------------------

Dim bSTR449
bSTR449 = ""
Dim bSTR450
bSTR450 = ""
Dim boolean225
settingRepository1.GetAttrInfo "HEATTRANSFER_ExtraLarge", bSTR449, bSTR450, boolean225
'--------------------------------------------------
' Parameter 1 : (String) "HEATTRANSFER_ExtraLarge"
' Parameter 2 : (String) "Default value"
' Parameter 3 : (String) "Unlocked"
' Parameter 4 : (Boolean) False
'--------------------------------------------------

long226 = settingRepository1.GetAttr("HEATTRANSFER_Small")
'--------------------------------------------------
' Parameter 1 : (String) "HEATTRANSFER_Small"
' Returned value : (Variant) (Long) 1
'--------------------------------------------------

Dim bSTR451
bSTR451 = ""
Dim bSTR452
bSTR452 = ""
Dim boolean226
settingRepository1.GetAttrInfo "HEATTRANSFER_Small", bSTR451, bSTR452, boolean226
'--------------------------------------------------
' Parameter 1 : (String) "HEATTRANSFER_Small"
' Parameter 2 : (String) "Default value"
' Parameter 3 : (String) "Unlocked"
' Parameter 4 : (Boolean) False
'--------------------------------------------------

long227 = settingRepository1.GetAttr("HEATTRANSFER_ExtraSmall")
'--------------------------------------------------
' Parameter 1 : (String) "HEATTRANSFER_ExtraSmall"
' Returned value : (Variant) (Long) 1
'--------------------------------------------------

Dim bSTR453
bSTR453 = ""
Dim bSTR454
bSTR454 = ""
Dim boolean227
settingRepository1.GetAttrInfo "HEATTRANSFER_ExtraSmall", bSTR453, bSTR454, boolean227
'--------------------------------------------------
' Parameter 1 : (String) "HEATTRANSFER_ExtraSmall"
' Parameter 2 : (String) "Default value"
' Parameter 3 : (String) "Unlocked"
' Parameter 4 : (Boolean) False
'--------------------------------------------------

long228 = settingRepository1.GetAttr("HEATTRANSFER_Nanometric")
'--------------------------------------------------
' Parameter 1 : (String) "HEATTRANSFER_Nanometric"
' Returned value : (Variant) (Long) 1
'--------------------------------------------------

Dim bSTR455
bSTR455 = ""
Dim bSTR456
bSTR456 = ""
Dim boolean228
settingRepository1.GetAttrInfo "HEATTRANSFER_Nanometric", bSTR455, bSTR456, boolean228
'--------------------------------------------------
' Parameter 1 : (String) "HEATTRANSFER_Nanometric"
' Parameter 2 : (String) "Default value"
' Parameter 3 : (String) "Unlocked"
' Parameter 4 : (Boolean) False
'--------------------------------------------------

long229 = settingRepository1.GetAttr("MOLECULARFLOW")
'--------------------------------------------------
' Parameter 1 : (String) "MOLECULARFLOW"
' Returned value : (Variant) (Long) 1
'--------------------------------------------------

Dim bSTR457
bSTR457 = ""
Dim bSTR458
bSTR458 = ""
Dim boolean229
settingRepository1.GetAttrInfo "MOLECULARFLOW", bSTR457, bSTR458, boolean229
'--------------------------------------------------
' Parameter 1 : (String) "MOLECULARFLOW"
' Parameter 2 : (String) "Default value"
' Parameter 3 : (String) "Unlocked"
' Parameter 4 : (Boolean) False
'--------------------------------------------------

long230 = settingRepository1.GetAttr("MOLECULARFLOW_Large")
'--------------------------------------------------
' Parameter 1 : (String) "MOLECULARFLOW_Large"
' Returned value : (Variant) (Long) 1
'--------------------------------------------------

Dim bSTR459
bSTR459 = ""
Dim bSTR460
bSTR460 = ""
Dim boolean230
settingRepository1.GetAttrInfo "MOLECULARFLOW_Large", bSTR459, bSTR460, boolean230
'--------------------------------------------------
' Parameter 1 : (String) "MOLECULARFLOW_Large"
' Parameter 2 : (String) "Default value"
' Parameter 3 : (String) "Unlocked"
' Parameter 4 : (Boolean) False
'--------------------------------------------------

long231 = settingRepository1.GetAttr("MOLECULARFLOW_ExtraLarge")
'--------------------------------------------------
' Parameter 1 : (String) "MOLECULARFLOW_ExtraLarge"
' Returned value : (Variant) (Long) 1
'--------------------------------------------------

Dim bSTR461
bSTR461 = ""
Dim bSTR462
bSTR462 = ""
Dim boolean231
settingRepository1.GetAttrInfo "MOLECULARFLOW_ExtraLarge", bSTR461, bSTR462, boolean231
'--------------------------------------------------
' Parameter 1 : (String) "MOLECULARFLOW_ExtraLarge"
' Parameter 2 : (String) "Default value"
' Parameter 3 : (String) "Unlocked"
' Parameter 4 : (Boolean) False
'--------------------------------------------------

long232 = settingRepository1.GetAttr("MOLECULARFLOW_Small")
'--------------------------------------------------
' Parameter 1 : (String) "MOLECULARFLOW_Small"
' Returned value : (Variant) (Long) 1
'--------------------------------------------------

Dim bSTR463
bSTR463 = ""
Dim bSTR464
bSTR464 = ""
Dim boolean232
settingRepository1.GetAttrInfo "MOLECULARFLOW_Small", bSTR463, bSTR464, boolean232
'--------------------------------------------------
' Parameter 1 : (String) "MOLECULARFLOW_Small"
' Parameter 2 : (String) "Default value"
' Parameter 3 : (String) "Unlocked"
' Parameter 4 : (Boolean) False
'--------------------------------------------------

long233 = settingRepository1.GetAttr("MOLECULARFLOW_ExtraSmall")
'--------------------------------------------------
' Parameter 1 : (String) "MOLECULARFLOW_ExtraSmall"
' Returned value : (Variant) (Long) 1
'--------------------------------------------------

Dim bSTR465
bSTR465 = ""
Dim bSTR466
bSTR466 = ""
Dim boolean233
settingRepository1.GetAttrInfo "MOLECULARFLOW_ExtraSmall", bSTR465, bSTR466, boolean233
'--------------------------------------------------
' Parameter 1 : (String) "MOLECULARFLOW_ExtraSmall"
' Parameter 2 : (String) "Default value"
' Parameter 3 : (String) "Unlocked"
' Parameter 4 : (Boolean) False
'--------------------------------------------------

long234 = settingRepository1.GetAttr("MOLECULARFLOW_Nanometric")
'--------------------------------------------------
' Parameter 1 : (String) "MOLECULARFLOW_Nanometric"
' Returned value : (Variant) (Long) 1
'--------------------------------------------------

Dim bSTR467
bSTR467 = ""
Dim bSTR468
bSTR468 = ""
Dim boolean234
settingRepository1.GetAttrInfo "MOLECULARFLOW_Nanometric", bSTR467, bSTR468, boolean234
'--------------------------------------------------
' Parameter 1 : (String) "MOLECULARFLOW_Nanometric"
' Parameter 2 : (String) "Default value"
' Parameter 3 : (String) "Unlocked"
' Parameter 4 : (Boolean) False
'--------------------------------------------------

long235 = settingRepository1.GetAttr("MOLECULARDENSITY")
'--------------------------------------------------
' Parameter 1 : (String) "MOLECULARDENSITY"
' Returned value : (Variant) (Long) 1
'--------------------------------------------------

Dim bSTR469
bSTR469 = ""
Dim bSTR470
bSTR470 = ""
Dim boolean235
settingRepository1.GetAttrInfo "MOLECULARDENSITY", bSTR469, bSTR470, boolean235
'--------------------------------------------------
' Parameter 1 : (String) "MOLECULARDENSITY"
' Parameter 2 : (String) "Default value"
' Parameter 3 : (String) "Unlocked"
' Parameter 4 : (Boolean) False
'--------------------------------------------------

long236 = settingRepository1.GetAttr("MOLECULARDENSITY_Large")
'--------------------------------------------------
' Parameter 1 : (String) "MOLECULARDENSITY_Large"
' Returned value : (Variant) (Long) 1
'--------------------------------------------------

Dim bSTR471
bSTR471 = ""
Dim bSTR472
bSTR472 = ""
Dim boolean236
settingRepository1.GetAttrInfo "MOLECULARDENSITY_Large", bSTR471, bSTR472, boolean236
'--------------------------------------------------
' Parameter 1 : (String) "MOLECULARDENSITY_Large"
' Parameter 2 : (String) "Default value"
' Parameter 3 : (String) "Unlocked"
' Parameter 4 : (Boolean) False
'--------------------------------------------------

long237 = settingRepository1.GetAttr("MOLECULARDENSITY_ExtraLarge")
'--------------------------------------------------
' Parameter 1 : (String) "MOLECULARDENSITY_ExtraLarge"
' Returned value : (Variant) (Long) 1
'--------------------------------------------------

Dim bSTR473
bSTR473 = ""
Dim bSTR474
bSTR474 = ""
Dim boolean237
settingRepository1.GetAttrInfo "MOLECULARDENSITY_ExtraLarge", bSTR473, bSTR474, boolean237
'--------------------------------------------------
' Parameter 1 : (String) "MOLECULARDENSITY_ExtraLarge"
' Parameter 2 : (String) "Default value"
' Parameter 3 : (String) "Unlocked"
' Parameter 4 : (Boolean) False
'--------------------------------------------------

long238 = settingRepository1.GetAttr("MOLECULARDENSITY_Small")
'--------------------------------------------------
' Parameter 1 : (String) "MOLECULARDENSITY_Small"
' Returned value : (Variant) (Long) 1
'--------------------------------------------------

Dim bSTR475
bSTR475 = ""
Dim bSTR476
bSTR476 = ""
Dim boolean238
settingRepository1.GetAttrInfo "MOLECULARDENSITY_Small", bSTR475, bSTR476, boolean238
'--------------------------------------------------
' Parameter 1 : (String) "MOLECULARDENSITY_Small"
' Parameter 2 : (String) "Default value"
' Parameter 3 : (String) "Unlocked"
' Parameter 4 : (Boolean) False
'--------------------------------------------------

long239 = settingRepository1.GetAttr("MOLECULARDENSITY_ExtraSmall")
'--------------------------------------------------
' Parameter 1 : (String) "MOLECULARDENSITY_ExtraSmall"
' Returned value : (Variant) (Long) 1
'--------------------------------------------------

Dim bSTR477
bSTR477 = ""
Dim bSTR478
bSTR478 = ""
Dim boolean239
settingRepository1.GetAttrInfo "MOLECULARDENSITY_ExtraSmall", bSTR477, bSTR478, boolean239
'--------------------------------------------------
' Parameter 1 : (String) "MOLECULARDENSITY_ExtraSmall"
' Parameter 2 : (String) "Default value"
' Parameter 3 : (String) "Unlocked"
' Parameter 4 : (Boolean) False
'--------------------------------------------------

long240 = settingRepository1.GetAttr("MOLECULARDENSITY_Nanometric")
'--------------------------------------------------
' Parameter 1 : (String) "MOLECULARDENSITY_Nanometric"
' Returned value : (Variant) (Long) 1
'--------------------------------------------------

Dim bSTR479
bSTR479 = ""
Dim bSTR480
bSTR480 = ""
Dim boolean240
settingRepository1.GetAttrInfo "MOLECULARDENSITY_Nanometric", bSTR479, bSTR480, boolean240
'--------------------------------------------------
' Parameter 1 : (String) "MOLECULARDENSITY_Nanometric"
' Parameter 2 : (String) "Default value"
' Parameter 3 : (String) "Unlocked"
' Parameter 4 : (Boolean) False
'--------------------------------------------------

long241 = settingRepository1.GetAttr("ENTHALPY")
'--------------------------------------------------
' Parameter 1 : (String) "ENTHALPY"
' Returned value : (Variant) (Long) 1
'--------------------------------------------------

Dim bSTR481
bSTR481 = ""
Dim bSTR482
bSTR482 = ""
Dim boolean241
settingRepository1.GetAttrInfo "ENTHALPY", bSTR481, bSTR482, boolean241
'--------------------------------------------------
' Parameter 1 : (String) "ENTHALPY"
' Parameter 2 : (String) "Default value"
' Parameter 3 : (String) "Unlocked"
' Parameter 4 : (Boolean) False
'--------------------------------------------------

long242 = settingRepository1.GetAttr("ENTHALPY_Large")
'--------------------------------------------------
' Parameter 1 : (String) "ENTHALPY_Large"
' Returned value : (Variant) (Long) 1
'--------------------------------------------------

Dim bSTR483
bSTR483 = ""
Dim bSTR484
bSTR484 = ""
Dim boolean242
settingRepository1.GetAttrInfo "ENTHALPY_Large", bSTR483, bSTR484, boolean242
'--------------------------------------------------
' Parameter 1 : (String) "ENTHALPY_Large"
' Parameter 2 : (String) "Default value"
' Parameter 3 : (String) "Unlocked"
' Parameter 4 : (Boolean) False
'--------------------------------------------------

long243 = settingRepository1.GetAttr("ENTHALPY_ExtraLarge")
'--------------------------------------------------
' Parameter 1 : (String) "ENTHALPY_ExtraLarge"
' Returned value : (Variant) (Long) 1
'--------------------------------------------------

Dim bSTR485
bSTR485 = ""
Dim bSTR486
bSTR486 = ""
Dim boolean243
settingRepository1.GetAttrInfo "ENTHALPY_ExtraLarge", bSTR485, bSTR486, boolean243
'--------------------------------------------------
' Parameter 1 : (String) "ENTHALPY_ExtraLarge"
' Parameter 2 : (String) "Default value"
' Parameter 3 : (String) "Unlocked"
' Parameter 4 : (Boolean) False
'--------------------------------------------------

long244 = settingRepository1.GetAttr("ENTHALPY_Small")
'--------------------------------------------------
' Parameter 1 : (String) "ENTHALPY_Small"
' Returned value : (Variant) (Long) 1
'--------------------------------------------------

Dim bSTR487
bSTR487 = ""
Dim bSTR488
bSTR488 = ""
Dim boolean244
settingRepository1.GetAttrInfo "ENTHALPY_Small", bSTR487, bSTR488, boolean244
'--------------------------------------------------
' Parameter 1 : (String) "ENTHALPY_Small"
' Parameter 2 : (String) "Default value"
' Parameter 3 : (String) "Unlocked"
' Parameter 4 : (Boolean) False
'--------------------------------------------------

long245 = settingRepository1.GetAttr("ENTHALPY_ExtraSmall")
'--------------------------------------------------
' Parameter 1 : (String) "ENTHALPY_ExtraSmall"
' Returned value : (Variant) (Long) 1
'--------------------------------------------------

Dim bSTR489
bSTR489 = ""
Dim bSTR490
bSTR490 = ""
Dim boolean245
settingRepository1.GetAttrInfo "ENTHALPY_ExtraSmall", bSTR489, bSTR490, boolean245
'--------------------------------------------------
' Parameter 1 : (String) "ENTHALPY_ExtraSmall"
' Parameter 2 : (String) "Default value"
' Parameter 3 : (String) "Unlocked"
' Parameter 4 : (Boolean) False
'--------------------------------------------------

long246 = settingRepository1.GetAttr("ENTHALPY_Nanometric")
'--------------------------------------------------
' Parameter 1 : (String) "ENTHALPY_Nanometric"
' Returned value : (Variant) (Long) 1
'--------------------------------------------------

Dim bSTR491
bSTR491 = ""
Dim bSTR492
bSTR492 = ""
Dim boolean246
settingRepository1.GetAttrInfo "ENTHALPY_Nanometric", bSTR491, bSTR492, boolean246
'--------------------------------------------------
' Parameter 1 : (String) "ENTHALPY_Nanometric"
' Parameter 2 : (String) "Default value"
' Parameter 3 : (String) "Unlocked"
' Parameter 4 : (Boolean) False
'--------------------------------------------------

long247 = settingRepository1.GetAttr("ENTROPY")
'--------------------------------------------------
' Parameter 1 : (String) "ENTROPY"
' Returned value : (Variant) (Long) 1
'--------------------------------------------------

Dim bSTR493
bSTR493 = ""
Dim bSTR494
bSTR494 = ""
Dim boolean247
settingRepository1.GetAttrInfo "ENTROPY", bSTR493, bSTR494, boolean247
'--------------------------------------------------
' Parameter 1 : (String) "ENTROPY"
' Parameter 2 : (String) "Default value"
' Parameter 3 : (String) "Unlocked"
' Parameter 4 : (Boolean) False
'--------------------------------------------------

long248 = settingRepository1.GetAttr("ENTROPY_Large")
'--------------------------------------------------
' Parameter 1 : (String) "ENTROPY_Large"
' Returned value : (Variant) (Long) 1
'--------------------------------------------------

Dim bSTR495
bSTR495 = ""
Dim bSTR496
bSTR496 = ""
Dim boolean248
settingRepository1.GetAttrInfo "ENTROPY_Large", bSTR495, bSTR496, boolean248
'--------------------------------------------------
' Parameter 1 : (String) "ENTROPY_Large"
' Parameter 2 : (String) "Default value"
' Parameter 3 : (String) "Unlocked"
' Parameter 4 : (Boolean) False
'--------------------------------------------------

long249 = settingRepository1.GetAttr("ENTROPY_ExtraLarge")
'--------------------------------------------------
' Parameter 1 : (String) "ENTROPY_ExtraLarge"
' Returned value : (Variant) (Long) 1
'--------------------------------------------------

Dim bSTR497
bSTR497 = ""
Dim bSTR498
bSTR498 = ""
Dim boolean249
settingRepository1.GetAttrInfo "ENTROPY_ExtraLarge", bSTR497, bSTR498, boolean249
'--------------------------------------------------
' Parameter 1 : (String) "ENTROPY_ExtraLarge"
' Parameter 2 : (String) "Default value"
' Parameter 3 : (String) "Unlocked"
' Parameter 4 : (Boolean) False
'--------------------------------------------------

long250 = settingRepository1.GetAttr("ENTROPY_Small")
'--------------------------------------------------
' Parameter 1 : (String) "ENTROPY_Small"
' Returned value : (Variant) (Long) 1
'--------------------------------------------------

Dim bSTR499
bSTR499 = ""
Dim bSTR500
bSTR500 = ""
Dim boolean250
settingRepository1.GetAttrInfo "ENTROPY_Small", bSTR499, bSTR500, boolean250
'--------------------------------------------------
' Parameter 1 : (String) "ENTROPY_Small"
' Parameter 2 : (String) "Default value"
' Parameter 3 : (String) "Unlocked"
' Parameter 4 : (Boolean) False
'--------------------------------------------------

long251 = settingRepository1.GetAttr("ENTROPY_ExtraSmall")
'--------------------------------------------------
' Parameter 1 : (String) "ENTROPY_ExtraSmall"
' Returned value : (Variant) (Long) 1
'--------------------------------------------------

Dim bSTR501
bSTR501 = ""
Dim bSTR502
bSTR502 = ""
Dim boolean251
settingRepository1.GetAttrInfo "ENTROPY_ExtraSmall", bSTR501, bSTR502, boolean251
'--------------------------------------------------
' Parameter 1 : (String) "ENTROPY_ExtraSmall"
' Parameter 2 : (String) "Default value"
' Parameter 3 : (String) "Unlocked"
' Parameter 4 : (Boolean) False
'--------------------------------------------------

long252 = settingRepository1.GetAttr("ENTROPY_Nanometric")
'--------------------------------------------------
' Parameter 1 : (String) "ENTROPY_Nanometric"
' Returned value : (Variant) (Long) 1
'--------------------------------------------------

Dim bSTR503
bSTR503 = ""
Dim bSTR504
bSTR504 = ""
Dim boolean252
settingRepository1.GetAttrInfo "ENTROPY_Nanometric", bSTR503, bSTR504, boolean252
'--------------------------------------------------
' Parameter 1 : (String) "ENTROPY_Nanometric"
' Parameter 2 : (String) "Default value"
' Parameter 3 : (String) "Unlocked"
' Parameter 4 : (Boolean) False
'--------------------------------------------------

long253 = settingRepository1.GetAttr("MOLECULARENTHALPY")
'--------------------------------------------------
' Parameter 1 : (String) "MOLECULARENTHALPY"
' Returned value : (Variant) (Long) 1
'--------------------------------------------------

Dim bSTR505
bSTR505 = ""
Dim bSTR506
bSTR506 = ""
Dim boolean253
settingRepository1.GetAttrInfo "MOLECULARENTHALPY", bSTR505, bSTR506, boolean253
'--------------------------------------------------
' Parameter 1 : (String) "MOLECULARENTHALPY"
' Parameter 2 : (String) "Default value"
' Parameter 3 : (String) "Unlocked"
' Parameter 4 : (Boolean) False
'--------------------------------------------------

long254 = settingRepository1.GetAttr("MOLECULARENTHALPY_Large")
'--------------------------------------------------
' Parameter 1 : (String) "MOLECULARENTHALPY_Large"
' Returned value : (Variant) (Long) 1
'--------------------------------------------------

Dim bSTR507
bSTR507 = ""
Dim bSTR508
bSTR508 = ""
Dim boolean254
settingRepository1.GetAttrInfo "MOLECULARENTHALPY_Large", bSTR507, bSTR508, boolean254
'--------------------------------------------------
' Parameter 1 : (String) "MOLECULARENTHALPY_Large"
' Parameter 2 : (String) "Default value"
' Parameter 3 : (String) "Unlocked"
' Parameter 4 : (Boolean) False
'--------------------------------------------------

long255 = settingRepository1.GetAttr("MOLECULARENTHALPY_ExtraLarge")
'--------------------------------------------------
' Parameter 1 : (String) "MOLECULARENTHALPY_ExtraLarge"
' Returned value : (Variant) (Long) 1
'--------------------------------------------------

Dim bSTR509
bSTR509 = ""
Dim bSTR510
bSTR510 = ""
Dim boolean255
settingRepository1.GetAttrInfo "MOLECULARENTHALPY_ExtraLarge", bSTR509, bSTR510, boolean255
'--------------------------------------------------
' Parameter 1 : (String) "MOLECULARENTHALPY_ExtraLarge"
' Parameter 2 : (String) "Default value"
' Parameter 3 : (String) "Unlocked"
' Parameter 4 : (Boolean) False
'--------------------------------------------------

long256 = settingRepository1.GetAttr("MOLECULARENTHALPY_Small")
'--------------------------------------------------
' Parameter 1 : (String) "MOLECULARENTHALPY_Small"
' Returned value : (Variant) (Long) 1
'--------------------------------------------------

Dim bSTR511
bSTR511 = ""
Dim bSTR512
bSTR512 = ""
Dim boolean256
settingRepository1.GetAttrInfo "MOLECULARENTHALPY_Small", bSTR511, bSTR512, boolean256
'--------------------------------------------------
' Parameter 1 : (String) "MOLECULARENTHALPY_Small"
' Parameter 2 : (String) "Default value"
' Parameter 3 : (String) "Unlocked"
' Parameter 4 : (Boolean) False
'--------------------------------------------------

long257 = settingRepository1.GetAttr("MOLECULARENTHALPY_ExtraSmall")
'--------------------------------------------------
' Parameter 1 : (String) "MOLECULARENTHALPY_ExtraSmall"
' Returned value : (Variant) (Long) 1
'--------------------------------------------------

Dim bSTR513
bSTR513 = ""
Dim bSTR514
bSTR514 = ""
Dim boolean257
settingRepository1.GetAttrInfo "MOLECULARENTHALPY_ExtraSmall", bSTR513, bSTR514, boolean257
'--------------------------------------------------
' Parameter 1 : (String) "MOLECULARENTHALPY_ExtraSmall"
' Parameter 2 : (String) "Default value"
' Parameter 3 : (String) "Unlocked"
' Parameter 4 : (Boolean) False
'--------------------------------------------------

long258 = settingRepository1.GetAttr("MOLECULARENTHALPY_Nanometric")
'--------------------------------------------------
' Parameter 1 : (String) "MOLECULARENTHALPY_Nanometric"
' Returned value : (Variant) (Long) 1
'--------------------------------------------------

Dim bSTR515
bSTR515 = ""
Dim bSTR516
bSTR516 = ""
Dim boolean258
settingRepository1.GetAttrInfo "MOLECULARENTHALPY_Nanometric", bSTR515, bSTR516, boolean258
'--------------------------------------------------
' Parameter 1 : (String) "MOLECULARENTHALPY_Nanometric"
' Parameter 2 : (String) "Default value"
' Parameter 3 : (String) "Unlocked"
' Parameter 4 : (Boolean) False
'--------------------------------------------------

long259 = settingRepository1.GetAttr("MOLECULARENTROPY")
'--------------------------------------------------
' Parameter 1 : (String) "MOLECULARENTROPY"
' Returned value : (Variant) (Long) 1
'--------------------------------------------------

Dim bSTR517
bSTR517 = ""
Dim bSTR518
bSTR518 = ""
Dim boolean259
settingRepository1.GetAttrInfo "MOLECULARENTROPY", bSTR517, bSTR518, boolean259
'--------------------------------------------------
' Parameter 1 : (String) "MOLECULARENTROPY"
' Parameter 2 : (String) "Default value"
' Parameter 3 : (String) "Unlocked"
' Parameter 4 : (Boolean) False
'--------------------------------------------------

long260 = settingRepository1.GetAttr("MOLECULARENTROPY_Large")
'--------------------------------------------------
' Parameter 1 : (String) "MOLECULARENTROPY_Large"
' Returned value : (Variant) (Long) 1
'--------------------------------------------------

Dim bSTR519
bSTR519 = ""
Dim bSTR520
bSTR520 = ""
Dim boolean260
settingRepository1.GetAttrInfo "MOLECULARENTROPY_Large", bSTR519, bSTR520, boolean260
'--------------------------------------------------
' Parameter 1 : (String) "MOLECULARENTROPY_Large"
' Parameter 2 : (String) "Default value"
' Parameter 3 : (String) "Unlocked"
' Parameter 4 : (Boolean) False
'--------------------------------------------------

long261 = settingRepository1.GetAttr("MOLECULARENTROPY_ExtraLarge")
'--------------------------------------------------
' Parameter 1 : (String) "MOLECULARENTROPY_ExtraLarge"
' Returned value : (Variant) (Long) 1
'--------------------------------------------------

Dim bSTR521
bSTR521 = ""
Dim bSTR522
bSTR522 = ""
Dim boolean261
settingRepository1.GetAttrInfo "MOLECULARENTROPY_ExtraLarge", bSTR521, bSTR522, boolean261
'--------------------------------------------------
' Parameter 1 : (String) "MOLECULARENTROPY_ExtraLarge"
' Parameter 2 : (String) "Default value"
' Parameter 3 : (String) "Unlocked"
' Parameter 4 : (Boolean) False
'--------------------------------------------------

long262 = settingRepository1.GetAttr("MOLECULARENTROPY_Small")
'--------------------------------------------------
' Parameter 1 : (String) "MOLECULARENTROPY_Small"
' Returned value : (Variant) (Long) 1
'--------------------------------------------------

Dim bSTR523
bSTR523 = ""
Dim bSTR524
bSTR524 = ""
Dim boolean262
settingRepository1.GetAttrInfo "MOLECULARENTROPY_Small", bSTR523, bSTR524, boolean262
'--------------------------------------------------
' Parameter 1 : (String) "MOLECULARENTROPY_Small"
' Parameter 2 : (String) "Default value"
' Parameter 3 : (String) "Unlocked"
' Parameter 4 : (Boolean) False
'--------------------------------------------------

long263 = settingRepository1.GetAttr("MOLECULARENTROPY_ExtraSmall")
'--------------------------------------------------
' Parameter 1 : (String) "MOLECULARENTROPY_ExtraSmall"
' Returned value : (Variant) (Long) 1
'--------------------------------------------------

Dim bSTR525
bSTR525 = ""
Dim bSTR526
bSTR526 = ""
Dim boolean263
settingRepository1.GetAttrInfo "MOLECULARENTROPY_ExtraSmall", bSTR525, bSTR526, boolean263
'--------------------------------------------------
' Parameter 1 : (String) "MOLECULARENTROPY_ExtraSmall"
' Parameter 2 : (String) "Default value"
' Parameter 3 : (String) "Unlocked"
' Parameter 4 : (Boolean) False
'--------------------------------------------------

long264 = settingRepository1.GetAttr("MOLECULARENTROPY_Nanometric")
'--------------------------------------------------
' Parameter 1 : (String) "MOLECULARENTROPY_Nanometric"
' Returned value : (Variant) (Long) 1
'--------------------------------------------------

Dim bSTR527
bSTR527 = ""
Dim bSTR528
bSTR528 = ""
Dim boolean264
settingRepository1.GetAttrInfo "MOLECULARENTROPY_Nanometric", bSTR527, bSTR528, boolean264
'--------------------------------------------------
' Parameter 1 : (String) "MOLECULARENTROPY_Nanometric"
' Parameter 2 : (String) "Default value"
' Parameter 3 : (String) "Unlocked"
' Parameter 4 : (Boolean) False
'--------------------------------------------------

long265 = settingRepository1.GetAttr("HEATCAPACITY")
'--------------------------------------------------
' Parameter 1 : (String) "HEATCAPACITY"
' Returned value : (Variant) (Long) 1
'--------------------------------------------------

Dim bSTR529
bSTR529 = ""
Dim bSTR530
bSTR530 = ""
Dim boolean265
settingRepository1.GetAttrInfo "HEATCAPACITY", bSTR529, bSTR530, boolean265
'--------------------------------------------------
' Parameter 1 : (String) "HEATCAPACITY"
' Parameter 2 : (String) "Default value"
' Parameter 3 : (String) "Unlocked"
' Parameter 4 : (Boolean) False
'--------------------------------------------------

long266 = settingRepository1.GetAttr("HEATCAPACITY_Large")
'--------------------------------------------------
' Parameter 1 : (String) "HEATCAPACITY_Large"
' Returned value : (Variant) (Long) 1
'--------------------------------------------------

Dim bSTR531
bSTR531 = ""
Dim bSTR532
bSTR532 = ""
Dim boolean266
settingRepository1.GetAttrInfo "HEATCAPACITY_Large", bSTR531, bSTR532, boolean266
'--------------------------------------------------
' Parameter 1 : (String) "HEATCAPACITY_Large"
' Parameter 2 : (String) "Default value"
' Parameter 3 : (String) "Unlocked"
' Parameter 4 : (Boolean) False
'--------------------------------------------------

long267 = settingRepository1.GetAttr("HEATCAPACITY_ExtraLarge")
'--------------------------------------------------
' Parameter 1 : (String) "HEATCAPACITY_ExtraLarge"
' Returned value : (Variant) (Long) 1
'--------------------------------------------------

Dim bSTR533
bSTR533 = ""
Dim bSTR534
bSTR534 = ""
Dim boolean267
settingRepository1.GetAttrInfo "HEATCAPACITY_ExtraLarge", bSTR533, bSTR534, boolean267
'--------------------------------------------------
' Parameter 1 : (String) "HEATCAPACITY_ExtraLarge"
' Parameter 2 : (String) "Default value"
' Parameter 3 : (String) "Unlocked"
' Parameter 4 : (Boolean) False
'--------------------------------------------------

long268 = settingRepository1.GetAttr("HEATCAPACITY_Small")
'--------------------------------------------------
' Parameter 1 : (String) "HEATCAPACITY_Small"
' Returned value : (Variant) (Long) 1
'--------------------------------------------------

Dim bSTR535
bSTR535 = ""
Dim bSTR536
bSTR536 = ""
Dim boolean268
settingRepository1.GetAttrInfo "HEATCAPACITY_Small", bSTR535, bSTR536, boolean268
'--------------------------------------------------
' Parameter 1 : (String) "HEATCAPACITY_Small"
' Parameter 2 : (String) "Default value"
' Parameter 3 : (String) "Unlocked"
' Parameter 4 : (Boolean) False
'--------------------------------------------------

long269 = settingRepository1.GetAttr("HEATCAPACITY_ExtraSmall")
'--------------------------------------------------
' Parameter 1 : (String) "HEATCAPACITY_ExtraSmall"
' Returned value : (Variant) (Long) 1
'--------------------------------------------------

Dim bSTR537
bSTR537 = ""
Dim bSTR538
bSTR538 = ""
Dim boolean269
settingRepository1.GetAttrInfo "HEATCAPACITY_ExtraSmall", bSTR537, bSTR538, boolean269
'--------------------------------------------------
' Parameter 1 : (String) "HEATCAPACITY_ExtraSmall"
' Parameter 2 : (String) "Default value"
' Parameter 3 : (String) "Unlocked"
' Parameter 4 : (Boolean) False
'--------------------------------------------------

long270 = settingRepository1.GetAttr("HEATCAPACITY_Nanometric")
'--------------------------------------------------
' Parameter 1 : (String) "HEATCAPACITY_Nanometric"
' Returned value : (Variant) (Long) 1
'--------------------------------------------------

Dim bSTR539
bSTR539 = ""
Dim bSTR540
bSTR540 = ""
Dim boolean270
settingRepository1.GetAttrInfo "HEATCAPACITY_Nanometric", bSTR539, bSTR540, boolean270
'--------------------------------------------------
' Parameter 1 : (String) "HEATCAPACITY_Nanometric"
' Parameter 2 : (String) "Default value"
' Parameter 3 : (String) "Unlocked"
' Parameter 4 : (Boolean) False
'--------------------------------------------------

long271 = settingRepository1.GetAttr("DYNAMICVISCOSITY")
'--------------------------------------------------
' Parameter 1 : (String) "DYNAMICVISCOSITY"
' Returned value : (Variant) (Long) 1
'--------------------------------------------------

Dim bSTR541
bSTR541 = ""
Dim bSTR542
bSTR542 = ""
Dim boolean271
settingRepository1.GetAttrInfo "DYNAMICVISCOSITY", bSTR541, bSTR542, boolean271
'--------------------------------------------------
' Parameter 1 : (String) "DYNAMICVISCOSITY"
' Parameter 2 : (String) "Default value"
' Parameter 3 : (String) "Unlocked"
' Parameter 4 : (Boolean) False
'--------------------------------------------------

long272 = settingRepository1.GetAttr("DYNAMICVISCOSITY_Large")
'--------------------------------------------------
' Parameter 1 : (String) "DYNAMICVISCOSITY_Large"
' Returned value : (Variant) (Long) 1
'--------------------------------------------------

Dim bSTR543
bSTR543 = ""
Dim bSTR544
bSTR544 = ""
Dim boolean272
settingRepository1.GetAttrInfo "DYNAMICVISCOSITY_Large", bSTR543, bSTR544, boolean272
'--------------------------------------------------
' Parameter 1 : (String) "DYNAMICVISCOSITY_Large"
' Parameter 2 : (String) "Default value"
' Parameter 3 : (String) "Unlocked"
' Parameter 4 : (Boolean) False
'--------------------------------------------------

long273 = settingRepository1.GetAttr("DYNAMICVISCOSITY_ExtraLarge")
'--------------------------------------------------
' Parameter 1 : (String) "DYNAMICVISCOSITY_ExtraLarge"
' Returned value : (Variant) (Long) 1
'--------------------------------------------------

Dim bSTR545
bSTR545 = ""
Dim bSTR546
bSTR546 = ""
Dim boolean273
settingRepository1.GetAttrInfo "DYNAMICVISCOSITY_ExtraLarge", bSTR545, bSTR546, boolean273
'--------------------------------------------------
' Parameter 1 : (String) "DYNAMICVISCOSITY_ExtraLarge"
' Parameter 2 : (String) "Default value"
' Parameter 3 : (String) "Unlocked"
' Parameter 4 : (Boolean) False
'--------------------------------------------------

long274 = settingRepository1.GetAttr("DYNAMICVISCOSITY_Small")
'--------------------------------------------------
' Parameter 1 : (String) "DYNAMICVISCOSITY_Small"
' Returned value : (Variant) (Long) 1
'--------------------------------------------------

Dim bSTR547
bSTR547 = ""
Dim bSTR548
bSTR548 = ""
Dim boolean274
settingRepository1.GetAttrInfo "DYNAMICVISCOSITY_Small", bSTR547, bSTR548, boolean274
'--------------------------------------------------
' Parameter 1 : (String) "DYNAMICVISCOSITY_Small"
' Parameter 2 : (String) "Default value"
' Parameter 3 : (String) "Unlocked"
' Parameter 4 : (Boolean) False
'--------------------------------------------------

long275 = settingRepository1.GetAttr("DYNAMICVISCOSITY_ExtraSmall")
'--------------------------------------------------
' Parameter 1 : (String) "DYNAMICVISCOSITY_ExtraSmall"
' Returned value : (Variant) (Long) 1
'--------------------------------------------------

Dim bSTR549
bSTR549 = ""
Dim bSTR550
bSTR550 = ""
Dim boolean275
settingRepository1.GetAttrInfo "DYNAMICVISCOSITY_ExtraSmall", bSTR549, bSTR550, boolean275
'--------------------------------------------------
' Parameter 1 : (String) "DYNAMICVISCOSITY_ExtraSmall"
' Parameter 2 : (String) "Default value"
' Parameter 3 : (String) "Unlocked"
' Parameter 4 : (Boolean) False
'--------------------------------------------------

long276 = settingRepository1.GetAttr("DYNAMICVISCOSITY_Nanometric")
'--------------------------------------------------
' Parameter 1 : (String) "DYNAMICVISCOSITY_Nanometric"
' Returned value : (Variant) (Long) 1
'--------------------------------------------------

Dim bSTR551
bSTR551 = ""
Dim bSTR552
bSTR552 = ""
Dim boolean276
settingRepository1.GetAttrInfo "DYNAMICVISCOSITY_Nanometric", bSTR551, bSTR552, boolean276
'--------------------------------------------------
' Parameter 1 : (String) "DYNAMICVISCOSITY_Nanometric"
' Parameter 2 : (String) "Default value"
' Parameter 3 : (String) "Unlocked"
' Parameter 4 : (Boolean) False
'--------------------------------------------------

long277 = settingRepository1.GetAttr("MOLECULARWEIGHT")
'--------------------------------------------------
' Parameter 1 : (String) "MOLECULARWEIGHT"
' Returned value : (Variant) (Long) 1
'--------------------------------------------------

Dim bSTR553
bSTR553 = ""
Dim bSTR554
bSTR554 = ""
Dim boolean277
settingRepository1.GetAttrInfo "MOLECULARWEIGHT", bSTR553, bSTR554, boolean277
'--------------------------------------------------
' Parameter 1 : (String) "MOLECULARWEIGHT"
' Parameter 2 : (String) "Default value"
' Parameter 3 : (String) "Unlocked"
' Parameter 4 : (Boolean) False
'--------------------------------------------------

long278 = settingRepository1.GetAttr("MOLECULARWEIGHT_Large")
'--------------------------------------------------
' Parameter 1 : (String) "MOLECULARWEIGHT_Large"
' Returned value : (Variant) (Long) 1
'--------------------------------------------------

Dim bSTR555
bSTR555 = ""
Dim bSTR556
bSTR556 = ""
Dim boolean278
settingRepository1.GetAttrInfo "MOLECULARWEIGHT_Large", bSTR555, bSTR556, boolean278
'--------------------------------------------------
' Parameter 1 : (String) "MOLECULARWEIGHT_Large"
' Parameter 2 : (String) "Default value"
' Parameter 3 : (String) "Unlocked"
' Parameter 4 : (Boolean) False
'--------------------------------------------------

long279 = settingRepository1.GetAttr("MOLECULARWEIGHT_ExtraLarge")
'--------------------------------------------------
' Parameter 1 : (String) "MOLECULARWEIGHT_ExtraLarge"
' Returned value : (Variant) (Long) 1
'--------------------------------------------------

Dim bSTR557
bSTR557 = ""
Dim bSTR558
bSTR558 = ""
Dim boolean279
settingRepository1.GetAttrInfo "MOLECULARWEIGHT_ExtraLarge", bSTR557, bSTR558, boolean279
'--------------------------------------------------
' Parameter 1 : (String) "MOLECULARWEIGHT_ExtraLarge"
' Parameter 2 : (String) "Default value"
' Parameter 3 : (String) "Unlocked"
' Parameter 4 : (Boolean) False
'--------------------------------------------------

long280 = settingRepository1.GetAttr("MOLECULARWEIGHT_Small")
'--------------------------------------------------
' Parameter 1 : (String) "MOLECULARWEIGHT_Small"
' Returned value : (Variant) (Long) 1
'--------------------------------------------------

Dim bSTR559
bSTR559 = ""
Dim bSTR560
bSTR560 = ""
Dim boolean280
settingRepository1.GetAttrInfo "MOLECULARWEIGHT_Small", bSTR559, bSTR560, boolean280
'--------------------------------------------------
' Parameter 1 : (String) "MOLECULARWEIGHT_Small"
' Parameter 2 : (String) "Default value"
' Parameter 3 : (String) "Unlocked"
' Parameter 4 : (Boolean) False
'--------------------------------------------------

long281 = settingRepository1.GetAttr("MOLECULARWEIGHT_ExtraSmall")
'--------------------------------------------------
' Parameter 1 : (String) "MOLECULARWEIGHT_ExtraSmall"
' Returned value : (Variant) (Long) 1
'--------------------------------------------------

Dim bSTR561
bSTR561 = ""
Dim bSTR562
bSTR562 = ""
Dim boolean281
settingRepository1.GetAttrInfo "MOLECULARWEIGHT_ExtraSmall", bSTR561, bSTR562, boolean281
'--------------------------------------------------
' Parameter 1 : (String) "MOLECULARWEIGHT_ExtraSmall"
' Parameter 2 : (String) "Default value"
' Parameter 3 : (String) "Unlocked"
' Parameter 4 : (Boolean) False
'--------------------------------------------------

long282 = settingRepository1.GetAttr("MOLECULARWEIGHT_Nanometric")
'--------------------------------------------------
' Parameter 1 : (String) "MOLECULARWEIGHT_Nanometric"
' Returned value : (Variant) (Long) 1
'--------------------------------------------------

Dim bSTR563
bSTR563 = ""
Dim bSTR564
bSTR564 = ""
Dim boolean282
settingRepository1.GetAttrInfo "MOLECULARWEIGHT_Nanometric", bSTR563, bSTR564, boolean282
'--------------------------------------------------
' Parameter 1 : (String) "MOLECULARWEIGHT_Nanometric"
' Parameter 2 : (String) "Default value"
' Parameter 3 : (String) "Unlocked"
' Parameter 4 : (Boolean) False
'--------------------------------------------------

long283 = settingRepository1.GetAttr("ABSOLUTEVISCOSITY")
'--------------------------------------------------
' Parameter 1 : (String) "ABSOLUTEVISCOSITY"
' Returned value : (Variant) (Long) 1
'--------------------------------------------------

Dim bSTR565
bSTR565 = ""
Dim bSTR566
bSTR566 = ""
Dim boolean283
settingRepository1.GetAttrInfo "ABSOLUTEVISCOSITY", bSTR565, bSTR566, boolean283
'--------------------------------------------------
' Parameter 1 : (String) "ABSOLUTEVISCOSITY"
' Parameter 2 : (String) "Default value"
' Parameter 3 : (String) "Unlocked"
' Parameter 4 : (Boolean) False
'--------------------------------------------------

long284 = settingRepository1.GetAttr("ABSOLUTEVISCOSITY_Large")
'--------------------------------------------------
' Parameter 1 : (String) "ABSOLUTEVISCOSITY_Large"
' Returned value : (Variant) (Long) 1
'--------------------------------------------------

Dim bSTR567
bSTR567 = ""
Dim bSTR568
bSTR568 = ""
Dim boolean284
settingRepository1.GetAttrInfo "ABSOLUTEVISCOSITY_Large", bSTR567, bSTR568, boolean284
'--------------------------------------------------
' Parameter 1 : (String) "ABSOLUTEVISCOSITY_Large"
' Parameter 2 : (String) "Default value"
' Parameter 3 : (String) "Unlocked"
' Parameter 4 : (Boolean) False
'--------------------------------------------------

long285 = settingRepository1.GetAttr("ABSOLUTEVISCOSITY_ExtraLarge")
'--------------------------------------------------
' Parameter 1 : (String) "ABSOLUTEVISCOSITY_ExtraLarge"
' Returned value : (Variant) (Long) 1
'--------------------------------------------------

Dim bSTR569
bSTR569 = ""
Dim bSTR570
bSTR570 = ""
Dim boolean285
settingRepository1.GetAttrInfo "ABSOLUTEVISCOSITY_ExtraLarge", bSTR569, bSTR570, boolean285
'--------------------------------------------------
' Parameter 1 : (String) "ABSOLUTEVISCOSITY_ExtraLarge"
' Parameter 2 : (String) "Default value"
' Parameter 3 : (String) "Unlocked"
' Parameter 4 : (Boolean) False
'--------------------------------------------------

long286 = settingRepository1.GetAttr("ABSOLUTEVISCOSITY_Small")
'--------------------------------------------------
' Parameter 1 : (String) "ABSOLUTEVISCOSITY_Small"
' Returned value : (Variant) (Long) 1
'--------------------------------------------------

Dim bSTR571
bSTR571 = ""
Dim bSTR572
bSTR572 = ""
Dim boolean286
settingRepository1.GetAttrInfo "ABSOLUTEVISCOSITY_Small", bSTR571, bSTR572, boolean286
'--------------------------------------------------
' Parameter 1 : (String) "ABSOLUTEVISCOSITY_Small"
' Parameter 2 : (String) "Default value"
' Parameter 3 : (String) "Unlocked"
' Parameter 4 : (Boolean) False
'--------------------------------------------------

long287 = settingRepository1.GetAttr("ABSOLUTEVISCOSITY_ExtraSmall")
'--------------------------------------------------
' Parameter 1 : (String) "ABSOLUTEVISCOSITY_ExtraSmall"
' Returned value : (Variant) (Long) 1
'--------------------------------------------------

Dim bSTR573
bSTR573 = ""
Dim bSTR574
bSTR574 = ""
Dim boolean287
settingRepository1.GetAttrInfo "ABSOLUTEVISCOSITY_ExtraSmall", bSTR573, bSTR574, boolean287
'--------------------------------------------------
' Parameter 1 : (String) "ABSOLUTEVISCOSITY_ExtraSmall"
' Parameter 2 : (String) "Default value"
' Parameter 3 : (String) "Unlocked"
' Parameter 4 : (Boolean) False
'--------------------------------------------------

long288 = settingRepository1.GetAttr("ABSOLUTEVISCOSITY_Nanometric")
'--------------------------------------------------
' Parameter 1 : (String) "ABSOLUTEVISCOSITY_Nanometric"
' Returned value : (Variant) (Long) 1
'--------------------------------------------------

Dim bSTR575
bSTR575 = ""
Dim bSTR576
bSTR576 = ""
Dim boolean288
settingRepository1.GetAttrInfo "ABSOLUTEVISCOSITY_Nanometric", bSTR575, bSTR576, boolean288
'--------------------------------------------------
' Parameter 1 : (String) "ABSOLUTEVISCOSITY_Nanometric"
' Parameter 2 : (String) "Default value"
' Parameter 3 : (String) "Unlocked"
' Parameter 4 : (Boolean) False
'--------------------------------------------------

long289 = settingRepository1.GetAttr("KINEMATICVISCOSITY")
'--------------------------------------------------
' Parameter 1 : (String) "KINEMATICVISCOSITY"
' Returned value : (Variant) (Long) 1
'--------------------------------------------------

Dim bSTR577
bSTR577 = ""
Dim bSTR578
bSTR578 = ""
Dim boolean289
settingRepository1.GetAttrInfo "KINEMATICVISCOSITY", bSTR577, bSTR578, boolean289
'--------------------------------------------------
' Parameter 1 : (String) "KINEMATICVISCOSITY"
' Parameter 2 : (String) "Default value"
' Parameter 3 : (String) "Unlocked"
' Parameter 4 : (Boolean) False
'--------------------------------------------------

long290 = settingRepository1.GetAttr("KINEMATICVISCOSITY_Large")
'--------------------------------------------------
' Parameter 1 : (String) "KINEMATICVISCOSITY_Large"
' Returned value : (Variant) (Long) 1
'--------------------------------------------------

Dim bSTR579
bSTR579 = ""
Dim bSTR580
bSTR580 = ""
Dim boolean290
settingRepository1.GetAttrInfo "KINEMATICVISCOSITY_Large", bSTR579, bSTR580, boolean290
'--------------------------------------------------
' Parameter 1 : (String) "KINEMATICVISCOSITY_Large"
' Parameter 2 : (String) "Default value"
' Parameter 3 : (String) "Unlocked"
' Parameter 4 : (Boolean) False
'--------------------------------------------------

long291 = settingRepository1.GetAttr("KINEMATICVISCOSITY_ExtraLarge")
'--------------------------------------------------
' Parameter 1 : (String) "KINEMATICVISCOSITY_ExtraLarge"
' Returned value : (Variant) (Long) 1
'--------------------------------------------------

Dim bSTR581
bSTR581 = ""
Dim bSTR582
bSTR582 = ""
Dim boolean291
settingRepository1.GetAttrInfo "KINEMATICVISCOSITY_ExtraLarge", bSTR581, bSTR582, boolean291
'--------------------------------------------------
' Parameter 1 : (String) "KINEMATICVISCOSITY_ExtraLarge"
' Parameter 2 : (String) "Default value"
' Parameter 3 : (String) "Unlocked"
' Parameter 4 : (Boolean) False
'--------------------------------------------------

long292 = settingRepository1.GetAttr("KINEMATICVISCOSITY_Small")
'--------------------------------------------------
' Parameter 1 : (String) "KINEMATICVISCOSITY_Small"
' Returned value : (Variant) (Long) 1
'--------------------------------------------------

Dim bSTR583
bSTR583 = ""
Dim bSTR584
bSTR584 = ""
Dim boolean292
settingRepository1.GetAttrInfo "KINEMATICVISCOSITY_Small", bSTR583, bSTR584, boolean292
'--------------------------------------------------
' Parameter 1 : (String) "KINEMATICVISCOSITY_Small"
' Parameter 2 : (String) "Default value"
' Parameter 3 : (String) "Unlocked"
' Parameter 4 : (Boolean) False
'--------------------------------------------------

long293 = settingRepository1.GetAttr("KINEMATICVISCOSITY_ExtraSmall")
'--------------------------------------------------
' Parameter 1 : (String) "KINEMATICVISCOSITY_ExtraSmall"
' Returned value : (Variant) (Long) 1
'--------------------------------------------------

Dim bSTR585
bSTR585 = ""
Dim bSTR586
bSTR586 = ""
Dim boolean293
settingRepository1.GetAttrInfo "KINEMATICVISCOSITY_ExtraSmall", bSTR585, bSTR586, boolean293
'--------------------------------------------------
' Parameter 1 : (String) "KINEMATICVISCOSITY_ExtraSmall"
' Parameter 2 : (String) "Default value"
' Parameter 3 : (String) "Unlocked"
' Parameter 4 : (Boolean) False
'--------------------------------------------------

long294 = settingRepository1.GetAttr("KINEMATICVISCOSITY_Nanometric")
'--------------------------------------------------
' Parameter 1 : (String) "KINEMATICVISCOSITY_Nanometric"
' Returned value : (Variant) (Long) 1
'--------------------------------------------------

Dim bSTR587
bSTR587 = ""
Dim bSTR588
bSTR588 = ""
Dim boolean294
settingRepository1.GetAttrInfo "KINEMATICVISCOSITY_Nanometric", bSTR587, bSTR588, boolean294
'--------------------------------------------------
' Parameter 1 : (String) "KINEMATICVISCOSITY_Nanometric"
' Parameter 2 : (String) "Default value"
' Parameter 3 : (String) "Unlocked"
' Parameter 4 : (Boolean) False
'--------------------------------------------------

long295 = settingRepository1.GetAttr("MASSICFLOW")
'--------------------------------------------------
' Parameter 1 : (String) "MASSICFLOW"
' Returned value : (Variant) (Long) 1
'--------------------------------------------------

Dim bSTR589
bSTR589 = ""
Dim bSTR590
bSTR590 = ""
Dim boolean295
settingRepository1.GetAttrInfo "MASSICFLOW", bSTR589, bSTR590, boolean295
'--------------------------------------------------
' Parameter 1 : (String) "MASSICFLOW"
' Parameter 2 : (String) "Default value"
' Parameter 3 : (String) "Unlocked"
' Parameter 4 : (Boolean) False
'--------------------------------------------------

long296 = settingRepository1.GetAttr("MASSICFLOW_Large")
'--------------------------------------------------
' Parameter 1 : (String) "MASSICFLOW_Large"
' Returned value : (Variant) (Long) 1
'--------------------------------------------------

Dim bSTR591
bSTR591 = ""
Dim bSTR592
bSTR592 = ""
Dim boolean296
settingRepository1.GetAttrInfo "MASSICFLOW_Large", bSTR591, bSTR592, boolean296
'--------------------------------------------------
' Parameter 1 : (String) "MASSICFLOW_Large"
' Parameter 2 : (String) "Default value"
' Parameter 3 : (String) "Unlocked"
' Parameter 4 : (Boolean) False
'--------------------------------------------------

long297 = settingRepository1.GetAttr("MASSICFLOW_ExtraLarge")
'--------------------------------------------------
' Parameter 1 : (String) "MASSICFLOW_ExtraLarge"
' Returned value : (Variant) (Long) 1
'--------------------------------------------------

Dim bSTR593
bSTR593 = ""
Dim bSTR594
bSTR594 = ""
Dim boolean297
settingRepository1.GetAttrInfo "MASSICFLOW_ExtraLarge", bSTR593, bSTR594, boolean297
'--------------------------------------------------
' Parameter 1 : (String) "MASSICFLOW_ExtraLarge"
' Parameter 2 : (String) "Default value"
' Parameter 3 : (String) "Unlocked"
' Parameter 4 : (Boolean) False
'--------------------------------------------------

long298 = settingRepository1.GetAttr("MASSICFLOW_Small")
'--------------------------------------------------
' Parameter 1 : (String) "MASSICFLOW_Small"
' Returned value : (Variant) (Long) 1
'--------------------------------------------------

Dim bSTR595
bSTR595 = ""
Dim bSTR596
bSTR596 = ""
Dim boolean298
settingRepository1.GetAttrInfo "MASSICFLOW_Small", bSTR595, bSTR596, boolean298
'--------------------------------------------------
' Parameter 1 : (String) "MASSICFLOW_Small"
' Parameter 2 : (String) "Default value"
' Parameter 3 : (String) "Unlocked"
' Parameter 4 : (Boolean) False
'--------------------------------------------------

long299 = settingRepository1.GetAttr("MASSICFLOW_ExtraSmall")
'--------------------------------------------------
' Parameter 1 : (String) "MASSICFLOW_ExtraSmall"
' Returned value : (Variant) (Long) 1
'--------------------------------------------------

Dim bSTR597
bSTR597 = ""
Dim bSTR598
bSTR598 = ""
Dim boolean299
settingRepository1.GetAttrInfo "MASSICFLOW_ExtraSmall", bSTR597, bSTR598, boolean299
'--------------------------------------------------
' Parameter 1 : (String) "MASSICFLOW_ExtraSmall"
' Parameter 2 : (String) "Default value"
' Parameter 3 : (String) "Unlocked"
' Parameter 4 : (Boolean) False
'--------------------------------------------------

long300 = settingRepository1.GetAttr("MASSICFLOW_Nanometric")
'--------------------------------------------------
' Parameter 1 : (String) "MASSICFLOW_Nanometric"
' Returned value : (Variant) (Long) 1
'--------------------------------------------------

Dim bSTR599
bSTR599 = ""
Dim bSTR600
bSTR600 = ""
Dim boolean300
settingRepository1.GetAttrInfo "MASSICFLOW_Nanometric", bSTR599, bSTR600, boolean300
'--------------------------------------------------
' Parameter 1 : (String) "MASSICFLOW_Nanometric"
' Parameter 2 : (String) "Default value"
' Parameter 3 : (String) "Unlocked"
' Parameter 4 : (Boolean) False
'--------------------------------------------------

long301 = settingRepository1.GetAttr("THERMALCONDUCTIVITY")
'--------------------------------------------------
' Parameter 1 : (String) "THERMALCONDUCTIVITY"
' Returned value : (Variant) (Long) 1
'--------------------------------------------------

Dim bSTR601
bSTR601 = ""
Dim bSTR602
bSTR602 = ""
Dim boolean301
settingRepository1.GetAttrInfo "THERMALCONDUCTIVITY", bSTR601, bSTR602, boolean301
'--------------------------------------------------
' Parameter 1 : (String) "THERMALCONDUCTIVITY"
' Parameter 2 : (String) "Default value"
' Parameter 3 : (String) "Unlocked"
' Parameter 4 : (Boolean) False
'--------------------------------------------------

long302 = settingRepository1.GetAttr("THERMALCONDUCTIVITY_Large")
'--------------------------------------------------
' Parameter 1 : (String) "THERMALCONDUCTIVITY_Large"
' Returned value : (Variant) (Long) 1
'--------------------------------------------------

Dim bSTR603
bSTR603 = ""
Dim bSTR604
bSTR604 = ""
Dim boolean302
settingRepository1.GetAttrInfo "THERMALCONDUCTIVITY_Large", bSTR603, bSTR604, boolean302
'--------------------------------------------------
' Parameter 1 : (String) "THERMALCONDUCTIVITY_Large"
' Parameter 2 : (String) "Default value"
' Parameter 3 : (String) "Unlocked"
' Parameter 4 : (Boolean) False
'--------------------------------------------------

long303 = settingRepository1.GetAttr("THERMALCONDUCTIVITY_ExtraLarge")
'--------------------------------------------------
' Parameter 1 : (String) "THERMALCONDUCTIVITY_ExtraLarge"
' Returned value : (Variant) (Long) 1
'--------------------------------------------------

Dim bSTR605
bSTR605 = ""
Dim bSTR606
bSTR606 = ""
Dim boolean303
settingRepository1.GetAttrInfo "THERMALCONDUCTIVITY_ExtraLarge", bSTR605, bSTR606, boolean303
'--------------------------------------------------
' Parameter 1 : (String) "THERMALCONDUCTIVITY_ExtraLarge"
' Parameter 2 : (String) "Default value"
' Parameter 3 : (String) "Unlocked"
' Parameter 4 : (Boolean) False
'--------------------------------------------------

long304 = settingRepository1.GetAttr("THERMALCONDUCTIVITY_Small")
'--------------------------------------------------
' Parameter 1 : (String) "THERMALCONDUCTIVITY_Small"
' Returned value : (Variant) (Long) 1
'--------------------------------------------------

Dim bSTR607
bSTR607 = ""
Dim bSTR608
bSTR608 = ""
Dim boolean304
settingRepository1.GetAttrInfo "THERMALCONDUCTIVITY_Small", bSTR607, bSTR608, boolean304
'--------------------------------------------------
' Parameter 1 : (String) "THERMALCONDUCTIVITY_Small"
' Parameter 2 : (String) "Default value"
' Parameter 3 : (String) "Unlocked"
' Parameter 4 : (Boolean) False
'--------------------------------------------------

long305 = settingRepository1.GetAttr("THERMALCONDUCTIVITY_ExtraSmall")
'--------------------------------------------------
' Parameter 1 : (String) "THERMALCONDUCTIVITY_ExtraSmall"
' Returned value : (Variant) (Long) 1
'--------------------------------------------------

Dim bSTR609
bSTR609 = ""
Dim bSTR610
bSTR610 = ""
Dim boolean305
settingRepository1.GetAttrInfo "THERMALCONDUCTIVITY_ExtraSmall", bSTR609, bSTR610, boolean305
'--------------------------------------------------
' Parameter 1 : (String) "THERMALCONDUCTIVITY_ExtraSmall"
' Parameter 2 : (String) "Default value"
' Parameter 3 : (String) "Unlocked"
' Parameter 4 : (Boolean) False
'--------------------------------------------------

long306 = settingRepository1.GetAttr("THERMALCONDUCTIVITY_Nanometric")
'--------------------------------------------------
' Parameter 1 : (String) "THERMALCONDUCTIVITY_Nanometric"
' Returned value : (Variant) (Long) 1
'--------------------------------------------------

Dim bSTR611
bSTR611 = ""
Dim bSTR612
bSTR612 = ""
Dim boolean306
settingRepository1.GetAttrInfo "THERMALCONDUCTIVITY_Nanometric", bSTR611, bSTR612, boolean306
'--------------------------------------------------
' Parameter 1 : (String) "THERMALCONDUCTIVITY_Nanometric"
' Parameter 2 : (String) "Default value"
' Parameter 3 : (String) "Unlocked"
' Parameter 4 : (Boolean) False
'--------------------------------------------------

long307 = settingRepository1.GetAttr("RPM")
'--------------------------------------------------
' Parameter 1 : (String) "RPM"
' Returned value : (Variant) (Long) 1
'--------------------------------------------------

Dim bSTR613
bSTR613 = ""
Dim bSTR614
bSTR614 = ""
Dim boolean307
settingRepository1.GetAttrInfo "RPM", bSTR613, bSTR614, boolean307
'--------------------------------------------------
' Parameter 1 : (String) "RPM"
' Parameter 2 : (String) "Default value"
' Parameter 3 : (String) "Unlocked"
' Parameter 4 : (Boolean) False
'--------------------------------------------------

long308 = settingRepository1.GetAttr("RPM_Large")
'--------------------------------------------------
' Parameter 1 : (String) "RPM_Large"
' Returned value : (Variant) (Long) 1
'--------------------------------------------------

Dim bSTR615
bSTR615 = ""
Dim bSTR616
bSTR616 = ""
Dim boolean308
settingRepository1.GetAttrInfo "RPM_Large", bSTR615, bSTR616, boolean308
'--------------------------------------------------
' Parameter 1 : (String) "RPM_Large"
' Parameter 2 : (String) "Default value"
' Parameter 3 : (String) "Unlocked"
' Parameter 4 : (Boolean) False
'--------------------------------------------------

long309 = settingRepository1.GetAttr("RPM_ExtraLarge")
'--------------------------------------------------
' Parameter 1 : (String) "RPM_ExtraLarge"
' Returned value : (Variant) (Long) 1
'--------------------------------------------------

Dim bSTR617
bSTR617 = ""
Dim bSTR618
bSTR618 = ""
Dim boolean309
settingRepository1.GetAttrInfo "RPM_ExtraLarge", bSTR617, bSTR618, boolean309
'--------------------------------------------------
' Parameter 1 : (String) "RPM_ExtraLarge"
' Parameter 2 : (String) "Default value"
' Parameter 3 : (String) "Unlocked"
' Parameter 4 : (Boolean) False
'--------------------------------------------------

long310 = settingRepository1.GetAttr("RPM_Small")
'--------------------------------------------------
' Parameter 1 : (String) "RPM_Small"
' Returned value : (Variant) (Long) 1
'--------------------------------------------------

Dim bSTR619
bSTR619 = ""
Dim bSTR620
bSTR620 = ""
Dim boolean310
settingRepository1.GetAttrInfo "RPM_Small", bSTR619, bSTR620, boolean310
'--------------------------------------------------
' Parameter 1 : (String) "RPM_Small"
' Parameter 2 : (String) "Default value"
' Parameter 3 : (String) "Unlocked"
' Parameter 4 : (Boolean) False
'--------------------------------------------------

long311 = settingRepository1.GetAttr("RPM_ExtraSmall")
'--------------------------------------------------
' Parameter 1 : (String) "RPM_ExtraSmall"
' Returned value : (Variant) (Long) 1
'--------------------------------------------------

Dim bSTR621
bSTR621 = ""
Dim bSTR622
bSTR622 = ""
Dim boolean311
settingRepository1.GetAttrInfo "RPM_ExtraSmall", bSTR621, bSTR622, boolean311
'--------------------------------------------------
' Parameter 1 : (String) "RPM_ExtraSmall"
' Parameter 2 : (String) "Default value"
' Parameter 3 : (String) "Unlocked"
' Parameter 4 : (Boolean) False
'--------------------------------------------------

long312 = settingRepository1.GetAttr("RPM_Nanometric")
'--------------------------------------------------
' Parameter 1 : (String) "RPM_Nanometric"
' Returned value : (Variant) (Long) 1
'--------------------------------------------------

Dim bSTR623
bSTR623 = ""
Dim bSTR624
bSTR624 = ""
Dim boolean312
settingRepository1.GetAttrInfo "RPM_Nanometric", bSTR623, bSTR624, boolean312
'--------------------------------------------------
' Parameter 1 : (String) "RPM_Nanometric"
' Parameter 2 : (String) "Default value"
' Parameter 3 : (String) "Unlocked"
' Parameter 4 : (Boolean) False
'--------------------------------------------------

long313 = settingRepository1.GetAttr("VELOCITY_OVER_FORCE")
'--------------------------------------------------
' Parameter 1 : (String) "VELOCITY_OVER_FORCE"
' Returned value : (Variant) (Long) 1
'--------------------------------------------------

Dim bSTR625
bSTR625 = ""
Dim bSTR626
bSTR626 = ""
Dim boolean313
settingRepository1.GetAttrInfo "VELOCITY_OVER_FORCE", bSTR625, bSTR626, boolean313
'--------------------------------------------------
' Parameter 1 : (String) "VELOCITY_OVER_FORCE"
' Parameter 2 : (String) "Default value"
' Parameter 3 : (String) "Unlocked"
' Parameter 4 : (Boolean) False
'--------------------------------------------------

long314 = settingRepository1.GetAttr("VELOCITY_OVER_FORCE_Large")
'--------------------------------------------------
' Parameter 1 : (String) "VELOCITY_OVER_FORCE_Large"
' Returned value : (Variant) (Long) 1
'--------------------------------------------------

Dim bSTR627
bSTR627 = ""
Dim bSTR628
bSTR628 = ""
Dim boolean314
settingRepository1.GetAttrInfo "VELOCITY_OVER_FORCE_Large", bSTR627, bSTR628, boolean314
'--------------------------------------------------
' Parameter 1 : (String) "VELOCITY_OVER_FORCE_Large"
' Parameter 2 : (String) "Default value"
' Parameter 3 : (String) "Unlocked"
' Parameter 4 : (Boolean) False
'--------------------------------------------------

long315 = settingRepository1.GetAttr("VELOCITY_OVER_FORCE_ExtraLarge")
'--------------------------------------------------
' Parameter 1 : (String) "VELOCITY_OVER_FORCE_ExtraLarge"
' Returned value : (Variant) (Long) 1
'--------------------------------------------------

Dim bSTR629
bSTR629 = ""
Dim bSTR630
bSTR630 = ""
Dim boolean315
settingRepository1.GetAttrInfo "VELOCITY_OVER_FORCE_ExtraLarge", bSTR629, bSTR630, boolean315
'--------------------------------------------------
' Parameter 1 : (String) "VELOCITY_OVER_FORCE_ExtraLarge"
' Parameter 2 : (String) "Default value"
' Parameter 3 : (String) "Unlocked"
' Parameter 4 : (Boolean) False
'--------------------------------------------------

long316 = settingRepository1.GetAttr("VELOCITY_OVER_FORCE_Small")
'--------------------------------------------------
' Parameter 1 : (String) "VELOCITY_OVER_FORCE_Small"
' Returned value : (Variant) (Long) 1
'--------------------------------------------------

Dim bSTR631
bSTR631 = ""
Dim bSTR632
bSTR632 = ""
Dim boolean316
settingRepository1.GetAttrInfo "VELOCITY_OVER_FORCE_Small", bSTR631, bSTR632, boolean316
'--------------------------------------------------
' Parameter 1 : (String) "VELOCITY_OVER_FORCE_Small"
' Parameter 2 : (String) "Default value"
' Parameter 3 : (String) "Unlocked"
' Parameter 4 : (Boolean) False
'--------------------------------------------------

long317 = settingRepository1.GetAttr("VELOCITY_OVER_FORCE_ExtraSmall")
'--------------------------------------------------
' Parameter 1 : (String) "VELOCITY_OVER_FORCE_ExtraSmall"
' Returned value : (Variant) (Long) 1
'--------------------------------------------------

Dim bSTR633
bSTR633 = ""
Dim bSTR634
bSTR634 = ""
Dim boolean317
settingRepository1.GetAttrInfo "VELOCITY_OVER_FORCE_ExtraSmall", bSTR633, bSTR634, boolean317
'--------------------------------------------------
' Parameter 1 : (String) "VELOCITY_OVER_FORCE_ExtraSmall"
' Parameter 2 : (String) "Default value"
' Parameter 3 : (String) "Unlocked"
' Parameter 4 : (Boolean) False
'--------------------------------------------------

long318 = settingRepository1.GetAttr("VELOCITY_OVER_FORCE_Nanometric")
'--------------------------------------------------
' Parameter 1 : (String) "VELOCITY_OVER_FORCE_Nanometric"
' Returned value : (Variant) (Long) 1
'--------------------------------------------------

Dim bSTR635
bSTR635 = ""
Dim bSTR636
bSTR636 = ""
Dim boolean318
settingRepository1.GetAttrInfo "VELOCITY_OVER_FORCE_Nanometric", bSTR635, bSTR636, boolean318
'--------------------------------------------------
' Parameter 1 : (String) "VELOCITY_OVER_FORCE_Nanometric"
' Parameter 2 : (String) "Default value"
' Parameter 3 : (String) "Unlocked"
' Parameter 4 : (Boolean) False
'--------------------------------------------------

long319 = settingRepository1.GetAttr("ACCELERATION_OVER_FORCE")
'--------------------------------------------------
' Parameter 1 : (String) "ACCELERATION_OVER_FORCE"
' Returned value : (Variant) (Long) 1
'--------------------------------------------------

Dim bSTR637
bSTR637 = ""
Dim bSTR638
bSTR638 = ""
Dim boolean319
settingRepository1.GetAttrInfo "ACCELERATION_OVER_FORCE", bSTR637, bSTR638, boolean319
'--------------------------------------------------
' Parameter 1 : (String) "ACCELERATION_OVER_FORCE"
' Parameter 2 : (String) "Default value"
' Parameter 3 : (String) "Unlocked"
' Parameter 4 : (Boolean) False
'--------------------------------------------------

long320 = settingRepository1.GetAttr("ACCELERATION_OVER_FORCE_Large")
'--------------------------------------------------
' Parameter 1 : (String) "ACCELERATION_OVER_FORCE_Large"
' Returned value : (Variant) (Long) 1
'--------------------------------------------------

Dim bSTR639
bSTR639 = ""
Dim bSTR640
bSTR640 = ""
Dim boolean320
settingRepository1.GetAttrInfo "ACCELERATION_OVER_FORCE_Large", bSTR639, bSTR640, boolean320
'--------------------------------------------------
' Parameter 1 : (String) "ACCELERATION_OVER_FORCE_Large"
' Parameter 2 : (String) "Default value"
' Parameter 3 : (String) "Unlocked"
' Parameter 4 : (Boolean) False
'--------------------------------------------------

long321 = settingRepository1.GetAttr("ACCELERATION_OVER_FORCE_ExtraLarge")
'--------------------------------------------------
' Parameter 1 : (String) "ACCELERATION_OVER_FORCE_ExtraLarge"
' Returned value : (Variant) (Long) 1
'--------------------------------------------------

Dim bSTR641
bSTR641 = ""
Dim bSTR642
bSTR642 = ""
Dim boolean321
settingRepository1.GetAttrInfo "ACCELERATION_OVER_FORCE_ExtraLarge", bSTR641, bSTR642, boolean321
'--------------------------------------------------
' Parameter 1 : (String) "ACCELERATION_OVER_FORCE_ExtraLarge"
' Parameter 2 : (String) "Default value"
' Parameter 3 : (String) "Unlocked"
' Parameter 4 : (Boolean) False
'--------------------------------------------------

long322 = settingRepository1.GetAttr("ACCELERATION_OVER_FORCE_Small")
'--------------------------------------------------
' Parameter 1 : (String) "ACCELERATION_OVER_FORCE_Small"
' Returned value : (Variant) (Long) 1
'--------------------------------------------------

Dim bSTR643
bSTR643 = ""
Dim bSTR644
bSTR644 = ""
Dim boolean322
settingRepository1.GetAttrInfo "ACCELERATION_OVER_FORCE_Small", bSTR643, bSTR644, boolean322
'--------------------------------------------------
' Parameter 1 : (String) "ACCELERATION_OVER_FORCE_Small"
' Parameter 2 : (String) "Default value"
' Parameter 3 : (String) "Unlocked"
' Parameter 4 : (Boolean) False
'--------------------------------------------------

long323 = settingRepository1.GetAttr("ACCELERATION_OVER_FORCE_ExtraSmall")
'--------------------------------------------------
' Parameter 1 : (String) "ACCELERATION_OVER_FORCE_ExtraSmall"
' Returned value : (Variant) (Long) 1
'--------------------------------------------------

Dim bSTR645
bSTR645 = ""
Dim bSTR646
bSTR646 = ""
Dim boolean323
settingRepository1.GetAttrInfo "ACCELERATION_OVER_FORCE_ExtraSmall", bSTR645, bSTR646, boolean323
'--------------------------------------------------
' Parameter 1 : (String) "ACCELERATION_OVER_FORCE_ExtraSmall"
' Parameter 2 : (String) "Default value"
' Parameter 3 : (String) "Unlocked"
' Parameter 4 : (Boolean) False
'--------------------------------------------------

long324 = settingRepository1.GetAttr("ACCELERATION_OVER_FORCE_Nanometric")
'--------------------------------------------------
' Parameter 1 : (String) "ACCELERATION_OVER_FORCE_Nanometric"
' Returned value : (Variant) (Long) 1
'--------------------------------------------------

Dim bSTR647
bSTR647 = ""
Dim bSTR648
bSTR648 = ""
Dim boolean324
settingRepository1.GetAttrInfo "ACCELERATION_OVER_FORCE_Nanometric", bSTR647, bSTR648, boolean324
'--------------------------------------------------
' Parameter 1 : (String) "ACCELERATION_OVER_FORCE_Nanometric"
' Parameter 2 : (String) "Default value"
' Parameter 3 : (String) "Unlocked"
' Parameter 4 : (Boolean) False
'--------------------------------------------------

long325 = settingRepository1.GetAttr("PRESSURE_OVER_FORCE")
'--------------------------------------------------
' Parameter 1 : (String) "PRESSURE_OVER_FORCE"
' Returned value : (Variant) (Long) 1
'--------------------------------------------------

Dim bSTR649
bSTR649 = ""
Dim bSTR650
bSTR650 = ""
Dim boolean325
settingRepository1.GetAttrInfo "PRESSURE_OVER_FORCE", bSTR649, bSTR650, boolean325
'--------------------------------------------------
' Parameter 1 : (String) "PRESSURE_OVER_FORCE"
' Parameter 2 : (String) "Default value"
' Parameter 3 : (String) "Unlocked"
' Parameter 4 : (Boolean) False
'--------------------------------------------------

long326 = settingRepository1.GetAttr("PRESSURE_OVER_FORCE_Large")
'--------------------------------------------------
' Parameter 1 : (String) "PRESSURE_OVER_FORCE_Large"
' Returned value : (Variant) (Long) 1
'--------------------------------------------------

Dim bSTR651
bSTR651 = ""
Dim bSTR652
bSTR652 = ""
Dim boolean326
settingRepository1.GetAttrInfo "PRESSURE_OVER_FORCE_Large", bSTR651, bSTR652, boolean326
'--------------------------------------------------
' Parameter 1 : (String) "PRESSURE_OVER_FORCE_Large"
' Parameter 2 : (String) "Default value"
' Parameter 3 : (String) "Unlocked"
' Parameter 4 : (Boolean) False
'--------------------------------------------------

long327 = settingRepository1.GetAttr("PRESSURE_OVER_FORCE_ExtraLarge")
'--------------------------------------------------
' Parameter 1 : (String) "PRESSURE_OVER_FORCE_ExtraLarge"
' Returned value : (Variant) (Long) 1
'--------------------------------------------------

Dim bSTR653
bSTR653 = ""
Dim bSTR654
bSTR654 = ""
Dim boolean327
settingRepository1.GetAttrInfo "PRESSURE_OVER_FORCE_ExtraLarge", bSTR653, bSTR654, boolean327
'--------------------------------------------------
' Parameter 1 : (String) "PRESSURE_OVER_FORCE_ExtraLarge"
' Parameter 2 : (String) "Default value"
' Parameter 3 : (String) "Unlocked"
' Parameter 4 : (Boolean) False
'--------------------------------------------------

long328 = settingRepository1.GetAttr("PRESSURE_OVER_FORCE_Small")
'--------------------------------------------------
' Parameter 1 : (String) "PRESSURE_OVER_FORCE_Small"
' Returned value : (Variant) (Long) 1
'--------------------------------------------------

Dim bSTR655
bSTR655 = ""
Dim bSTR656
bSTR656 = ""
Dim boolean328
settingRepository1.GetAttrInfo "PRESSURE_OVER_FORCE_Small", bSTR655, bSTR656, boolean328
'--------------------------------------------------
' Parameter 1 : (String) "PRESSURE_OVER_FORCE_Small"
' Parameter 2 : (String) "Default value"
' Parameter 3 : (String) "Unlocked"
' Parameter 4 : (Boolean) False
'--------------------------------------------------

long329 = settingRepository1.GetAttr("PRESSURE_OVER_FORCE_ExtraSmall")
'--------------------------------------------------
' Parameter 1 : (String) "PRESSURE_OVER_FORCE_ExtraSmall"
' Returned value : (Variant) (Long) 1
'--------------------------------------------------

Dim bSTR657
bSTR657 = ""
Dim bSTR658
bSTR658 = ""
Dim boolean329
settingRepository1.GetAttrInfo "PRESSURE_OVER_FORCE_ExtraSmall", bSTR657, bSTR658, boolean329
'--------------------------------------------------
' Parameter 1 : (String) "PRESSURE_OVER_FORCE_ExtraSmall"
' Parameter 2 : (String) "Default value"
' Parameter 3 : (String) "Unlocked"
' Parameter 4 : (Boolean) False
'--------------------------------------------------

long330 = settingRepository1.GetAttr("PRESSURE_OVER_FORCE_Nanometric")
'--------------------------------------------------
' Parameter 1 : (String) "PRESSURE_OVER_FORCE_Nanometric"
' Returned value : (Variant) (Long) 1
'--------------------------------------------------

Dim bSTR659
bSTR659 = ""
Dim bSTR660
bSTR660 = ""
Dim boolean330
settingRepository1.GetAttrInfo "PRESSURE_OVER_FORCE_Nanometric", bSTR659, bSTR660, boolean330
'--------------------------------------------------
' Parameter 1 : (String) "PRESSURE_OVER_FORCE_Nanometric"
' Parameter 2 : (String) "Default value"
' Parameter 3 : (String) "Unlocked"
' Parameter 4 : (Boolean) False
'--------------------------------------------------

long331 = settingRepository1.GetAttr("PRESSURE_OVER_NORMAL_VELOCITY")
'--------------------------------------------------
' Parameter 1 : (String) "PRESSURE_OVER_NORMAL_VELOCITY"
' Returned value : (Variant) (Long) 1
'--------------------------------------------------

Dim bSTR661
bSTR661 = ""
Dim bSTR662
bSTR662 = ""
Dim boolean331
settingRepository1.GetAttrInfo "PRESSURE_OVER_NORMAL_VELOCITY", bSTR661, bSTR662, boolean331
'--------------------------------------------------
' Parameter 1 : (String) "PRESSURE_OVER_NORMAL_VELOCITY"
' Parameter 2 : (String) "Default value"
' Parameter 3 : (String) "Unlocked"
' Parameter 4 : (Boolean) False
'--------------------------------------------------

long332 = settingRepository1.GetAttr("PRESSURE_OVER_NORMAL_VELOCITY_Large")
'--------------------------------------------------
' Parameter 1 : (String) "PRESSURE_OVER_NORMAL_VELOCITY_Large"
' Returned value : (Variant) (Long) 1
'--------------------------------------------------

Dim bSTR663
bSTR663 = ""
Dim bSTR664
bSTR664 = ""
Dim boolean332
settingRepository1.GetAttrInfo "PRESSURE_OVER_NORMAL_VELOCITY_Large", bSTR663, bSTR664, boolean332
'--------------------------------------------------
' Parameter 1 : (String) "PRESSURE_OVER_NORMAL_VELOCITY_Large"
' Parameter 2 : (String) "Default value"
' Parameter 3 : (String) "Unlocked"
' Parameter 4 : (Boolean) False
'--------------------------------------------------

long333 = settingRepository1.GetAttr("PRESSURE_OVER_NORMAL_VELOCITY_ExtraLarge")
'--------------------------------------------------
' Parameter 1 : (String) "PRESSURE_OVER_NORMAL_VELOCITY_ExtraLarge"
' Returned value : (Variant) (Long) 1
'--------------------------------------------------

Dim bSTR665
bSTR665 = ""
Dim bSTR666
bSTR666 = ""
Dim boolean333
settingRepository1.GetAttrInfo "PRESSURE_OVER_NORMAL_VELOCITY_ExtraLarge", bSTR665, bSTR666, boolean333
'--------------------------------------------------
' Parameter 1 : (String) "PRESSURE_OVER_NORMAL_VELOCITY_ExtraLarge"
' Parameter 2 : (String) "Default value"
' Parameter 3 : (String) "Unlocked"
' Parameter 4 : (Boolean) False
'--------------------------------------------------

long334 = settingRepository1.GetAttr("PRESSURE_OVER_NORMAL_VELOCITY_Small")
'--------------------------------------------------
' Parameter 1 : (String) "PRESSURE_OVER_NORMAL_VELOCITY_Small"
' Returned value : (Variant) (Long) 1
'--------------------------------------------------

Dim bSTR667
bSTR667 = ""
Dim bSTR668
bSTR668 = ""
Dim boolean334
settingRepository1.GetAttrInfo "PRESSURE_OVER_NORMAL_VELOCITY_Small", bSTR667, bSTR668, boolean334
'--------------------------------------------------
' Parameter 1 : (String) "PRESSURE_OVER_NORMAL_VELOCITY_Small"
' Parameter 2 : (String) "Default value"
' Parameter 3 : (String) "Unlocked"
' Parameter 4 : (Boolean) False
'--------------------------------------------------

long335 = settingRepository1.GetAttr("PRESSURE_OVER_NORMAL_VELOCITY_ExtraSmall")
'--------------------------------------------------
' Parameter 1 : (String) "PRESSURE_OVER_NORMAL_VELOCITY_ExtraSmall"
' Returned value : (Variant) (Long) 1
'--------------------------------------------------

Dim bSTR669
bSTR669 = ""
Dim bSTR670
bSTR670 = ""
Dim boolean335
settingRepository1.GetAttrInfo "PRESSURE_OVER_NORMAL_VELOCITY_ExtraSmall", bSTR669, bSTR670, boolean335
'--------------------------------------------------
' Parameter 1 : (String) "PRESSURE_OVER_NORMAL_VELOCITY_ExtraSmall"
' Parameter 2 : (String) "Default value"
' Parameter 3 : (String) "Unlocked"
' Parameter 4 : (Boolean) False
'--------------------------------------------------

long336 = settingRepository1.GetAttr("PRESSURE_OVER_NORMAL_VELOCITY_Nanometric")
'--------------------------------------------------
' Parameter 1 : (String) "PRESSURE_OVER_NORMAL_VELOCITY_Nanometric"
' Returned value : (Variant) (Long) 1
'--------------------------------------------------

Dim bSTR671
bSTR671 = ""
Dim bSTR672
bSTR672 = ""
Dim boolean336
settingRepository1.GetAttrInfo "PRESSURE_OVER_NORMAL_VELOCITY_Nanometric", bSTR671, bSTR672, boolean336
'--------------------------------------------------
' Parameter 1 : (String) "PRESSURE_OVER_NORMAL_VELOCITY_Nanometric"
' Parameter 2 : (String) "Default value"
' Parameter 3 : (String) "Unlocked"
' Parameter 4 : (Boolean) False
'--------------------------------------------------

long337 = settingRepository1.GetAttr("PRESSURE_OVER_VOLUME_VELOCITY")
'--------------------------------------------------
' Parameter 1 : (String) "PRESSURE_OVER_VOLUME_VELOCITY"
' Returned value : (Variant) (Long) 1
'--------------------------------------------------

Dim bSTR673
bSTR673 = ""
Dim bSTR674
bSTR674 = ""
Dim boolean337
settingRepository1.GetAttrInfo "PRESSURE_OVER_VOLUME_VELOCITY", bSTR673, bSTR674, boolean337
'--------------------------------------------------
' Parameter 1 : (String) "PRESSURE_OVER_VOLUME_VELOCITY"
' Parameter 2 : (String) "Default value"
' Parameter 3 : (String) "Unlocked"
' Parameter 4 : (Boolean) False
'--------------------------------------------------

long338 = settingRepository1.GetAttr("PRESSURE_OVER_VOLUME_VELOCITY_Large")
'--------------------------------------------------
' Parameter 1 : (String) "PRESSURE_OVER_VOLUME_VELOCITY_Large"
' Returned value : (Variant) (Long) 1
'--------------------------------------------------

Dim bSTR675
bSTR675 = ""
Dim bSTR676
bSTR676 = ""
Dim boolean338
settingRepository1.GetAttrInfo "PRESSURE_OVER_VOLUME_VELOCITY_Large", bSTR675, bSTR676, boolean338
'--------------------------------------------------
' Parameter 1 : (String) "PRESSURE_OVER_VOLUME_VELOCITY_Large"
' Parameter 2 : (String) "Default value"
' Parameter 3 : (String) "Unlocked"
' Parameter 4 : (Boolean) False
'--------------------------------------------------

long339 = settingRepository1.GetAttr("PRESSURE_OVER_VOLUME_VELOCITY_ExtraLarge")
'--------------------------------------------------
' Parameter 1 : (String) "PRESSURE_OVER_VOLUME_VELOCITY_ExtraLarge"
' Returned value : (Variant) (Long) 1
'--------------------------------------------------

Dim bSTR677
bSTR677 = ""
Dim bSTR678
bSTR678 = ""
Dim boolean339
settingRepository1.GetAttrInfo "PRESSURE_OVER_VOLUME_VELOCITY_ExtraLarge", bSTR677, bSTR678, boolean339
'--------------------------------------------------
' Parameter 1 : (String) "PRESSURE_OVER_VOLUME_VELOCITY_ExtraLarge"
' Parameter 2 : (String) "Default value"
' Parameter 3 : (String) "Unlocked"
' Parameter 4 : (Boolean) False
'--------------------------------------------------

long340 = settingRepository1.GetAttr("PRESSURE_OVER_VOLUME_VELOCITY_Small")
'--------------------------------------------------
' Parameter 1 : (String) "PRESSURE_OVER_VOLUME_VELOCITY_Small"
' Returned value : (Variant) (Long) 1
'--------------------------------------------------

Dim bSTR679
bSTR679 = ""
Dim bSTR680
bSTR680 = ""
Dim boolean340
settingRepository1.GetAttrInfo "PRESSURE_OVER_VOLUME_VELOCITY_Small", bSTR679, bSTR680, boolean340
'--------------------------------------------------
' Parameter 1 : (String) "PRESSURE_OVER_VOLUME_VELOCITY_Small"
' Parameter 2 : (String) "Default value"
' Parameter 3 : (String) "Unlocked"
' Parameter 4 : (Boolean) False
'--------------------------------------------------

long341 = settingRepository1.GetAttr("PRESSURE_OVER_VOLUME_VELOCITY_ExtraSmall")
'--------------------------------------------------
' Parameter 1 : (String) "PRESSURE_OVER_VOLUME_VELOCITY_ExtraSmall"
' Returned value : (Variant) (Long) 1
'--------------------------------------------------

Dim bSTR681
bSTR681 = ""
Dim bSTR682
bSTR682 = ""
Dim boolean341
settingRepository1.GetAttrInfo "PRESSURE_OVER_VOLUME_VELOCITY_ExtraSmall", bSTR681, bSTR682, boolean341
'--------------------------------------------------
' Parameter 1 : (String) "PRESSURE_OVER_VOLUME_VELOCITY_ExtraSmall"
' Parameter 2 : (String) "Default value"
' Parameter 3 : (String) "Unlocked"
' Parameter 4 : (Boolean) False
'--------------------------------------------------

long342 = settingRepository1.GetAttr("PRESSURE_OVER_VOLUME_VELOCITY_Nanometric")
'--------------------------------------------------
' Parameter 1 : (String) "PRESSURE_OVER_VOLUME_VELOCITY_Nanometric"
' Returned value : (Variant) (Long) 1
'--------------------------------------------------

Dim bSTR683
bSTR683 = ""
Dim bSTR684
bSTR684 = ""
Dim boolean342
settingRepository1.GetAttrInfo "PRESSURE_OVER_VOLUME_VELOCITY_Nanometric", bSTR683, bSTR684, boolean342
'--------------------------------------------------
' Parameter 1 : (String) "PRESSURE_OVER_VOLUME_VELOCITY_Nanometric"
' Parameter 2 : (String) "Default value"
' Parameter 3 : (String) "Unlocked"
' Parameter 4 : (Boolean) False
'--------------------------------------------------

long343 = settingRepository1.GetAttr("PULSATION")
'--------------------------------------------------
' Parameter 1 : (String) "PULSATION"
' Returned value : (Variant) (Long) 1
'--------------------------------------------------

Dim bSTR685
bSTR685 = ""
Dim bSTR686
bSTR686 = ""
Dim boolean343
settingRepository1.GetAttrInfo "PULSATION", bSTR685, bSTR686, boolean343
'--------------------------------------------------
' Parameter 1 : (String) "PULSATION"
' Parameter 2 : (String) "Default value"
' Parameter 3 : (String) "Unlocked"
' Parameter 4 : (Boolean) False
'--------------------------------------------------

long344 = settingRepository1.GetAttr("PULSATION_Large")
'--------------------------------------------------
' Parameter 1 : (String) "PULSATION_Large"
' Returned value : (Variant) (Long) 1
'--------------------------------------------------

Dim bSTR687
bSTR687 = ""
Dim bSTR688
bSTR688 = ""
Dim boolean344
settingRepository1.GetAttrInfo "PULSATION_Large", bSTR687, bSTR688, boolean344
'--------------------------------------------------
' Parameter 1 : (String) "PULSATION_Large"
' Parameter 2 : (String) "Default value"
' Parameter 3 : (String) "Unlocked"
' Parameter 4 : (Boolean) False
'--------------------------------------------------

long345 = settingRepository1.GetAttr("PULSATION_ExtraLarge")
'--------------------------------------------------
' Parameter 1 : (String) "PULSATION_ExtraLarge"
' Returned value : (Variant) (Long) 1
'--------------------------------------------------

Dim bSTR689
bSTR689 = ""
Dim bSTR690
bSTR690 = ""
Dim boolean345
settingRepository1.GetAttrInfo "PULSATION_ExtraLarge", bSTR689, bSTR690, boolean345
'--------------------------------------------------
' Parameter 1 : (String) "PULSATION_ExtraLarge"
' Parameter 2 : (String) "Default value"
' Parameter 3 : (String) "Unlocked"
' Parameter 4 : (Boolean) False
'--------------------------------------------------

long346 = settingRepository1.GetAttr("PULSATION_Small")
'--------------------------------------------------
' Parameter 1 : (String) "PULSATION_Small"
' Returned value : (Variant) (Long) 1
'--------------------------------------------------

Dim bSTR691
bSTR691 = ""
Dim bSTR692
bSTR692 = ""
Dim boolean346
settingRepository1.GetAttrInfo "PULSATION_Small", bSTR691, bSTR692, boolean346
'--------------------------------------------------
' Parameter 1 : (String) "PULSATION_Small"
' Parameter 2 : (String) "Default value"
' Parameter 3 : (String) "Unlocked"
' Parameter 4 : (Boolean) False
'--------------------------------------------------

long347 = settingRepository1.GetAttr("PULSATION_ExtraSmall")
'--------------------------------------------------
' Parameter 1 : (String) "PULSATION_ExtraSmall"
' Returned value : (Variant) (Long) 1
'--------------------------------------------------

Dim bSTR693
bSTR693 = ""
Dim bSTR694
bSTR694 = ""
Dim boolean347
settingRepository1.GetAttrInfo "PULSATION_ExtraSmall", bSTR693, bSTR694, boolean347
'--------------------------------------------------
' Parameter 1 : (String) "PULSATION_ExtraSmall"
' Parameter 2 : (String) "Default value"
' Parameter 3 : (String) "Unlocked"
' Parameter 4 : (Boolean) False
'--------------------------------------------------

long348 = settingRepository1.GetAttr("PULSATION_Nanometric")
'--------------------------------------------------
' Parameter 1 : (String) "PULSATION_Nanometric"
' Returned value : (Variant) (Long) 1
'--------------------------------------------------

Dim bSTR695
bSTR695 = ""
Dim bSTR696
bSTR696 = ""
Dim boolean348
settingRepository1.GetAttrInfo "PULSATION_Nanometric", bSTR695, bSTR696, boolean348
'--------------------------------------------------
' Parameter 1 : (String) "PULSATION_Nanometric"
' Parameter 2 : (String) "Default value"
' Parameter 3 : (String) "Unlocked"
' Parameter 4 : (Boolean) False
'--------------------------------------------------

long349 = settingRepository1.GetAttr("MODAL_DAMPING")
'--------------------------------------------------
' Parameter 1 : (String) "MODAL_DAMPING"
' Returned value : (Variant) (Long) 1
'--------------------------------------------------

Dim bSTR697
bSTR697 = ""
Dim bSTR698
bSTR698 = ""
Dim boolean349
settingRepository1.GetAttrInfo "MODAL_DAMPING", bSTR697, bSTR698, boolean349
'--------------------------------------------------
' Parameter 1 : (String) "MODAL_DAMPING"
' Parameter 2 : (String) "Default value"
' Parameter 3 : (String) "Unlocked"
' Parameter 4 : (Boolean) False
'--------------------------------------------------

long350 = settingRepository1.GetAttr("MODAL_DAMPING_Large")
'--------------------------------------------------
' Parameter 1 : (String) "MODAL_DAMPING_Large"
' Returned value : (Variant) (Long) 1
'--------------------------------------------------

Dim bSTR699
bSTR699 = ""
Dim bSTR700
bSTR700 = ""
Dim boolean350
settingRepository1.GetAttrInfo "MODAL_DAMPING_Large", bSTR699, bSTR700, boolean350
'--------------------------------------------------
' Parameter 1 : (String) "MODAL_DAMPING_Large"
' Parameter 2 : (String) "Default value"
' Parameter 3 : (String) "Unlocked"
' Parameter 4 : (Boolean) False
'--------------------------------------------------

long351 = settingRepository1.GetAttr("MODAL_DAMPING_ExtraLarge")
'--------------------------------------------------
' Parameter 1 : (String) "MODAL_DAMPING_ExtraLarge"
' Returned value : (Variant) (Long) 1
'--------------------------------------------------

Dim bSTR701
bSTR701 = ""
Dim bSTR702
bSTR702 = ""
Dim boolean351
settingRepository1.GetAttrInfo "MODAL_DAMPING_ExtraLarge", bSTR701, bSTR702, boolean351
'--------------------------------------------------
' Parameter 1 : (String) "MODAL_DAMPING_ExtraLarge"
' Parameter 2 : (String) "Default value"
' Parameter 3 : (String) "Unlocked"
' Parameter 4 : (Boolean) False
'--------------------------------------------------

long352 = settingRepository1.GetAttr("MODAL_DAMPING_Small")
'--------------------------------------------------
' Parameter 1 : (String) "MODAL_DAMPING_Small"
' Returned value : (Variant) (Long) 1
'--------------------------------------------------

Dim bSTR703
bSTR703 = ""
Dim bSTR704
bSTR704 = ""
Dim boolean352
settingRepository1.GetAttrInfo "MODAL_DAMPING_Small", bSTR703, bSTR704, boolean352
'--------------------------------------------------
' Parameter 1 : (String) "MODAL_DAMPING_Small"
' Parameter 2 : (String) "Default value"
' Parameter 3 : (String) "Unlocked"
' Parameter 4 : (Boolean) False
'--------------------------------------------------

long353 = settingRepository1.GetAttr("MODAL_DAMPING_ExtraSmall")
'--------------------------------------------------
' Parameter 1 : (String) "MODAL_DAMPING_ExtraSmall"
' Returned value : (Variant) (Long) 1
'--------------------------------------------------

Dim bSTR705
bSTR705 = ""
Dim bSTR706
bSTR706 = ""
Dim boolean353
settingRepository1.GetAttrInfo "MODAL_DAMPING_ExtraSmall", bSTR705, bSTR706, boolean353
'--------------------------------------------------
' Parameter 1 : (String) "MODAL_DAMPING_ExtraSmall"
' Parameter 2 : (String) "Default value"
' Parameter 3 : (String) "Unlocked"
' Parameter 4 : (Boolean) False
'--------------------------------------------------

long354 = settingRepository1.GetAttr("MODAL_DAMPING_Nanometric")
'--------------------------------------------------
' Parameter 1 : (String) "MODAL_DAMPING_Nanometric"
' Returned value : (Variant) (Long) 1
'--------------------------------------------------

Dim bSTR707
bSTR707 = ""
Dim bSTR708
bSTR708 = ""
Dim boolean354
settingRepository1.GetAttrInfo "MODAL_DAMPING_Nanometric", bSTR707, bSTR708, boolean354
'--------------------------------------------------
' Parameter 1 : (String) "MODAL_DAMPING_Nanometric"
' Parameter 2 : (String) "Default value"
' Parameter 3 : (String) "Unlocked"
' Parameter 4 : (Boolean) False
'--------------------------------------------------

long355 = settingRepository1.GetAttr("VISCOUS_DAMPING")
'--------------------------------------------------
' Parameter 1 : (String) "VISCOUS_DAMPING"
' Returned value : (Variant) (Long) 1
'--------------------------------------------------

Dim bSTR709
bSTR709 = ""
Dim bSTR710
bSTR710 = ""
Dim boolean355
settingRepository1.GetAttrInfo "VISCOUS_DAMPING", bSTR709, bSTR710, boolean355
'--------------------------------------------------
' Parameter 1 : (String) "VISCOUS_DAMPING"
' Parameter 2 : (String) "Default value"
' Parameter 3 : (String) "Unlocked"
' Parameter 4 : (Boolean) False
'--------------------------------------------------

long356 = settingRepository1.GetAttr("VISCOUS_DAMPING_Large")
'--------------------------------------------------
' Parameter 1 : (String) "VISCOUS_DAMPING_Large"
' Returned value : (Variant) (Long) 1
'--------------------------------------------------

Dim bSTR711
bSTR711 = ""
Dim bSTR712
bSTR712 = ""
Dim boolean356
settingRepository1.GetAttrInfo "VISCOUS_DAMPING_Large", bSTR711, bSTR712, boolean356
'--------------------------------------------------
' Parameter 1 : (String) "VISCOUS_DAMPING_Large"
' Parameter 2 : (String) "Default value"
' Parameter 3 : (String) "Unlocked"
' Parameter 4 : (Boolean) False
'--------------------------------------------------

long357 = settingRepository1.GetAttr("VISCOUS_DAMPING_ExtraLarge")
'--------------------------------------------------
' Parameter 1 : (String) "VISCOUS_DAMPING_ExtraLarge"
' Returned value : (Variant) (Long) 1
'--------------------------------------------------

Dim bSTR713
bSTR713 = ""
Dim bSTR714
bSTR714 = ""
Dim boolean357
settingRepository1.GetAttrInfo "VISCOUS_DAMPING_ExtraLarge", bSTR713, bSTR714, boolean357
'--------------------------------------------------
' Parameter 1 : (String) "VISCOUS_DAMPING_ExtraLarge"
' Parameter 2 : (String) "Default value"
' Parameter 3 : (String) "Unlocked"
' Parameter 4 : (Boolean) False
'--------------------------------------------------

long358 = settingRepository1.GetAttr("VISCOUS_DAMPING_Small")
'--------------------------------------------------
' Parameter 1 : (String) "VISCOUS_DAMPING_Small"
' Returned value : (Variant) (Long) 1
'--------------------------------------------------

Dim bSTR715
bSTR715 = ""
Dim bSTR716
bSTR716 = ""
Dim boolean358
settingRepository1.GetAttrInfo "VISCOUS_DAMPING_Small", bSTR715, bSTR716, boolean358
'--------------------------------------------------
' Parameter 1 : (String) "VISCOUS_DAMPING_Small"
' Parameter 2 : (String) "Default value"
' Parameter 3 : (String) "Unlocked"
' Parameter 4 : (Boolean) False
'--------------------------------------------------

long359 = settingRepository1.GetAttr("VISCOUS_DAMPING_ExtraSmall")
'--------------------------------------------------
' Parameter 1 : (String) "VISCOUS_DAMPING_ExtraSmall"
' Returned value : (Variant) (Long) 1
'--------------------------------------------------

Dim bSTR717
bSTR717 = ""
Dim bSTR718
bSTR718 = ""
Dim boolean359
settingRepository1.GetAttrInfo "VISCOUS_DAMPING_ExtraSmall", bSTR717, bSTR718, boolean359
'--------------------------------------------------
' Parameter 1 : (String) "VISCOUS_DAMPING_ExtraSmall"
' Parameter 2 : (String) "Default value"
' Parameter 3 : (String) "Unlocked"
' Parameter 4 : (Boolean) False
'--------------------------------------------------

long360 = settingRepository1.GetAttr("VISCOUS_DAMPING_Nanometric")
'--------------------------------------------------
' Parameter 1 : (String) "VISCOUS_DAMPING_Nanometric"
' Returned value : (Variant) (Long) 1
'--------------------------------------------------

Dim bSTR719
bSTR719 = ""
Dim bSTR720
bSTR720 = ""
Dim boolean360
settingRepository1.GetAttrInfo "VISCOUS_DAMPING_Nanometric", bSTR719, bSTR720, boolean360
'--------------------------------------------------
' Parameter 1 : (String) "VISCOUS_DAMPING_Nanometric"
' Parameter 2 : (String) "Default value"
' Parameter 3 : (String) "Unlocked"
' Parameter 4 : (Boolean) False
'--------------------------------------------------

long361 = settingRepository1.GetAttr("MODAL_PARTICIPATION_FACTOR")
'--------------------------------------------------
' Parameter 1 : (String) "MODAL_PARTICIPATION_FACTOR"
' Returned value : (Variant) (Long) 1
'--------------------------------------------------

Dim bSTR721
bSTR721 = ""
Dim bSTR722
bSTR722 = ""
Dim boolean361
settingRepository1.GetAttrInfo "MODAL_PARTICIPATION_FACTOR", bSTR721, bSTR722, boolean361
'--------------------------------------------------
' Parameter 1 : (String) "MODAL_PARTICIPATION_FACTOR"
' Parameter 2 : (String) "Default value"
' Parameter 3 : (String) "Unlocked"
' Parameter 4 : (Boolean) False
'--------------------------------------------------

long362 = settingRepository1.GetAttr("MODAL_PARTICIPATION_FACTOR_Large")
'--------------------------------------------------
' Parameter 1 : (String) "MODAL_PARTICIPATION_FACTOR_Large"
' Returned value : (Variant) (Long) 1
'--------------------------------------------------

Dim bSTR723
bSTR723 = ""
Dim bSTR724
bSTR724 = ""
Dim boolean362
settingRepository1.GetAttrInfo "MODAL_PARTICIPATION_FACTOR_Large", bSTR723, bSTR724, boolean362
'--------------------------------------------------
' Parameter 1 : (String) "MODAL_PARTICIPATION_FACTOR_Large"
' Parameter 2 : (String) "Default value"
' Parameter 3 : (String) "Unlocked"
' Parameter 4 : (Boolean) False
'--------------------------------------------------

long363 = settingRepository1.GetAttr("MODAL_PARTICIPATION_FACTOR_ExtraLarge")
'--------------------------------------------------
' Parameter 1 : (String) "MODAL_PARTICIPATION_FACTOR_ExtraLarge"
' Returned value : (Variant) (Long) 1
'--------------------------------------------------

Dim bSTR725
bSTR725 = ""
Dim bSTR726
bSTR726 = ""
Dim boolean363
settingRepository1.GetAttrInfo "MODAL_PARTICIPATION_FACTOR_ExtraLarge", bSTR725, bSTR726, boolean363
'--------------------------------------------------
' Parameter 1 : (String) "MODAL_PARTICIPATION_FACTOR_ExtraLarge"
' Parameter 2 : (String) "Default value"
' Parameter 3 : (String) "Unlocked"
' Parameter 4 : (Boolean) False
'--------------------------------------------------

long364 = settingRepository1.GetAttr("MODAL_PARTICIPATION_FACTOR_Small")
'--------------------------------------------------
' Parameter 1 : (String) "MODAL_PARTICIPATION_FACTOR_Small"
' Returned value : (Variant) (Long) 1
'--------------------------------------------------

Dim bSTR727
bSTR727 = ""
Dim bSTR728
bSTR728 = ""
Dim boolean364
settingRepository1.GetAttrInfo "MODAL_PARTICIPATION_FACTOR_Small", bSTR727, bSTR728, boolean364
'--------------------------------------------------
' Parameter 1 : (String) "MODAL_PARTICIPATION_FACTOR_Small"
' Parameter 2 : (String) "Default value"
' Parameter 3 : (String) "Unlocked"
' Parameter 4 : (Boolean) False
'--------------------------------------------------

long365 = settingRepository1.GetAttr("MODAL_PARTICIPATION_FACTOR_ExtraSmall")
'--------------------------------------------------
' Parameter 1 : (String) "MODAL_PARTICIPATION_FACTOR_ExtraSmall"
' Returned value : (Variant) (Long) 1
'--------------------------------------------------

Dim bSTR729
bSTR729 = ""
Dim bSTR730
bSTR730 = ""
Dim boolean365
settingRepository1.GetAttrInfo "MODAL_PARTICIPATION_FACTOR_ExtraSmall", bSTR729, bSTR730, boolean365
'--------------------------------------------------
' Parameter 1 : (String) "MODAL_PARTICIPATION_FACTOR_ExtraSmall"
' Parameter 2 : (String) "Default value"
' Parameter 3 : (String) "Unlocked"
' Parameter 4 : (Boolean) False
'--------------------------------------------------

long366 = settingRepository1.GetAttr("MODAL_PARTICIPATION_FACTOR_Nanometric")
'--------------------------------------------------
' Parameter 1 : (String) "MODAL_PARTICIPATION_FACTOR_Nanometric"
' Returned value : (Variant) (Long) 1
'--------------------------------------------------

Dim bSTR731
bSTR731 = ""
Dim bSTR732
bSTR732 = ""
Dim boolean366
settingRepository1.GetAttrInfo "MODAL_PARTICIPATION_FACTOR_Nanometric", bSTR731, bSTR732, boolean366
'--------------------------------------------------
' Parameter 1 : (String) "MODAL_PARTICIPATION_FACTOR_Nanometric"
' Parameter 2 : (String) "Default value"
' Parameter 3 : (String) "Unlocked"
' Parameter 4 : (Boolean) False
'--------------------------------------------------

long367 = settingRepository1.GetAttr("MODAL_MASS")
'--------------------------------------------------
' Parameter 1 : (String) "MODAL_MASS"
' Returned value : (Variant) (Long) 1
'--------------------------------------------------

Dim bSTR733
bSTR733 = ""
Dim bSTR734
bSTR734 = ""
Dim boolean367
settingRepository1.GetAttrInfo "MODAL_MASS", bSTR733, bSTR734, boolean367
'--------------------------------------------------
' Parameter 1 : (String) "MODAL_MASS"
' Parameter 2 : (String) "Default value"
' Parameter 3 : (String) "Unlocked"
' Parameter 4 : (Boolean) False
'--------------------------------------------------

long368 = settingRepository1.GetAttr("MODAL_MASS_Large")
'--------------------------------------------------
' Parameter 1 : (String) "MODAL_MASS_Large"
' Returned value : (Variant) (Long) 1
'--------------------------------------------------

Dim bSTR735
bSTR735 = ""
Dim bSTR736
bSTR736 = ""
Dim boolean368
settingRepository1.GetAttrInfo "MODAL_MASS_Large", bSTR735, bSTR736, boolean368
'--------------------------------------------------
' Parameter 1 : (String) "MODAL_MASS_Large"
' Parameter 2 : (String) "Default value"
' Parameter 3 : (String) "Unlocked"
' Parameter 4 : (Boolean) False
'--------------------------------------------------

long369 = settingRepository1.GetAttr("MODAL_MASS_ExtraLarge")
'--------------------------------------------------
' Parameter 1 : (String) "MODAL_MASS_ExtraLarge"
' Returned value : (Variant) (Long) 1
'--------------------------------------------------

Dim bSTR737
bSTR737 = ""
Dim bSTR738
bSTR738 = ""
Dim boolean369
settingRepository1.GetAttrInfo "MODAL_MASS_ExtraLarge", bSTR737, bSTR738, boolean369
'--------------------------------------------------
' Parameter 1 : (String) "MODAL_MASS_ExtraLarge"
' Parameter 2 : (String) "Default value"
' Parameter 3 : (String) "Unlocked"
' Parameter 4 : (Boolean) False
'--------------------------------------------------

long370 = settingRepository1.GetAttr("MODAL_MASS_Small")
'--------------------------------------------------
' Parameter 1 : (String) "MODAL_MASS_Small"
' Returned value : (Variant) (Long) 1
'--------------------------------------------------

Dim bSTR739
bSTR739 = ""
Dim bSTR740
bSTR740 = ""
Dim boolean370
settingRepository1.GetAttrInfo "MODAL_MASS_Small", bSTR739, bSTR740, boolean370
'--------------------------------------------------
' Parameter 1 : (String) "MODAL_MASS_Small"
' Parameter 2 : (String) "Default value"
' Parameter 3 : (String) "Unlocked"
' Parameter 4 : (Boolean) False
'--------------------------------------------------

long371 = settingRepository1.GetAttr("MODAL_MASS_ExtraSmall")
'--------------------------------------------------
' Parameter 1 : (String) "MODAL_MASS_ExtraSmall"
' Returned value : (Variant) (Long) 1
'--------------------------------------------------

Dim bSTR741
bSTR741 = ""
Dim bSTR742
bSTR742 = ""
Dim boolean371
settingRepository1.GetAttrInfo "MODAL_MASS_ExtraSmall", bSTR741, bSTR742, boolean371
'--------------------------------------------------
' Parameter 1 : (String) "MODAL_MASS_ExtraSmall"
' Parameter 2 : (String) "Default value"
' Parameter 3 : (String) "Unlocked"
' Parameter 4 : (Boolean) False
'--------------------------------------------------

long372 = settingRepository1.GetAttr("MODAL_MASS_Nanometric")
'--------------------------------------------------
' Parameter 1 : (String) "MODAL_MASS_Nanometric"
' Returned value : (Variant) (Long) 1
'--------------------------------------------------

Dim bSTR743
bSTR743 = ""
Dim bSTR744
bSTR744 = ""
Dim boolean372
settingRepository1.GetAttrInfo "MODAL_MASS_Nanometric", bSTR743, bSTR744, boolean372
'--------------------------------------------------
' Parameter 1 : (String) "MODAL_MASS_Nanometric"
' Parameter 2 : (String) "Default value"
' Parameter 3 : (String) "Unlocked"
' Parameter 4 : (Boolean) False
'--------------------------------------------------

long373 = settingRepository1.GetAttr("DIMENSIONLESS")
'--------------------------------------------------
' Parameter 1 : (String) "DIMENSIONLESS"
' Returned value : (Variant) (Long) 1
'--------------------------------------------------

Dim bSTR745
bSTR745 = ""
Dim bSTR746
bSTR746 = ""
Dim boolean373
settingRepository1.GetAttrInfo "DIMENSIONLESS", bSTR745, bSTR746, boolean373
'--------------------------------------------------
' Parameter 1 : (String) "DIMENSIONLESS"
' Parameter 2 : (String) "Default value"
' Parameter 3 : (String) "Unlocked"
' Parameter 4 : (Boolean) False
'--------------------------------------------------

long374 = settingRepository1.GetAttr("DIMENSIONLESS_Large")
'--------------------------------------------------
' Parameter 1 : (String) "DIMENSIONLESS_Large"
' Returned value : (Variant) (Long) 1
'--------------------------------------------------

Dim bSTR747
bSTR747 = ""
Dim bSTR748
bSTR748 = ""
Dim boolean374
settingRepository1.GetAttrInfo "DIMENSIONLESS_Large", bSTR747, bSTR748, boolean374
'--------------------------------------------------
' Parameter 1 : (String) "DIMENSIONLESS_Large"
' Parameter 2 : (String) "Default value"
' Parameter 3 : (String) "Unlocked"
' Parameter 4 : (Boolean) False
'--------------------------------------------------

long375 = settingRepository1.GetAttr("DIMENSIONLESS_ExtraLarge")
'--------------------------------------------------
' Parameter 1 : (String) "DIMENSIONLESS_ExtraLarge"
' Returned value : (Variant) (Long) 1
'--------------------------------------------------

Dim bSTR749
bSTR749 = ""
Dim bSTR750
bSTR750 = ""
Dim boolean375
settingRepository1.GetAttrInfo "DIMENSIONLESS_ExtraLarge", bSTR749, bSTR750, boolean375
'--------------------------------------------------
' Parameter 1 : (String) "DIMENSIONLESS_ExtraLarge"
' Parameter 2 : (String) "Default value"
' Parameter 3 : (String) "Unlocked"
' Parameter 4 : (Boolean) False
'--------------------------------------------------

long376 = settingRepository1.GetAttr("DIMENSIONLESS_Small")
'--------------------------------------------------
' Parameter 1 : (String) "DIMENSIONLESS_Small"
' Returned value : (Variant) (Long) 1
'--------------------------------------------------

Dim bSTR751
bSTR751 = ""
Dim bSTR752
bSTR752 = ""
Dim boolean376
settingRepository1.GetAttrInfo "DIMENSIONLESS_Small", bSTR751, bSTR752, boolean376
'--------------------------------------------------
' Parameter 1 : (String) "DIMENSIONLESS_Small"
' Parameter 2 : (String) "Default value"
' Parameter 3 : (String) "Unlocked"
' Parameter 4 : (Boolean) False
'--------------------------------------------------

long377 = settingRepository1.GetAttr("DIMENSIONLESS_ExtraSmall")
'--------------------------------------------------
' Parameter 1 : (String) "DIMENSIONLESS_ExtraSmall"
' Returned value : (Variant) (Long) 1
'--------------------------------------------------

Dim bSTR753
bSTR753 = ""
Dim bSTR754
bSTR754 = ""
Dim boolean377
settingRepository1.GetAttrInfo "DIMENSIONLESS_ExtraSmall", bSTR753, bSTR754, boolean377
'--------------------------------------------------
' Parameter 1 : (String) "DIMENSIONLESS_ExtraSmall"
' Parameter 2 : (String) "Default value"
' Parameter 3 : (String) "Unlocked"
' Parameter 4 : (Boolean) False
'--------------------------------------------------

long378 = settingRepository1.GetAttr("DIMENSIONLESS_Nanometric")
'--------------------------------------------------
' Parameter 1 : (String) "DIMENSIONLESS_Nanometric"
' Returned value : (Variant) (Long) 1
'--------------------------------------------------

Dim bSTR755
bSTR755 = ""
Dim bSTR756
bSTR756 = ""
Dim boolean378
settingRepository1.GetAttrInfo "DIMENSIONLESS_Nanometric", bSTR755, bSTR756, boolean378
'--------------------------------------------------
' Parameter 1 : (String) "DIMENSIONLESS_Nanometric"
' Parameter 2 : (String) "Default value"
' Parameter 3 : (String) "Unlocked"
' Parameter 4 : (Boolean) False
'--------------------------------------------------

long379 = settingRepository1.GetAttr("DISPLACEMENT_OVER_FORCE")
'--------------------------------------------------
' Parameter 1 : (String) "DISPLACEMENT_OVER_FORCE"
' Returned value : (Variant) (Long) 1
'--------------------------------------------------

Dim bSTR757
bSTR757 = ""
Dim bSTR758
bSTR758 = ""
Dim boolean379
settingRepository1.GetAttrInfo "DISPLACEMENT_OVER_FORCE", bSTR757, bSTR758, boolean379
'--------------------------------------------------
' Parameter 1 : (String) "DISPLACEMENT_OVER_FORCE"
' Parameter 2 : (String) "Default value"
' Parameter 3 : (String) "Unlocked"
' Parameter 4 : (Boolean) False
'--------------------------------------------------

long380 = settingRepository1.GetAttr("DISPLACEMENT_OVER_FORCE_Large")
'--------------------------------------------------
' Parameter 1 : (String) "DISPLACEMENT_OVER_FORCE_Large"
' Returned value : (Variant) (Long) 1
'--------------------------------------------------

Dim bSTR759
bSTR759 = ""
Dim bSTR760
bSTR760 = ""
Dim boolean380
settingRepository1.GetAttrInfo "DISPLACEMENT_OVER_FORCE_Large", bSTR759, bSTR760, boolean380
'--------------------------------------------------
' Parameter 1 : (String) "DISPLACEMENT_OVER_FORCE_Large"
' Parameter 2 : (String) "Default value"
' Parameter 3 : (String) "Unlocked"
' Parameter 4 : (Boolean) False
'--------------------------------------------------

long381 = settingRepository1.GetAttr("DISPLACEMENT_OVER_FORCE_ExtraLarge")
'--------------------------------------------------
' Parameter 1 : (String) "DISPLACEMENT_OVER_FORCE_ExtraLarge"
' Returned value : (Variant) (Long) 1
'--------------------------------------------------

Dim bSTR761
bSTR761 = ""
Dim bSTR762
bSTR762 = ""
Dim boolean381
settingRepository1.GetAttrInfo "DISPLACEMENT_OVER_FORCE_ExtraLarge", bSTR761, bSTR762, boolean381
'--------------------------------------------------
' Parameter 1 : (String) "DISPLACEMENT_OVER_FORCE_ExtraLarge"
' Parameter 2 : (String) "Default value"
' Parameter 3 : (String) "Unlocked"
' Parameter 4 : (Boolean) False
'--------------------------------------------------

long382 = settingRepository1.GetAttr("DISPLACEMENT_OVER_FORCE_Small")
'--------------------------------------------------
' Parameter 1 : (String) "DISPLACEMENT_OVER_FORCE_Small"
' Returned value : (Variant) (Long) 1
'--------------------------------------------------

Dim bSTR763
bSTR763 = ""
Dim bSTR764
bSTR764 = ""
Dim boolean382
settingRepository1.GetAttrInfo "DISPLACEMENT_OVER_FORCE_Small", bSTR763, bSTR764, boolean382
'--------------------------------------------------
' Parameter 1 : (String) "DISPLACEMENT_OVER_FORCE_Small"
' Parameter 2 : (String) "Default value"
' Parameter 3 : (String) "Unlocked"
' Parameter 4 : (Boolean) False
'--------------------------------------------------

long383 = settingRepository1.GetAttr("DISPLACEMENT_OVER_FORCE_ExtraSmall")
'--------------------------------------------------
' Parameter 1 : (String) "DISPLACEMENT_OVER_FORCE_ExtraSmall"
' Returned value : (Variant) (Long) 1
'--------------------------------------------------

Dim bSTR765
bSTR765 = ""
Dim bSTR766
bSTR766 = ""
Dim boolean383
settingRepository1.GetAttrInfo "DISPLACEMENT_OVER_FORCE_ExtraSmall", bSTR765, bSTR766, boolean383
'--------------------------------------------------
' Parameter 1 : (String) "DISPLACEMENT_OVER_FORCE_ExtraSmall"
' Parameter 2 : (String) "Default value"
' Parameter 3 : (String) "Unlocked"
' Parameter 4 : (Boolean) False
'--------------------------------------------------

long384 = settingRepository1.GetAttr("DISPLACEMENT_OVER_FORCE_Nanometric")
'--------------------------------------------------
' Parameter 1 : (String) "DISPLACEMENT_OVER_FORCE_Nanometric"
' Returned value : (Variant) (Long) 1
'--------------------------------------------------

Dim bSTR767
bSTR767 = ""
Dim bSTR768
bSTR768 = ""
Dim boolean384
settingRepository1.GetAttrInfo "DISPLACEMENT_OVER_FORCE_Nanometric", bSTR767, bSTR768, boolean384
'--------------------------------------------------
' Parameter 1 : (String) "DISPLACEMENT_OVER_FORCE_Nanometric"
' Parameter 2 : (String) "Default value"
' Parameter 3 : (String) "Unlocked"
' Parameter 4 : (Boolean) False
'--------------------------------------------------

long385 = settingRepository1.GetAttr("ACCELERATION_OVER_MOMENT")
'--------------------------------------------------
' Parameter 1 : (String) "ACCELERATION_OVER_MOMENT"
' Returned value : (Variant) (Long) 1
'--------------------------------------------------

Dim bSTR769
bSTR769 = ""
Dim bSTR770
bSTR770 = ""
Dim boolean385
settingRepository1.GetAttrInfo "ACCELERATION_OVER_MOMENT", bSTR769, bSTR770, boolean385
'--------------------------------------------------
' Parameter 1 : (String) "ACCELERATION_OVER_MOMENT"
' Parameter 2 : (String) "Default value"
' Parameter 3 : (String) "Unlocked"
' Parameter 4 : (Boolean) False
'--------------------------------------------------

long386 = settingRepository1.GetAttr("ACCELERATION_OVER_MOMENT_Large")
'--------------------------------------------------
' Parameter 1 : (String) "ACCELERATION_OVER_MOMENT_Large"
' Returned value : (Variant) (Long) 1
'--------------------------------------------------

Dim bSTR771
bSTR771 = ""
Dim bSTR772
bSTR772 = ""
Dim boolean386
settingRepository1.GetAttrInfo "ACCELERATION_OVER_MOMENT_Large", bSTR771, bSTR772, boolean386
'--------------------------------------------------
' Parameter 1 : (String) "ACCELERATION_OVER_MOMENT_Large"
' Parameter 2 : (String) "Default value"
' Parameter 3 : (String) "Unlocked"
' Parameter 4 : (Boolean) False
'--------------------------------------------------

long387 = settingRepository1.GetAttr("ACCELERATION_OVER_MOMENT_ExtraLarge")
'--------------------------------------------------
' Parameter 1 : (String) "ACCELERATION_OVER_MOMENT_ExtraLarge"
' Returned value : (Variant) (Long) 1
'--------------------------------------------------

Dim bSTR773
bSTR773 = ""
Dim bSTR774
bSTR774 = ""
Dim boolean387
settingRepository1.GetAttrInfo "ACCELERATION_OVER_MOMENT_ExtraLarge", bSTR773, bSTR774, boolean387
'--------------------------------------------------
' Parameter 1 : (String) "ACCELERATION_OVER_MOMENT_ExtraLarge"
' Parameter 2 : (String) "Default value"
' Parameter 3 : (String) "Unlocked"
' Parameter 4 : (Boolean) False
'--------------------------------------------------

long388 = settingRepository1.GetAttr("ACCELERATION_OVER_MOMENT_Small")
'--------------------------------------------------
' Parameter 1 : (String) "ACCELERATION_OVER_MOMENT_Small"
' Returned value : (Variant) (Long) 1
'--------------------------------------------------

Dim bSTR775
bSTR775 = ""
Dim bSTR776
bSTR776 = ""
Dim boolean388
settingRepository1.GetAttrInfo "ACCELERATION_OVER_MOMENT_Small", bSTR775, bSTR776, boolean388
'--------------------------------------------------
' Parameter 1 : (String) "ACCELERATION_OVER_MOMENT_Small"
' Parameter 2 : (String) "Default value"
' Parameter 3 : (String) "Unlocked"
' Parameter 4 : (Boolean) False
'--------------------------------------------------

long389 = settingRepository1.GetAttr("ACCELERATION_OVER_MOMENT_ExtraSmall")
'--------------------------------------------------
' Parameter 1 : (String) "ACCELERATION_OVER_MOMENT_ExtraSmall"
' Returned value : (Variant) (Long) 1
'--------------------------------------------------

Dim bSTR777
bSTR777 = ""
Dim bSTR778
bSTR778 = ""
Dim boolean389
settingRepository1.GetAttrInfo "ACCELERATION_OVER_MOMENT_ExtraSmall", bSTR777, bSTR778, boolean389
'--------------------------------------------------
' Parameter 1 : (String) "ACCELERATION_OVER_MOMENT_ExtraSmall"
' Parameter 2 : (String) "Default value"
' Parameter 3 : (String) "Unlocked"
' Parameter 4 : (Boolean) False
'--------------------------------------------------

long390 = settingRepository1.GetAttr("ACCELERATION_OVER_MOMENT_Nanometric")
'--------------------------------------------------
' Parameter 1 : (String) "ACCELERATION_OVER_MOMENT_Nanometric"
' Returned value : (Variant) (Long) 1
'--------------------------------------------------

Dim bSTR779
bSTR779 = ""
Dim bSTR780
bSTR780 = ""
Dim boolean390
settingRepository1.GetAttrInfo "ACCELERATION_OVER_MOMENT_Nanometric", bSTR779, bSTR780, boolean390
'--------------------------------------------------
' Parameter 1 : (String) "ACCELERATION_OVER_MOMENT_Nanometric"
' Parameter 2 : (String) "Default value"
' Parameter 3 : (String) "Unlocked"
' Parameter 4 : (Boolean) False
'--------------------------------------------------

long391 = settingRepository1.GetAttr("VELOCITY_OVER_MOMENT")
'--------------------------------------------------
' Parameter 1 : (String) "VELOCITY_OVER_MOMENT"
' Returned value : (Variant) (Long) 1
'--------------------------------------------------

Dim bSTR781
bSTR781 = ""
Dim bSTR782
bSTR782 = ""
Dim boolean391
settingRepository1.GetAttrInfo "VELOCITY_OVER_MOMENT", bSTR781, bSTR782, boolean391
'--------------------------------------------------
' Parameter 1 : (String) "VELOCITY_OVER_MOMENT"
' Parameter 2 : (String) "Default value"
' Parameter 3 : (String) "Unlocked"
' Parameter 4 : (Boolean) False
'--------------------------------------------------

long392 = settingRepository1.GetAttr("VELOCITY_OVER_MOMENT_Large")
'--------------------------------------------------
' Parameter 1 : (String) "VELOCITY_OVER_MOMENT_Large"
' Returned value : (Variant) (Long) 1
'--------------------------------------------------

Dim bSTR783
bSTR783 = ""
Dim bSTR784
bSTR784 = ""
Dim boolean392
settingRepository1.GetAttrInfo "VELOCITY_OVER_MOMENT_Large", bSTR783, bSTR784, boolean392
'--------------------------------------------------
' Parameter 1 : (String) "VELOCITY_OVER_MOMENT_Large"
' Parameter 2 : (String) "Default value"
' Parameter 3 : (String) "Unlocked"
' Parameter 4 : (Boolean) False
'--------------------------------------------------

long393 = settingRepository1.GetAttr("VELOCITY_OVER_MOMENT_ExtraLarge")
'--------------------------------------------------
' Parameter 1 : (String) "VELOCITY_OVER_MOMENT_ExtraLarge"
' Returned value : (Variant) (Long) 1
'--------------------------------------------------

Dim bSTR785
bSTR785 = ""
Dim bSTR786
bSTR786 = ""
Dim boolean393
settingRepository1.GetAttrInfo "VELOCITY_OVER_MOMENT_ExtraLarge", bSTR785, bSTR786, boolean393
'--------------------------------------------------
' Parameter 1 : (String) "VELOCITY_OVER_MOMENT_ExtraLarge"
' Parameter 2 : (String) "Default value"
' Parameter 3 : (String) "Unlocked"
' Parameter 4 : (Boolean) False
'--------------------------------------------------

long394 = settingRepository1.GetAttr("VELOCITY_OVER_MOMENT_Small")
'--------------------------------------------------
' Parameter 1 : (String) "VELOCITY_OVER_MOMENT_Small"
' Returned value : (Variant) (Long) 1
'--------------------------------------------------

Dim bSTR787
bSTR787 = ""
Dim bSTR788
bSTR788 = ""
Dim boolean394
settingRepository1.GetAttrInfo "VELOCITY_OVER_MOMENT_Small", bSTR787, bSTR788, boolean394
'--------------------------------------------------
' Parameter 1 : (String) "VELOCITY_OVER_MOMENT_Small"
' Parameter 2 : (String) "Default value"
' Parameter 3 : (String) "Unlocked"
' Parameter 4 : (Boolean) False
'--------------------------------------------------

long395 = settingRepository1.GetAttr("VELOCITY_OVER_MOMENT_ExtraSmall")
'--------------------------------------------------
' Parameter 1 : (String) "VELOCITY_OVER_MOMENT_ExtraSmall"
' Returned value : (Variant) (Long) 1
'--------------------------------------------------

Dim bSTR789
bSTR789 = ""
Dim bSTR790
bSTR790 = ""
Dim boolean395
settingRepository1.GetAttrInfo "VELOCITY_OVER_MOMENT_ExtraSmall", bSTR789, bSTR790, boolean395
'--------------------------------------------------
' Parameter 1 : (String) "VELOCITY_OVER_MOMENT_ExtraSmall"
' Parameter 2 : (String) "Default value"
' Parameter 3 : (String) "Unlocked"
' Parameter 4 : (Boolean) False
'--------------------------------------------------

long396 = settingRepository1.GetAttr("VELOCITY_OVER_MOMENT_Nanometric")
'--------------------------------------------------
' Parameter 1 : (String) "VELOCITY_OVER_MOMENT_Nanometric"
' Returned value : (Variant) (Long) 1
'--------------------------------------------------

Dim bSTR791
bSTR791 = ""
Dim bSTR792
bSTR792 = ""
Dim boolean396
settingRepository1.GetAttrInfo "VELOCITY_OVER_MOMENT_Nanometric", bSTR791, bSTR792, boolean396
'--------------------------------------------------
' Parameter 1 : (String) "VELOCITY_OVER_MOMENT_Nanometric"
' Parameter 2 : (String) "Default value"
' Parameter 3 : (String) "Unlocked"
' Parameter 4 : (Boolean) False
'--------------------------------------------------

long397 = settingRepository1.GetAttr("DISPLACEMENT_OVER_MOMENT")
'--------------------------------------------------
' Parameter 1 : (String) "DISPLACEMENT_OVER_MOMENT"
' Returned value : (Variant) (Long) 1
'--------------------------------------------------

Dim bSTR793
bSTR793 = ""
Dim bSTR794
bSTR794 = ""
Dim boolean397
settingRepository1.GetAttrInfo "DISPLACEMENT_OVER_MOMENT", bSTR793, bSTR794, boolean397
'--------------------------------------------------
' Parameter 1 : (String) "DISPLACEMENT_OVER_MOMENT"
' Parameter 2 : (String) "Default value"
' Parameter 3 : (String) "Unlocked"
' Parameter 4 : (Boolean) False
'--------------------------------------------------

long398 = settingRepository1.GetAttr("DISPLACEMENT_OVER_MOMENT_Large")
'--------------------------------------------------
' Parameter 1 : (String) "DISPLACEMENT_OVER_MOMENT_Large"
' Returned value : (Variant) (Long) 1
'--------------------------------------------------

Dim bSTR795
bSTR795 = ""
Dim bSTR796
bSTR796 = ""
Dim boolean398
settingRepository1.GetAttrInfo "DISPLACEMENT_OVER_MOMENT_Large", bSTR795, bSTR796, boolean398
'--------------------------------------------------
' Parameter 1 : (String) "DISPLACEMENT_OVER_MOMENT_Large"
' Parameter 2 : (String) "Default value"
' Parameter 3 : (String) "Unlocked"
' Parameter 4 : (Boolean) False
'--------------------------------------------------

long399 = settingRepository1.GetAttr("DISPLACEMENT_OVER_MOMENT_ExtraLarge")
'--------------------------------------------------
' Parameter 1 : (String) "DISPLACEMENT_OVER_MOMENT_ExtraLarge"
' Returned value : (Variant) (Long) 1
'--------------------------------------------------

Dim bSTR797
bSTR797 = ""
Dim bSTR798
bSTR798 = ""
Dim boolean399
settingRepository1.GetAttrInfo "DISPLACEMENT_OVER_MOMENT_ExtraLarge", bSTR797, bSTR798, boolean399
'--------------------------------------------------
' Parameter 1 : (String) "DISPLACEMENT_OVER_MOMENT_ExtraLarge"
' Parameter 2 : (String) "Default value"
' Parameter 3 : (String) "Unlocked"
' Parameter 4 : (Boolean) False
'--------------------------------------------------

long400 = settingRepository1.GetAttr("DISPLACEMENT_OVER_MOMENT_Small")
'--------------------------------------------------
' Parameter 1 : (String) "DISPLACEMENT_OVER_MOMENT_Small"
' Returned value : (Variant) (Long) 1
'--------------------------------------------------

Dim bSTR799
bSTR799 = ""
Dim bSTR800
bSTR800 = ""
Dim boolean400
settingRepository1.GetAttrInfo "DISPLACEMENT_OVER_MOMENT_Small", bSTR799, bSTR800, boolean400
'--------------------------------------------------
' Parameter 1 : (String) "DISPLACEMENT_OVER_MOMENT_Small"
' Parameter 2 : (String) "Default value"
' Parameter 3 : (String) "Unlocked"
' Parameter 4 : (Boolean) False
'--------------------------------------------------

long401 = settingRepository1.GetAttr("DISPLACEMENT_OVER_MOMENT_ExtraSmall")
'--------------------------------------------------
' Parameter 1 : (String) "DISPLACEMENT_OVER_MOMENT_ExtraSmall"
' Returned value : (Variant) (Long) 1
'--------------------------------------------------

Dim bSTR801
bSTR801 = ""
Dim bSTR802
bSTR802 = ""
Dim boolean401
settingRepository1.GetAttrInfo "DISPLACEMENT_OVER_MOMENT_ExtraSmall", bSTR801, bSTR802, boolean401
'--------------------------------------------------
' Parameter 1 : (String) "DISPLACEMENT_OVER_MOMENT_ExtraSmall"
' Parameter 2 : (String) "Default value"
' Parameter 3 : (String) "Unlocked"
' Parameter 4 : (Boolean) False
'--------------------------------------------------

long402 = settingRepository1.GetAttr("DISPLACEMENT_OVER_MOMENT_Nanometric")
'--------------------------------------------------
' Parameter 1 : (String) "DISPLACEMENT_OVER_MOMENT_Nanometric"
' Returned value : (Variant) (Long) 1
'--------------------------------------------------

Dim bSTR803
bSTR803 = ""
Dim bSTR804
bSTR804 = ""
Dim boolean402
settingRepository1.GetAttrInfo "DISPLACEMENT_OVER_MOMENT_Nanometric", bSTR803, bSTR804, boolean402
'--------------------------------------------------
' Parameter 1 : (String) "DISPLACEMENT_OVER_MOMENT_Nanometric"
' Parameter 2 : (String) "Default value"
' Parameter 3 : (String) "Unlocked"
' Parameter 4 : (Boolean) False
'--------------------------------------------------

long403 = settingRepository1.GetAttr("ROTATION_OVER_FORCE")
'--------------------------------------------------
' Parameter 1 : (String) "ROTATION_OVER_FORCE"
' Returned value : (Variant) (Long) 1
'--------------------------------------------------

Dim bSTR805
bSTR805 = ""
Dim bSTR806
bSTR806 = ""
Dim boolean403
settingRepository1.GetAttrInfo "ROTATION_OVER_FORCE", bSTR805, bSTR806, boolean403
'--------------------------------------------------
' Parameter 1 : (String) "ROTATION_OVER_FORCE"
' Parameter 2 : (String) "Default value"
' Parameter 3 : (String) "Unlocked"
' Parameter 4 : (Boolean) False
'--------------------------------------------------

long404 = settingRepository1.GetAttr("ROTATION_OVER_FORCE_Large")
'--------------------------------------------------
' Parameter 1 : (String) "ROTATION_OVER_FORCE_Large"
' Returned value : (Variant) (Long) 1
'--------------------------------------------------

Dim bSTR807
bSTR807 = ""
Dim bSTR808
bSTR808 = ""
Dim boolean404
settingRepository1.GetAttrInfo "ROTATION_OVER_FORCE_Large", bSTR807, bSTR808, boolean404
'--------------------------------------------------
' Parameter 1 : (String) "ROTATION_OVER_FORCE_Large"
' Parameter 2 : (String) "Default value"
' Parameter 3 : (String) "Unlocked"
' Parameter 4 : (Boolean) False
'--------------------------------------------------

long405 = settingRepository1.GetAttr("ROTATION_OVER_FORCE_ExtraLarge")
'--------------------------------------------------
' Parameter 1 : (String) "ROTATION_OVER_FORCE_ExtraLarge"
' Returned value : (Variant) (Long) 1
'--------------------------------------------------

Dim bSTR809
bSTR809 = ""
Dim bSTR810
bSTR810 = ""
Dim boolean405
settingRepository1.GetAttrInfo "ROTATION_OVER_FORCE_ExtraLarge", bSTR809, bSTR810, boolean405
'--------------------------------------------------
' Parameter 1 : (String) "ROTATION_OVER_FORCE_ExtraLarge"
' Parameter 2 : (String) "Default value"
' Parameter 3 : (String) "Unlocked"
' Parameter 4 : (Boolean) False
'--------------------------------------------------

long406 = settingRepository1.GetAttr("ROTATION_OVER_FORCE_Small")
'--------------------------------------------------
' Parameter 1 : (String) "ROTATION_OVER_FORCE_Small"
' Returned value : (Variant) (Long) 1
'--------------------------------------------------

Dim bSTR811
bSTR811 = ""
Dim bSTR812
bSTR812 = ""
Dim boolean406
settingRepository1.GetAttrInfo "ROTATION_OVER_FORCE_Small", bSTR811, bSTR812, boolean406
'--------------------------------------------------
' Parameter 1 : (String) "ROTATION_OVER_FORCE_Small"
' Parameter 2 : (String) "Default value"
' Parameter 3 : (String) "Unlocked"
' Parameter 4 : (Boolean) False
'--------------------------------------------------

long407 = settingRepository1.GetAttr("ROTATION_OVER_FORCE_ExtraSmall")
'--------------------------------------------------
' Parameter 1 : (String) "ROTATION_OVER_FORCE_ExtraSmall"
' Returned value : (Variant) (Long) 1
'--------------------------------------------------

Dim bSTR813
bSTR813 = ""
Dim bSTR814
bSTR814 = ""
Dim boolean407
settingRepository1.GetAttrInfo "ROTATION_OVER_FORCE_ExtraSmall", bSTR813, bSTR814, boolean407
'--------------------------------------------------
' Parameter 1 : (String) "ROTATION_OVER_FORCE_ExtraSmall"
' Parameter 2 : (String) "Default value"
' Parameter 3 : (String) "Unlocked"
' Parameter 4 : (Boolean) False
'--------------------------------------------------

long408 = settingRepository1.GetAttr("ROTATION_OVER_FORCE_Nanometric")
'--------------------------------------------------
' Parameter 1 : (String) "ROTATION_OVER_FORCE_Nanometric"
' Returned value : (Variant) (Long) 1
'--------------------------------------------------

Dim bSTR815
bSTR815 = ""
Dim bSTR816
bSTR816 = ""
Dim boolean408
settingRepository1.GetAttrInfo "ROTATION_OVER_FORCE_Nanometric", bSTR815, bSTR816, boolean408
'--------------------------------------------------
' Parameter 1 : (String) "ROTATION_OVER_FORCE_Nanometric"
' Parameter 2 : (String) "Default value"
' Parameter 3 : (String) "Unlocked"
' Parameter 4 : (Boolean) False
'--------------------------------------------------

long409 = settingRepository1.GetAttr("PULSATION_OVER_FORCE")
'--------------------------------------------------
' Parameter 1 : (String) "PULSATION_OVER_FORCE"
' Returned value : (Variant) (Long) 1
'--------------------------------------------------

Dim bSTR817
bSTR817 = ""
Dim bSTR818
bSTR818 = ""
Dim boolean409
settingRepository1.GetAttrInfo "PULSATION_OVER_FORCE", bSTR817, bSTR818, boolean409
'--------------------------------------------------
' Parameter 1 : (String) "PULSATION_OVER_FORCE"
' Parameter 2 : (String) "Default value"
' Parameter 3 : (String) "Unlocked"
' Parameter 4 : (Boolean) False
'--------------------------------------------------

long410 = settingRepository1.GetAttr("PULSATION_OVER_FORCE_Large")
'--------------------------------------------------
' Parameter 1 : (String) "PULSATION_OVER_FORCE_Large"
' Returned value : (Variant) (Long) 1
'--------------------------------------------------

Dim bSTR819
bSTR819 = ""
Dim bSTR820
bSTR820 = ""
Dim boolean410
settingRepository1.GetAttrInfo "PULSATION_OVER_FORCE_Large", bSTR819, bSTR820, boolean410
'--------------------------------------------------
' Parameter 1 : (String) "PULSATION_OVER_FORCE_Large"
' Parameter 2 : (String) "Default value"
' Parameter 3 : (String) "Unlocked"
' Parameter 4 : (Boolean) False
'--------------------------------------------------

long411 = settingRepository1.GetAttr("PULSATION_OVER_FORCE_ExtraLarge")
'--------------------------------------------------
' Parameter 1 : (String) "PULSATION_OVER_FORCE_ExtraLarge"
' Returned value : (Variant) (Long) 1
'--------------------------------------------------

Dim bSTR821
bSTR821 = ""
Dim bSTR822
bSTR822 = ""
Dim boolean411
settingRepository1.GetAttrInfo "PULSATION_OVER_FORCE_ExtraLarge", bSTR821, bSTR822, boolean411
'--------------------------------------------------
' Parameter 1 : (String) "PULSATION_OVER_FORCE_ExtraLarge"
' Parameter 2 : (String) "Default value"
' Parameter 3 : (String) "Unlocked"
' Parameter 4 : (Boolean) False
'--------------------------------------------------

long412 = settingRepository1.GetAttr("PULSATION_OVER_FORCE_Small")
'--------------------------------------------------
' Parameter 1 : (String) "PULSATION_OVER_FORCE_Small"
' Returned value : (Variant) (Long) 1
'--------------------------------------------------

Dim bSTR823
bSTR823 = ""
Dim bSTR824
bSTR824 = ""
Dim boolean412
settingRepository1.GetAttrInfo "PULSATION_OVER_FORCE_Small", bSTR823, bSTR824, boolean412
'--------------------------------------------------
' Parameter 1 : (String) "PULSATION_OVER_FORCE_Small"
' Parameter 2 : (String) "Default value"
' Parameter 3 : (String) "Unlocked"
' Parameter 4 : (Boolean) False
'--------------------------------------------------

long413 = settingRepository1.GetAttr("PULSATION_OVER_FORCE_ExtraSmall")
'--------------------------------------------------
' Parameter 1 : (String) "PULSATION_OVER_FORCE_ExtraSmall"
' Returned value : (Variant) (Long) 1
'--------------------------------------------------

Dim bSTR825
bSTR825 = ""
Dim bSTR826
bSTR826 = ""
Dim boolean413
settingRepository1.GetAttrInfo "PULSATION_OVER_FORCE_ExtraSmall", bSTR825, bSTR826, boolean413
'--------------------------------------------------
' Parameter 1 : (String) "PULSATION_OVER_FORCE_ExtraSmall"
' Parameter 2 : (String) "Default value"
' Parameter 3 : (String) "Unlocked"
' Parameter 4 : (Boolean) False
'--------------------------------------------------

long414 = settingRepository1.GetAttr("PULSATION_OVER_FORCE_Nanometric")
'--------------------------------------------------
' Parameter 1 : (String) "PULSATION_OVER_FORCE_Nanometric"
' Returned value : (Variant) (Long) 1
'--------------------------------------------------

Dim bSTR827
bSTR827 = ""
Dim bSTR828
bSTR828 = ""
Dim boolean414
settingRepository1.GetAttrInfo "PULSATION_OVER_FORCE_Nanometric", bSTR827, bSTR828, boolean414
'--------------------------------------------------
' Parameter 1 : (String) "PULSATION_OVER_FORCE_Nanometric"
' Parameter 2 : (String) "Default value"
' Parameter 3 : (String) "Unlocked"
' Parameter 4 : (Boolean) False
'--------------------------------------------------

long415 = settingRepository1.GetAttr("ROTATIONAL_ACCELERATION_OVER_FORCE")
'--------------------------------------------------
' Parameter 1 : (String) "ROTATIONAL_ACCELERATION_OVER_FORCE"
' Returned value : (Variant) (Long) 1
'--------------------------------------------------

Dim bSTR829
bSTR829 = ""
Dim bSTR830
bSTR830 = ""
Dim boolean415
settingRepository1.GetAttrInfo "ROTATIONAL_ACCELERATION_OVER_FORCE", bSTR829, bSTR830, boolean415
'--------------------------------------------------
' Parameter 1 : (String) "ROTATIONAL_ACCELERATION_OVER_FORCE"
' Parameter 2 : (String) "Default value"
' Parameter 3 : (String) "Unlocked"
' Parameter 4 : (Boolean) False
'--------------------------------------------------

long416 = settingRepository1.GetAttr("ROTATIONAL_ACCELERATION_OVER_FORCE_Large")
'--------------------------------------------------
' Parameter 1 : (String) "ROTATIONAL_ACCELERATION_OVER_FORCE_Large"
' Returned value : (Variant) (Long) 1
'--------------------------------------------------

Dim bSTR831
bSTR831 = ""
Dim bSTR832
bSTR832 = ""
Dim boolean416
settingRepository1.GetAttrInfo "ROTATIONAL_ACCELERATION_OVER_FORCE_Large", bSTR831, bSTR832, boolean416
'--------------------------------------------------
' Parameter 1 : (String) "ROTATIONAL_ACCELERATION_OVER_FORCE_Large"
' Parameter 2 : (String) "Default value"
' Parameter 3 : (String) "Unlocked"
' Parameter 4 : (Boolean) False
'--------------------------------------------------

long417 = settingRepository1.GetAttr("ROTATIONAL_ACCELERATION_OVER_FORCE_ExtraLarge")
'--------------------------------------------------
' Parameter 1 : (String) "ROTATIONAL_ACCELERATION_OVER_FORCE_ExtraLarge"
' Returned value : (Variant) (Long) 1
'--------------------------------------------------

Dim bSTR833
bSTR833 = ""
Dim bSTR834
bSTR834 = ""
Dim boolean417
settingRepository1.GetAttrInfo "ROTATIONAL_ACCELERATION_OVER_FORCE_ExtraLarge", bSTR833, bSTR834, boolean417
'--------------------------------------------------
' Parameter 1 : (String) "ROTATIONAL_ACCELERATION_OVER_FORCE_ExtraLarge"
' Parameter 2 : (String) "Default value"
' Parameter 3 : (String) "Unlocked"
' Parameter 4 : (Boolean) False
'--------------------------------------------------

long418 = settingRepository1.GetAttr("ROTATIONAL_ACCELERATION_OVER_FORCE_Small")
'--------------------------------------------------
' Parameter 1 : (String) "ROTATIONAL_ACCELERATION_OVER_FORCE_Small"
' Returned value : (Variant) (Long) 1
'--------------------------------------------------

Dim bSTR835
bSTR835 = ""
Dim bSTR836
bSTR836 = ""
Dim boolean418
settingRepository1.GetAttrInfo "ROTATIONAL_ACCELERATION_OVER_FORCE_Small", bSTR835, bSTR836, boolean418
'--------------------------------------------------
' Parameter 1 : (String) "ROTATIONAL_ACCELERATION_OVER_FORCE_Small"
' Parameter 2 : (String) "Default value"
' Parameter 3 : (String) "Unlocked"
' Parameter 4 : (Boolean) False
'--------------------------------------------------

long419 = settingRepository1.GetAttr("ROTATIONAL_ACCELERATION_OVER_FORCE_ExtraSmall")
'--------------------------------------------------
' Parameter 1 : (String) "ROTATIONAL_ACCELERATION_OVER_FORCE_ExtraSmall"
' Returned value : (Variant) (Long) 1
'--------------------------------------------------

Dim bSTR837
bSTR837 = ""
Dim bSTR838
bSTR838 = ""
Dim boolean419
settingRepository1.GetAttrInfo "ROTATIONAL_ACCELERATION_OVER_FORCE_ExtraSmall", bSTR837, bSTR838, boolean419
'--------------------------------------------------
' Parameter 1 : (String) "ROTATIONAL_ACCELERATION_OVER_FORCE_ExtraSmall"
' Parameter 2 : (String) "Default value"
' Parameter 3 : (String) "Unlocked"
' Parameter 4 : (Boolean) False
'--------------------------------------------------

long420 = settingRepository1.GetAttr("ROTATIONAL_ACCELERATION_OVER_FORCE_Nanometric")
'--------------------------------------------------
' Parameter 1 : (String) "ROTATIONAL_ACCELERATION_OVER_FORCE_Nanometric"
' Returned value : (Variant) (Long) 1
'--------------------------------------------------

Dim bSTR839
bSTR839 = ""
Dim bSTR840
bSTR840 = ""
Dim boolean420
settingRepository1.GetAttrInfo "ROTATIONAL_ACCELERATION_OVER_FORCE_Nanometric", bSTR839, bSTR840, boolean420
'--------------------------------------------------
' Parameter 1 : (String) "ROTATIONAL_ACCELERATION_OVER_FORCE_Nanometric"
' Parameter 2 : (String) "Default value"
' Parameter 3 : (String) "Unlocked"
' Parameter 4 : (Boolean) False
'--------------------------------------------------

long421 = settingRepository1.GetAttr("ROTATION_OVER_MOMENT")
'--------------------------------------------------
' Parameter 1 : (String) "ROTATION_OVER_MOMENT"
' Returned value : (Variant) (Long) 1
'--------------------------------------------------

Dim bSTR841
bSTR841 = ""
Dim bSTR842
bSTR842 = ""
Dim boolean421
settingRepository1.GetAttrInfo "ROTATION_OVER_MOMENT", bSTR841, bSTR842, boolean421
'--------------------------------------------------
' Parameter 1 : (String) "ROTATION_OVER_MOMENT"
' Parameter 2 : (String) "Default value"
' Parameter 3 : (String) "Unlocked"
' Parameter 4 : (Boolean) False
'--------------------------------------------------

long422 = settingRepository1.GetAttr("ROTATION_OVER_MOMENT_Large")
'--------------------------------------------------
' Parameter 1 : (String) "ROTATION_OVER_MOMENT_Large"
' Returned value : (Variant) (Long) 1
'--------------------------------------------------

Dim bSTR843
bSTR843 = ""
Dim bSTR844
bSTR844 = ""
Dim boolean422
settingRepository1.GetAttrInfo "ROTATION_OVER_MOMENT_Large", bSTR843, bSTR844, boolean422
'--------------------------------------------------
' Parameter 1 : (String) "ROTATION_OVER_MOMENT_Large"
' Parameter 2 : (String) "Default value"
' Parameter 3 : (String) "Unlocked"
' Parameter 4 : (Boolean) False
'--------------------------------------------------

long423 = settingRepository1.GetAttr("ROTATION_OVER_MOMENT_ExtraLarge")
'--------------------------------------------------
' Parameter 1 : (String) "ROTATION_OVER_MOMENT_ExtraLarge"
' Returned value : (Variant) (Long) 1
'--------------------------------------------------

Dim bSTR845
bSTR845 = ""
Dim bSTR846
bSTR846 = ""
Dim boolean423
settingRepository1.GetAttrInfo "ROTATION_OVER_MOMENT_ExtraLarge", bSTR845, bSTR846, boolean423
'--------------------------------------------------
' Parameter 1 : (String) "ROTATION_OVER_MOMENT_ExtraLarge"
' Parameter 2 : (String) "Default value"
' Parameter 3 : (String) "Unlocked"
' Parameter 4 : (Boolean) False
'--------------------------------------------------

long424 = settingRepository1.GetAttr("ROTATION_OVER_MOMENT_Small")
'--------------------------------------------------
' Parameter 1 : (String) "ROTATION_OVER_MOMENT_Small"
' Returned value : (Variant) (Long) 1
'--------------------------------------------------

Dim bSTR847
bSTR847 = ""
Dim bSTR848
bSTR848 = ""
Dim boolean424
settingRepository1.GetAttrInfo "ROTATION_OVER_MOMENT_Small", bSTR847, bSTR848, boolean424
'--------------------------------------------------
' Parameter 1 : (String) "ROTATION_OVER_MOMENT_Small"
' Parameter 2 : (String) "Default value"
' Parameter 3 : (String) "Unlocked"
' Parameter 4 : (Boolean) False
'--------------------------------------------------

long425 = settingRepository1.GetAttr("ROTATION_OVER_MOMENT_ExtraSmall")
'--------------------------------------------------
' Parameter 1 : (String) "ROTATION_OVER_MOMENT_ExtraSmall"
' Returned value : (Variant) (Long) 1
'--------------------------------------------------

Dim bSTR849
bSTR849 = ""
Dim bSTR850
bSTR850 = ""
Dim boolean425
settingRepository1.GetAttrInfo "ROTATION_OVER_MOMENT_ExtraSmall", bSTR849, bSTR850, boolean425
'--------------------------------------------------
' Parameter 1 : (String) "ROTATION_OVER_MOMENT_ExtraSmall"
' Parameter 2 : (String) "Default value"
' Parameter 3 : (String) "Unlocked"
' Parameter 4 : (Boolean) False
'--------------------------------------------------

long426 = settingRepository1.GetAttr("ROTATION_OVER_MOMENT_Nanometric")
'--------------------------------------------------
' Parameter 1 : (String) "ROTATION_OVER_MOMENT_Nanometric"
' Returned value : (Variant) (Long) 1
'--------------------------------------------------

Dim bSTR851
bSTR851 = ""
Dim bSTR852
bSTR852 = ""
Dim boolean426
settingRepository1.GetAttrInfo "ROTATION_OVER_MOMENT_Nanometric", bSTR851, bSTR852, boolean426
'--------------------------------------------------
' Parameter 1 : (String) "ROTATION_OVER_MOMENT_Nanometric"
' Parameter 2 : (String) "Default value"
' Parameter 3 : (String) "Unlocked"
' Parameter 4 : (Boolean) False
'--------------------------------------------------

long427 = settingRepository1.GetAttr("PULSATION_OVER_MOMENT")
'--------------------------------------------------
' Parameter 1 : (String) "PULSATION_OVER_MOMENT"
' Returned value : (Variant) (Long) 1
'--------------------------------------------------

Dim bSTR853
bSTR853 = ""
Dim bSTR854
bSTR854 = ""
Dim boolean427
settingRepository1.GetAttrInfo "PULSATION_OVER_MOMENT", bSTR853, bSTR854, boolean427
'--------------------------------------------------
' Parameter 1 : (String) "PULSATION_OVER_MOMENT"
' Parameter 2 : (String) "Default value"
' Parameter 3 : (String) "Unlocked"
' Parameter 4 : (Boolean) False
'--------------------------------------------------

long428 = settingRepository1.GetAttr("PULSATION_OVER_MOMENT_Large")
'--------------------------------------------------
' Parameter 1 : (String) "PULSATION_OVER_MOMENT_Large"
' Returned value : (Variant) (Long) 1
'--------------------------------------------------

Dim bSTR855
bSTR855 = ""
Dim bSTR856
bSTR856 = ""
Dim boolean428
settingRepository1.GetAttrInfo "PULSATION_OVER_MOMENT_Large", bSTR855, bSTR856, boolean428
'--------------------------------------------------
' Parameter 1 : (String) "PULSATION_OVER_MOMENT_Large"
' Parameter 2 : (String) "Default value"
' Parameter 3 : (String) "Unlocked"
' Parameter 4 : (Boolean) False
'--------------------------------------------------

long429 = settingRepository1.GetAttr("PULSATION_OVER_MOMENT_ExtraLarge")
'--------------------------------------------------
' Parameter 1 : (String) "PULSATION_OVER_MOMENT_ExtraLarge"
' Returned value : (Variant) (Long) 1
'--------------------------------------------------

Dim bSTR857
bSTR857 = ""
Dim bSTR858
bSTR858 = ""
Dim boolean429
settingRepository1.GetAttrInfo "PULSATION_OVER_MOMENT_ExtraLarge", bSTR857, bSTR858, boolean429
'--------------------------------------------------
' Parameter 1 : (String) "PULSATION_OVER_MOMENT_ExtraLarge"
' Parameter 2 : (String) "Default value"
' Parameter 3 : (String) "Unlocked"
' Parameter 4 : (Boolean) False
'--------------------------------------------------

long430 = settingRepository1.GetAttr("PULSATION_OVER_MOMENT_Small")
'--------------------------------------------------
' Parameter 1 : (String) "PULSATION_OVER_MOMENT_Small"
' Returned value : (Variant) (Long) 1
'--------------------------------------------------

Dim bSTR859
bSTR859 = ""
Dim bSTR860
bSTR860 = ""
Dim boolean430
settingRepository1.GetAttrInfo "PULSATION_OVER_MOMENT_Small", bSTR859, bSTR860, boolean430
'--------------------------------------------------
' Parameter 1 : (String) "PULSATION_OVER_MOMENT_Small"
' Parameter 2 : (String) "Default value"
' Parameter 3 : (String) "Unlocked"
' Parameter 4 : (Boolean) False
'--------------------------------------------------

long431 = settingRepository1.GetAttr("PULSATION_OVER_MOMENT_ExtraSmall")
'--------------------------------------------------
' Parameter 1 : (String) "PULSATION_OVER_MOMENT_ExtraSmall"
' Returned value : (Variant) (Long) 1
'--------------------------------------------------

Dim bSTR861
bSTR861 = ""
Dim bSTR862
bSTR862 = ""
Dim boolean431
settingRepository1.GetAttrInfo "PULSATION_OVER_MOMENT_ExtraSmall", bSTR861, bSTR862, boolean431
'--------------------------------------------------
' Parameter 1 : (String) "PULSATION_OVER_MOMENT_ExtraSmall"
' Parameter 2 : (String) "Default value"
' Parameter 3 : (String) "Unlocked"
' Parameter 4 : (Boolean) False
'--------------------------------------------------

long432 = settingRepository1.GetAttr("PULSATION_OVER_MOMENT_Nanometric")
'--------------------------------------------------
' Parameter 1 : (String) "PULSATION_OVER_MOMENT_Nanometric"
' Returned value : (Variant) (Long) 1
'--------------------------------------------------

Dim bSTR863
bSTR863 = ""
Dim bSTR864
bSTR864 = ""
Dim boolean432
settingRepository1.GetAttrInfo "PULSATION_OVER_MOMENT_Nanometric", bSTR863, bSTR864, boolean432
'--------------------------------------------------
' Parameter 1 : (String) "PULSATION_OVER_MOMENT_Nanometric"
' Parameter 2 : (String) "Default value"
' Parameter 3 : (String) "Unlocked"
' Parameter 4 : (Boolean) False
'--------------------------------------------------

long433 = settingRepository1.GetAttr("ROTATIONAL_ACCELERATION_OVER_MOMENT")
'--------------------------------------------------
' Parameter 1 : (String) "ROTATIONAL_ACCELERATION_OVER_MOMENT"
' Returned value : (Variant) (Long) 1
'--------------------------------------------------

Dim bSTR865
bSTR865 = ""
Dim bSTR866
bSTR866 = ""
Dim boolean433
settingRepository1.GetAttrInfo "ROTATIONAL_ACCELERATION_OVER_MOMENT", bSTR865, bSTR866, boolean433
'--------------------------------------------------
' Parameter 1 : (String) "ROTATIONAL_ACCELERATION_OVER_MOMENT"
' Parameter 2 : (String) "Default value"
' Parameter 3 : (String) "Unlocked"
' Parameter 4 : (Boolean) False
'--------------------------------------------------

long434 = settingRepository1.GetAttr("ROTATIONAL_ACCELERATION_OVER_MOMENT_Large")
'--------------------------------------------------
' Parameter 1 : (String) "ROTATIONAL_ACCELERATION_OVER_MOMENT_Large"
' Returned value : (Variant) (Long) 1
'--------------------------------------------------

Dim bSTR867
bSTR867 = ""
Dim bSTR868
bSTR868 = ""
Dim boolean434
settingRepository1.GetAttrInfo "ROTATIONAL_ACCELERATION_OVER_MOMENT_Large", bSTR867, bSTR868, boolean434
'--------------------------------------------------
' Parameter 1 : (String) "ROTATIONAL_ACCELERATION_OVER_MOMENT_Large"
' Parameter 2 : (String) "Default value"
' Parameter 3 : (String) "Unlocked"
' Parameter 4 : (Boolean) False
'--------------------------------------------------

long435 = settingRepository1.GetAttr("ROTATIONAL_ACCELERATION_OVER_MOMENT_ExtraLarge")
'--------------------------------------------------
' Parameter 1 : (String) "ROTATIONAL_ACCELERATION_OVER_MOMENT_ExtraLarge"
' Returned value : (Variant) (Long) 1
'--------------------------------------------------

Dim bSTR869
bSTR869 = ""
Dim bSTR870
bSTR870 = ""
Dim boolean435
settingRepository1.GetAttrInfo "ROTATIONAL_ACCELERATION_OVER_MOMENT_ExtraLarge", bSTR869, bSTR870, boolean435
'--------------------------------------------------
' Parameter 1 : (String) "ROTATIONAL_ACCELERATION_OVER_MOMENT_ExtraLarge"
' Parameter 2 : (String) "Default value"
' Parameter 3 : (String) "Unlocked"
' Parameter 4 : (Boolean) False
'--------------------------------------------------

long436 = settingRepository1.GetAttr("ROTATIONAL_ACCELERATION_OVER_MOMENT_Small")
'--------------------------------------------------
' Parameter 1 : (String) "ROTATIONAL_ACCELERATION_OVER_MOMENT_Small"
' Returned value : (Variant) (Long) 1
'--------------------------------------------------

Dim bSTR871
bSTR871 = ""
Dim bSTR872
bSTR872 = ""
Dim boolean436
settingRepository1.GetAttrInfo "ROTATIONAL_ACCELERATION_OVER_MOMENT_Small", bSTR871, bSTR872, boolean436
'--------------------------------------------------
' Parameter 1 : (String) "ROTATIONAL_ACCELERATION_OVER_MOMENT_Small"
' Parameter 2 : (String) "Default value"
' Parameter 3 : (String) "Unlocked"
' Parameter 4 : (Boolean) False
'--------------------------------------------------

long437 = settingRepository1.GetAttr("ROTATIONAL_ACCELERATION_OVER_MOMENT_ExtraSmall")
'--------------------------------------------------
' Parameter 1 : (String) "ROTATIONAL_ACCELERATION_OVER_MOMENT_ExtraSmall"
' Returned value : (Variant) (Long) 1
'--------------------------------------------------

Dim bSTR873
bSTR873 = ""
Dim bSTR874
bSTR874 = ""
Dim boolean437
settingRepository1.GetAttrInfo "ROTATIONAL_ACCELERATION_OVER_MOMENT_ExtraSmall", bSTR873, bSTR874, boolean437
'--------------------------------------------------
' Parameter 1 : (String) "ROTATIONAL_ACCELERATION_OVER_MOMENT_ExtraSmall"
' Parameter 2 : (String) "Default value"
' Parameter 3 : (String) "Unlocked"
' Parameter 4 : (Boolean) False
'--------------------------------------------------

long438 = settingRepository1.GetAttr("ROTATIONAL_ACCELERATION_OVER_MOMENT_Nanometric")
'--------------------------------------------------
' Parameter 1 : (String) "ROTATIONAL_ACCELERATION_OVER_MOMENT_Nanometric"
' Returned value : (Variant) (Long) 1
'--------------------------------------------------

Dim bSTR875
bSTR875 = ""
Dim bSTR876
bSTR876 = ""
Dim boolean438
settingRepository1.GetAttrInfo "ROTATIONAL_ACCELERATION_OVER_MOMENT_Nanometric", bSTR875, bSTR876, boolean438
'--------------------------------------------------
' Parameter 1 : (String) "ROTATIONAL_ACCELERATION_OVER_MOMENT_Nanometric"
' Parameter 2 : (String) "Default value"
' Parameter 3 : (String) "Unlocked"
' Parameter 4 : (Boolean) False
'--------------------------------------------------

long439 = settingRepository1.GetAttr("PRESSURE_OVER_MOMENT")
'--------------------------------------------------
' Parameter 1 : (String) "PRESSURE_OVER_MOMENT"
' Returned value : (Variant) (Long) 1
'--------------------------------------------------

Dim bSTR877
bSTR877 = ""
Dim bSTR878
bSTR878 = ""
Dim boolean439
settingRepository1.GetAttrInfo "PRESSURE_OVER_MOMENT", bSTR877, bSTR878, boolean439
'--------------------------------------------------
' Parameter 1 : (String) "PRESSURE_OVER_MOMENT"
' Parameter 2 : (String) "Default value"
' Parameter 3 : (String) "Unlocked"
' Parameter 4 : (Boolean) False
'--------------------------------------------------

long440 = settingRepository1.GetAttr("PRESSURE_OVER_MOMENT_Large")
'--------------------------------------------------
' Parameter 1 : (String) "PRESSURE_OVER_MOMENT_Large"
' Returned value : (Variant) (Long) 1
'--------------------------------------------------

Dim bSTR879
bSTR879 = ""
Dim bSTR880
bSTR880 = ""
Dim boolean440
settingRepository1.GetAttrInfo "PRESSURE_OVER_MOMENT_Large", bSTR879, bSTR880, boolean440
'--------------------------------------------------
' Parameter 1 : (String) "PRESSURE_OVER_MOMENT_Large"
' Parameter 2 : (String) "Default value"
' Parameter 3 : (String) "Unlocked"
' Parameter 4 : (Boolean) False
'--------------------------------------------------

long441 = settingRepository1.GetAttr("PRESSURE_OVER_MOMENT_ExtraLarge")
'--------------------------------------------------
' Parameter 1 : (String) "PRESSURE_OVER_MOMENT_ExtraLarge"
' Returned value : (Variant) (Long) 1
'--------------------------------------------------

Dim bSTR881
bSTR881 = ""
Dim bSTR882
bSTR882 = ""
Dim boolean441
settingRepository1.GetAttrInfo "PRESSURE_OVER_MOMENT_ExtraLarge", bSTR881, bSTR882, boolean441
'--------------------------------------------------
' Parameter 1 : (String) "PRESSURE_OVER_MOMENT_ExtraLarge"
' Parameter 2 : (String) "Default value"
' Parameter 3 : (String) "Unlocked"
' Parameter 4 : (Boolean) False
'--------------------------------------------------

long442 = settingRepository1.GetAttr("PRESSURE_OVER_MOMENT_Small")
'--------------------------------------------------
' Parameter 1 : (String) "PRESSURE_OVER_MOMENT_Small"
' Returned value : (Variant) (Long) 1
'--------------------------------------------------

Dim bSTR883
bSTR883 = ""
Dim bSTR884
bSTR884 = ""
Dim boolean442
settingRepository1.GetAttrInfo "PRESSURE_OVER_MOMENT_Small", bSTR883, bSTR884, boolean442
'--------------------------------------------------
' Parameter 1 : (String) "PRESSURE_OVER_MOMENT_Small"
' Parameter 2 : (String) "Default value"
' Parameter 3 : (String) "Unlocked"
' Parameter 4 : (Boolean) False
'--------------------------------------------------

long443 = settingRepository1.GetAttr("PRESSURE_OVER_MOMENT_ExtraSmall")
'--------------------------------------------------
' Parameter 1 : (String) "PRESSURE_OVER_MOMENT_ExtraSmall"
' Returned value : (Variant) (Long) 1
'--------------------------------------------------

Dim bSTR885
bSTR885 = ""
Dim bSTR886
bSTR886 = ""
Dim boolean443
settingRepository1.GetAttrInfo "PRESSURE_OVER_MOMENT_ExtraSmall", bSTR885, bSTR886, boolean443
'--------------------------------------------------
' Parameter 1 : (String) "PRESSURE_OVER_MOMENT_ExtraSmall"
' Parameter 2 : (String) "Default value"
' Parameter 3 : (String) "Unlocked"
' Parameter 4 : (Boolean) False
'--------------------------------------------------

long444 = settingRepository1.GetAttr("PRESSURE_OVER_MOMENT_Nanometric")
'--------------------------------------------------
' Parameter 1 : (String) "PRESSURE_OVER_MOMENT_Nanometric"
' Returned value : (Variant) (Long) 1
'--------------------------------------------------

Dim bSTR887
bSTR887 = ""
Dim bSTR888
bSTR888 = ""
Dim boolean444
settingRepository1.GetAttrInfo "PRESSURE_OVER_MOMENT_Nanometric", bSTR887, bSTR888, boolean444
'--------------------------------------------------
' Parameter 1 : (String) "PRESSURE_OVER_MOMENT_Nanometric"
' Parameter 2 : (String) "Default value"
' Parameter 3 : (String) "Unlocked"
' Parameter 4 : (Boolean) False
'--------------------------------------------------

long445 = settingRepository1.GetAttr("FORCE_OVER_DISPLACEMENT")
'--------------------------------------------------
' Parameter 1 : (String) "FORCE_OVER_DISPLACEMENT"
' Returned value : (Variant) (Long) 1
'--------------------------------------------------

Dim bSTR889
bSTR889 = ""
Dim bSTR890
bSTR890 = ""
Dim boolean445
settingRepository1.GetAttrInfo "FORCE_OVER_DISPLACEMENT", bSTR889, bSTR890, boolean445
'--------------------------------------------------
' Parameter 1 : (String) "FORCE_OVER_DISPLACEMENT"
' Parameter 2 : (String) "Default value"
' Parameter 3 : (String) "Unlocked"
' Parameter 4 : (Boolean) False
'--------------------------------------------------

long446 = settingRepository1.GetAttr("FORCE_OVER_DISPLACEMENT_Large")
'--------------------------------------------------
' Parameter 1 : (String) "FORCE_OVER_DISPLACEMENT_Large"
' Returned value : (Variant) (Long) 1
'--------------------------------------------------

Dim bSTR891
bSTR891 = ""
Dim bSTR892
bSTR892 = ""
Dim boolean446
settingRepository1.GetAttrInfo "FORCE_OVER_DISPLACEMENT_Large", bSTR891, bSTR892, boolean446
'--------------------------------------------------
' Parameter 1 : (String) "FORCE_OVER_DISPLACEMENT_Large"
' Parameter 2 : (String) "Default value"
' Parameter 3 : (String) "Unlocked"
' Parameter 4 : (Boolean) False
'--------------------------------------------------

long447 = settingRepository1.GetAttr("FORCE_OVER_DISPLACEMENT_ExtraLarge")
'--------------------------------------------------
' Parameter 1 : (String) "FORCE_OVER_DISPLACEMENT_ExtraLarge"
' Returned value : (Variant) (Long) 1
'--------------------------------------------------

Dim bSTR893
bSTR893 = ""
Dim bSTR894
bSTR894 = ""
Dim boolean447
settingRepository1.GetAttrInfo "FORCE_OVER_DISPLACEMENT_ExtraLarge", bSTR893, bSTR894, boolean447
'--------------------------------------------------
' Parameter 1 : (String) "FORCE_OVER_DISPLACEMENT_ExtraLarge"
' Parameter 2 : (String) "Default value"
' Parameter 3 : (String) "Unlocked"
' Parameter 4 : (Boolean) False
'--------------------------------------------------

long448 = settingRepository1.GetAttr("FORCE_OVER_DISPLACEMENT_Small")
'--------------------------------------------------
' Parameter 1 : (String) "FORCE_OVER_DISPLACEMENT_Small"
' Returned value : (Variant) (Long) 1
'--------------------------------------------------

Dim bSTR895
bSTR895 = ""
Dim bSTR896
bSTR896 = ""
Dim boolean448
settingRepository1.GetAttrInfo "FORCE_OVER_DISPLACEMENT_Small", bSTR895, bSTR896, boolean448
'--------------------------------------------------
' Parameter 1 : (String) "FORCE_OVER_DISPLACEMENT_Small"
' Parameter 2 : (String) "Default value"
' Parameter 3 : (String) "Unlocked"
' Parameter 4 : (Boolean) False
'--------------------------------------------------

long449 = settingRepository1.GetAttr("FORCE_OVER_DISPLACEMENT_ExtraSmall")
'--------------------------------------------------
' Parameter 1 : (String) "FORCE_OVER_DISPLACEMENT_ExtraSmall"
' Returned value : (Variant) (Long) 1
'--------------------------------------------------

Dim bSTR897
bSTR897 = ""
Dim bSTR898
bSTR898 = ""
Dim boolean449
settingRepository1.GetAttrInfo "FORCE_OVER_DISPLACEMENT_ExtraSmall", bSTR897, bSTR898, boolean449
'--------------------------------------------------
' Parameter 1 : (String) "FORCE_OVER_DISPLACEMENT_ExtraSmall"
' Parameter 2 : (String) "Default value"
' Parameter 3 : (String) "Unlocked"
' Parameter 4 : (Boolean) False
'--------------------------------------------------

long450 = settingRepository1.GetAttr("FORCE_OVER_DISPLACEMENT_Nanometric")
'--------------------------------------------------
' Parameter 1 : (String) "FORCE_OVER_DISPLACEMENT_Nanometric"
' Returned value : (Variant) (Long) 1
'--------------------------------------------------

Dim bSTR899
bSTR899 = ""
Dim bSTR900
bSTR900 = ""
Dim boolean450
settingRepository1.GetAttrInfo "FORCE_OVER_DISPLACEMENT_Nanometric", bSTR899, bSTR900, boolean450
'--------------------------------------------------
' Parameter 1 : (String) "FORCE_OVER_DISPLACEMENT_Nanometric"
' Parameter 2 : (String) "Default value"
' Parameter 3 : (String) "Unlocked"
' Parameter 4 : (Boolean) False
'--------------------------------------------------

long451 = settingRepository1.GetAttr("FORCE_OVER_ROTATION")
'--------------------------------------------------
' Parameter 1 : (String) "FORCE_OVER_ROTATION"
' Returned value : (Variant) (Long) 1
'--------------------------------------------------

Dim bSTR901
bSTR901 = ""
Dim bSTR902
bSTR902 = ""
Dim boolean451
settingRepository1.GetAttrInfo "FORCE_OVER_ROTATION", bSTR901, bSTR902, boolean451
'--------------------------------------------------
' Parameter 1 : (String) "FORCE_OVER_ROTATION"
' Parameter 2 : (String) "Default value"
' Parameter 3 : (String) "Unlocked"
' Parameter 4 : (Boolean) False
'--------------------------------------------------

long452 = settingRepository1.GetAttr("FORCE_OVER_ROTATION_Large")
'--------------------------------------------------
' Parameter 1 : (String) "FORCE_OVER_ROTATION_Large"
' Returned value : (Variant) (Long) 1
'--------------------------------------------------

Dim bSTR903
bSTR903 = ""
Dim bSTR904
bSTR904 = ""
Dim boolean452
settingRepository1.GetAttrInfo "FORCE_OVER_ROTATION_Large", bSTR903, bSTR904, boolean452
'--------------------------------------------------
' Parameter 1 : (String) "FORCE_OVER_ROTATION_Large"
' Parameter 2 : (String) "Default value"
' Parameter 3 : (String) "Unlocked"
' Parameter 4 : (Boolean) False
'--------------------------------------------------

long453 = settingRepository1.GetAttr("FORCE_OVER_ROTATION_ExtraLarge")
'--------------------------------------------------
' Parameter 1 : (String) "FORCE_OVER_ROTATION_ExtraLarge"
' Returned value : (Variant) (Long) 1
'--------------------------------------------------

Dim bSTR905
bSTR905 = ""
Dim bSTR906
bSTR906 = ""
Dim boolean453
settingRepository1.GetAttrInfo "FORCE_OVER_ROTATION_ExtraLarge", bSTR905, bSTR906, boolean453
'--------------------------------------------------
' Parameter 1 : (String) "FORCE_OVER_ROTATION_ExtraLarge"
' Parameter 2 : (String) "Default value"
' Parameter 3 : (String) "Unlocked"
' Parameter 4 : (Boolean) False
'--------------------------------------------------

long454 = settingRepository1.GetAttr("FORCE_OVER_ROTATION_Small")
'--------------------------------------------------
' Parameter 1 : (String) "FORCE_OVER_ROTATION_Small"
' Returned value : (Variant) (Long) 1
'--------------------------------------------------

Dim bSTR907
bSTR907 = ""
Dim bSTR908
bSTR908 = ""
Dim boolean454
settingRepository1.GetAttrInfo "FORCE_OVER_ROTATION_Small", bSTR907, bSTR908, boolean454
'--------------------------------------------------
' Parameter 1 : (String) "FORCE_OVER_ROTATION_Small"
' Parameter 2 : (String) "Default value"
' Parameter 3 : (String) "Unlocked"
' Parameter 4 : (Boolean) False
'--------------------------------------------------

long455 = settingRepository1.GetAttr("FORCE_OVER_ROTATION_ExtraSmall")
'--------------------------------------------------
' Parameter 1 : (String) "FORCE_OVER_ROTATION_ExtraSmall"
' Returned value : (Variant) (Long) 1
'--------------------------------------------------

Dim bSTR909
bSTR909 = ""
Dim bSTR910
bSTR910 = ""
Dim boolean455
settingRepository1.GetAttrInfo "FORCE_OVER_ROTATION_ExtraSmall", bSTR909, bSTR910, boolean455
'--------------------------------------------------
' Parameter 1 : (String) "FORCE_OVER_ROTATION_ExtraSmall"
' Parameter 2 : (String) "Default value"
' Parameter 3 : (String) "Unlocked"
' Parameter 4 : (Boolean) False
'--------------------------------------------------

long456 = settingRepository1.GetAttr("FORCE_OVER_ROTATION_Nanometric")
'--------------------------------------------------
' Parameter 1 : (String) "FORCE_OVER_ROTATION_Nanometric"
' Returned value : (Variant) (Long) 1
'--------------------------------------------------

Dim bSTR911
bSTR911 = ""
Dim bSTR912
bSTR912 = ""
Dim boolean456
settingRepository1.GetAttrInfo "FORCE_OVER_ROTATION_Nanometric", bSTR911, bSTR912, boolean456
'--------------------------------------------------
' Parameter 1 : (String) "FORCE_OVER_ROTATION_Nanometric"
' Parameter 2 : (String) "Default value"
' Parameter 3 : (String) "Unlocked"
' Parameter 4 : (Boolean) False
'--------------------------------------------------

long457 = settingRepository1.GetAttr("MOMENT_OVER_DISPLACEMENT")
'--------------------------------------------------
' Parameter 1 : (String) "MOMENT_OVER_DISPLACEMENT"
' Returned value : (Variant) (Long) 1
'--------------------------------------------------

Dim bSTR913
bSTR913 = ""
Dim bSTR914
bSTR914 = ""
Dim boolean457
settingRepository1.GetAttrInfo "MOMENT_OVER_DISPLACEMENT", bSTR913, bSTR914, boolean457
'--------------------------------------------------
' Parameter 1 : (String) "MOMENT_OVER_DISPLACEMENT"
' Parameter 2 : (String) "Default value"
' Parameter 3 : (String) "Unlocked"
' Parameter 4 : (Boolean) False
'--------------------------------------------------

long458 = settingRepository1.GetAttr("MOMENT_OVER_DISPLACEMENT_Large")
'--------------------------------------------------
' Parameter 1 : (String) "MOMENT_OVER_DISPLACEMENT_Large"
' Returned value : (Variant) (Long) 1
'--------------------------------------------------

Dim bSTR915
bSTR915 = ""
Dim bSTR916
bSTR916 = ""
Dim boolean458
settingRepository1.GetAttrInfo "MOMENT_OVER_DISPLACEMENT_Large", bSTR915, bSTR916, boolean458
'--------------------------------------------------
' Parameter 1 : (String) "MOMENT_OVER_DISPLACEMENT_Large"
' Parameter 2 : (String) "Default value"
' Parameter 3 : (String) "Unlocked"
' Parameter 4 : (Boolean) False
'--------------------------------------------------

long459 = settingRepository1.GetAttr("MOMENT_OVER_DISPLACEMENT_ExtraLarge")
'--------------------------------------------------
' Parameter 1 : (String) "MOMENT_OVER_DISPLACEMENT_ExtraLarge"
' Returned value : (Variant) (Long) 1
'--------------------------------------------------

Dim bSTR917
bSTR917 = ""
Dim bSTR918
bSTR918 = ""
Dim boolean459
settingRepository1.GetAttrInfo "MOMENT_OVER_DISPLACEMENT_ExtraLarge", bSTR917, bSTR918, boolean459
'--------------------------------------------------
' Parameter 1 : (String) "MOMENT_OVER_DISPLACEMENT_ExtraLarge"
' Parameter 2 : (String) "Default value"
' Parameter 3 : (String) "Unlocked"
' Parameter 4 : (Boolean) False
'--------------------------------------------------

long460 = settingRepository1.GetAttr("MOMENT_OVER_DISPLACEMENT_Small")
'--------------------------------------------------
' Parameter 1 : (String) "MOMENT_OVER_DISPLACEMENT_Small"
' Returned value : (Variant) (Long) 1
'--------------------------------------------------

Dim bSTR919
bSTR919 = ""
Dim bSTR920
bSTR920 = ""
Dim boolean460
settingRepository1.GetAttrInfo "MOMENT_OVER_DISPLACEMENT_Small", bSTR919, bSTR920, boolean460
'--------------------------------------------------
' Parameter 1 : (String) "MOMENT_OVER_DISPLACEMENT_Small"
' Parameter 2 : (String) "Default value"
' Parameter 3 : (String) "Unlocked"
' Parameter 4 : (Boolean) False
'--------------------------------------------------

long461 = settingRepository1.GetAttr("MOMENT_OVER_DISPLACEMENT_ExtraSmall")
'--------------------------------------------------
' Parameter 1 : (String) "MOMENT_OVER_DISPLACEMENT_ExtraSmall"
' Returned value : (Variant) (Long) 1
'--------------------------------------------------

Dim bSTR921
bSTR921 = ""
Dim bSTR922
bSTR922 = ""
Dim boolean461
settingRepository1.GetAttrInfo "MOMENT_OVER_DISPLACEMENT_ExtraSmall", bSTR921, bSTR922, boolean461
'--------------------------------------------------
' Parameter 1 : (String) "MOMENT_OVER_DISPLACEMENT_ExtraSmall"
' Parameter 2 : (String) "Default value"
' Parameter 3 : (String) "Unlocked"
' Parameter 4 : (Boolean) False
'--------------------------------------------------

long462 = settingRepository1.GetAttr("MOMENT_OVER_DISPLACEMENT_Nanometric")
'--------------------------------------------------
' Parameter 1 : (String) "MOMENT_OVER_DISPLACEMENT_Nanometric"
' Returned value : (Variant) (Long) 1
'--------------------------------------------------

Dim bSTR923
bSTR923 = ""
Dim bSTR924
bSTR924 = ""
Dim boolean462
settingRepository1.GetAttrInfo "MOMENT_OVER_DISPLACEMENT_Nanometric", bSTR923, bSTR924, boolean462
'--------------------------------------------------
' Parameter 1 : (String) "MOMENT_OVER_DISPLACEMENT_Nanometric"
' Parameter 2 : (String) "Default value"
' Parameter 3 : (String) "Unlocked"
' Parameter 4 : (Boolean) False
'--------------------------------------------------

long463 = settingRepository1.GetAttr("MOMENT_OVER_ROTATION")
'--------------------------------------------------
' Parameter 1 : (String) "MOMENT_OVER_ROTATION"
' Returned value : (Variant) (Long) 1
'--------------------------------------------------

Dim bSTR925
bSTR925 = ""
Dim bSTR926
bSTR926 = ""
Dim boolean463
settingRepository1.GetAttrInfo "MOMENT_OVER_ROTATION", bSTR925, bSTR926, boolean463
'--------------------------------------------------
' Parameter 1 : (String) "MOMENT_OVER_ROTATION"
' Parameter 2 : (String) "Default value"
' Parameter 3 : (String) "Unlocked"
' Parameter 4 : (Boolean) False
'--------------------------------------------------

long464 = settingRepository1.GetAttr("MOMENT_OVER_ROTATION_Large")
'--------------------------------------------------
' Parameter 1 : (String) "MOMENT_OVER_ROTATION_Large"
' Returned value : (Variant) (Long) 1
'--------------------------------------------------

Dim bSTR927
bSTR927 = ""
Dim bSTR928
bSTR928 = ""
Dim boolean464
settingRepository1.GetAttrInfo "MOMENT_OVER_ROTATION_Large", bSTR927, bSTR928, boolean464
'--------------------------------------------------
' Parameter 1 : (String) "MOMENT_OVER_ROTATION_Large"
' Parameter 2 : (String) "Default value"
' Parameter 3 : (String) "Unlocked"
' Parameter 4 : (Boolean) False
'--------------------------------------------------

long465 = settingRepository1.GetAttr("MOMENT_OVER_ROTATION_ExtraLarge")
'--------------------------------------------------
' Parameter 1 : (String) "MOMENT_OVER_ROTATION_ExtraLarge"
' Returned value : (Variant) (Long) 1
'--------------------------------------------------

Dim bSTR929
bSTR929 = ""
Dim bSTR930
bSTR930 = ""
Dim boolean465
settingRepository1.GetAttrInfo "MOMENT_OVER_ROTATION_ExtraLarge", bSTR929, bSTR930, boolean465
'--------------------------------------------------
' Parameter 1 : (String) "MOMENT_OVER_ROTATION_ExtraLarge"
' Parameter 2 : (String) "Default value"
' Parameter 3 : (String) "Unlocked"
' Parameter 4 : (Boolean) False
'--------------------------------------------------

long466 = settingRepository1.GetAttr("MOMENT_OVER_ROTATION_Small")
'--------------------------------------------------
' Parameter 1 : (String) "MOMENT_OVER_ROTATION_Small"
' Returned value : (Variant) (Long) 1
'--------------------------------------------------

Dim bSTR931
bSTR931 = ""
Dim bSTR932
bSTR932 = ""
Dim boolean466
settingRepository1.GetAttrInfo "MOMENT_OVER_ROTATION_Small", bSTR931, bSTR932, boolean466
'--------------------------------------------------
' Parameter 1 : (String) "MOMENT_OVER_ROTATION_Small"
' Parameter 2 : (String) "Default value"
' Parameter 3 : (String) "Unlocked"
' Parameter 4 : (Boolean) False
'--------------------------------------------------

long467 = settingRepository1.GetAttr("MOMENT_OVER_ROTATION_ExtraSmall")
'--------------------------------------------------
' Parameter 1 : (String) "MOMENT_OVER_ROTATION_ExtraSmall"
' Returned value : (Variant) (Long) 1
'--------------------------------------------------

Dim bSTR933
bSTR933 = ""
Dim bSTR934
bSTR934 = ""
Dim boolean467
settingRepository1.GetAttrInfo "MOMENT_OVER_ROTATION_ExtraSmall", bSTR933, bSTR934, boolean467
'--------------------------------------------------
' Parameter 1 : (String) "MOMENT_OVER_ROTATION_ExtraSmall"
' Parameter 2 : (String) "Default value"
' Parameter 3 : (String) "Unlocked"
' Parameter 4 : (Boolean) False
'--------------------------------------------------

long468 = settingRepository1.GetAttr("MOMENT_OVER_ROTATION_Nanometric")
'--------------------------------------------------
' Parameter 1 : (String) "MOMENT_OVER_ROTATION_Nanometric"
' Returned value : (Variant) (Long) 1
'--------------------------------------------------

Dim bSTR935
bSTR935 = ""
Dim bSTR936
bSTR936 = ""
Dim boolean468
settingRepository1.GetAttrInfo "MOMENT_OVER_ROTATION_Nanometric", bSTR935, bSTR936, boolean468
'--------------------------------------------------
' Parameter 1 : (String) "MOMENT_OVER_ROTATION_Nanometric"
' Parameter 2 : (String) "Default value"
' Parameter 3 : (String) "Unlocked"
' Parameter 4 : (Boolean) False
'--------------------------------------------------

long469 = settingRepository1.GetAttr("PRESSURE_OVER_DISPLACEMENT")
'--------------------------------------------------
' Parameter 1 : (String) "PRESSURE_OVER_DISPLACEMENT"
' Returned value : (Variant) (Long) 1
'--------------------------------------------------

Dim bSTR937
bSTR937 = ""
Dim bSTR938
bSTR938 = ""
Dim boolean469
settingRepository1.GetAttrInfo "PRESSURE_OVER_DISPLACEMENT", bSTR937, bSTR938, boolean469
'--------------------------------------------------
' Parameter 1 : (String) "PRESSURE_OVER_DISPLACEMENT"
' Parameter 2 : (String) "Default value"
' Parameter 3 : (String) "Unlocked"
' Parameter 4 : (Boolean) False
'--------------------------------------------------

long470 = settingRepository1.GetAttr("PRESSURE_OVER_DISPLACEMENT_Large")
'--------------------------------------------------
' Parameter 1 : (String) "PRESSURE_OVER_DISPLACEMENT_Large"
' Returned value : (Variant) (Long) 1
'--------------------------------------------------

Dim bSTR939
bSTR939 = ""
Dim bSTR940
bSTR940 = ""
Dim boolean470
settingRepository1.GetAttrInfo "PRESSURE_OVER_DISPLACEMENT_Large", bSTR939, bSTR940, boolean470
'--------------------------------------------------
' Parameter 1 : (String) "PRESSURE_OVER_DISPLACEMENT_Large"
' Parameter 2 : (String) "Default value"
' Parameter 3 : (String) "Unlocked"
' Parameter 4 : (Boolean) False
'--------------------------------------------------

long471 = settingRepository1.GetAttr("PRESSURE_OVER_DISPLACEMENT_ExtraLarge")
'--------------------------------------------------
' Parameter 1 : (String) "PRESSURE_OVER_DISPLACEMENT_ExtraLarge"
' Returned value : (Variant) (Long) 1
'--------------------------------------------------

Dim bSTR941
bSTR941 = ""
Dim bSTR942
bSTR942 = ""
Dim boolean471
settingRepository1.GetAttrInfo "PRESSURE_OVER_DISPLACEMENT_ExtraLarge", bSTR941, bSTR942, boolean471
'--------------------------------------------------
' Parameter 1 : (String) "PRESSURE_OVER_DISPLACEMENT_ExtraLarge"
' Parameter 2 : (String) "Default value"
' Parameter 3 : (String) "Unlocked"
' Parameter 4 : (Boolean) False
'--------------------------------------------------

long472 = settingRepository1.GetAttr("PRESSURE_OVER_DISPLACEMENT_Small")
'--------------------------------------------------
' Parameter 1 : (String) "PRESSURE_OVER_DISPLACEMENT_Small"
' Returned value : (Variant) (Long) 1
'--------------------------------------------------

Dim bSTR943
bSTR943 = ""
Dim bSTR944
bSTR944 = ""
Dim boolean472
settingRepository1.GetAttrInfo "PRESSURE_OVER_DISPLACEMENT_Small", bSTR943, bSTR944, boolean472
'--------------------------------------------------
' Parameter 1 : (String) "PRESSURE_OVER_DISPLACEMENT_Small"
' Parameter 2 : (String) "Default value"
' Parameter 3 : (String) "Unlocked"
' Parameter 4 : (Boolean) False
'--------------------------------------------------

long473 = settingRepository1.GetAttr("PRESSURE_OVER_DISPLACEMENT_ExtraSmall")
'--------------------------------------------------
' Parameter 1 : (String) "PRESSURE_OVER_DISPLACEMENT_ExtraSmall"
' Returned value : (Variant) (Long) 1
'--------------------------------------------------

Dim bSTR945
bSTR945 = ""
Dim bSTR946
bSTR946 = ""
Dim boolean473
settingRepository1.GetAttrInfo "PRESSURE_OVER_DISPLACEMENT_ExtraSmall", bSTR945, bSTR946, boolean473
'--------------------------------------------------
' Parameter 1 : (String) "PRESSURE_OVER_DISPLACEMENT_ExtraSmall"
' Parameter 2 : (String) "Default value"
' Parameter 3 : (String) "Unlocked"
' Parameter 4 : (Boolean) False
'--------------------------------------------------

long474 = settingRepository1.GetAttr("PRESSURE_OVER_DISPLACEMENT_Nanometric")
'--------------------------------------------------
' Parameter 1 : (String) "PRESSURE_OVER_DISPLACEMENT_Nanometric"
' Returned value : (Variant) (Long) 1
'--------------------------------------------------

Dim bSTR947
bSTR947 = ""
Dim bSTR948
bSTR948 = ""
Dim boolean474
settingRepository1.GetAttrInfo "PRESSURE_OVER_DISPLACEMENT_Nanometric", bSTR947, bSTR948, boolean474
'--------------------------------------------------
' Parameter 1 : (String) "PRESSURE_OVER_DISPLACEMENT_Nanometric"
' Parameter 2 : (String) "Default value"
' Parameter 3 : (String) "Unlocked"
' Parameter 4 : (Boolean) False
'--------------------------------------------------

long475 = settingRepository1.GetAttr("PRESSURE_OVER_ROTATION")
'--------------------------------------------------
' Parameter 1 : (String) "PRESSURE_OVER_ROTATION"
' Returned value : (Variant) (Long) 1
'--------------------------------------------------

Dim bSTR949
bSTR949 = ""
Dim bSTR950
bSTR950 = ""
Dim boolean475
settingRepository1.GetAttrInfo "PRESSURE_OVER_ROTATION", bSTR949, bSTR950, boolean475
'--------------------------------------------------
' Parameter 1 : (String) "PRESSURE_OVER_ROTATION"
' Parameter 2 : (String) "Default value"
' Parameter 3 : (String) "Unlocked"
' Parameter 4 : (Boolean) False
'--------------------------------------------------

long476 = settingRepository1.GetAttr("PRESSURE_OVER_ROTATION_Large")
'--------------------------------------------------
' Parameter 1 : (String) "PRESSURE_OVER_ROTATION_Large"
' Returned value : (Variant) (Long) 1
'--------------------------------------------------

Dim bSTR951
bSTR951 = ""
Dim bSTR952
bSTR952 = ""
Dim boolean476
settingRepository1.GetAttrInfo "PRESSURE_OVER_ROTATION_Large", bSTR951, bSTR952, boolean476
'--------------------------------------------------
' Parameter 1 : (String) "PRESSURE_OVER_ROTATION_Large"
' Parameter 2 : (String) "Default value"
' Parameter 3 : (String) "Unlocked"
' Parameter 4 : (Boolean) False
'--------------------------------------------------

long477 = settingRepository1.GetAttr("PRESSURE_OVER_ROTATION_ExtraLarge")
'--------------------------------------------------
' Parameter 1 : (String) "PRESSURE_OVER_ROTATION_ExtraLarge"
' Returned value : (Variant) (Long) 1
'--------------------------------------------------

Dim bSTR953
bSTR953 = ""
Dim bSTR954
bSTR954 = ""
Dim boolean477
settingRepository1.GetAttrInfo "PRESSURE_OVER_ROTATION_ExtraLarge", bSTR953, bSTR954, boolean477
'--------------------------------------------------
' Parameter 1 : (String) "PRESSURE_OVER_ROTATION_ExtraLarge"
' Parameter 2 : (String) "Default value"
' Parameter 3 : (String) "Unlocked"
' Parameter 4 : (Boolean) False
'--------------------------------------------------

long478 = settingRepository1.GetAttr("PRESSURE_OVER_ROTATION_Small")
'--------------------------------------------------
' Parameter 1 : (String) "PRESSURE_OVER_ROTATION_Small"
' Returned value : (Variant) (Long) 1
'--------------------------------------------------

Dim bSTR955
bSTR955 = ""
Dim bSTR956
bSTR956 = ""
Dim boolean478
settingRepository1.GetAttrInfo "PRESSURE_OVER_ROTATION_Small", bSTR955, bSTR956, boolean478
'--------------------------------------------------
' Parameter 1 : (String) "PRESSURE_OVER_ROTATION_Small"
' Parameter 2 : (String) "Default value"
' Parameter 3 : (String) "Unlocked"
' Parameter 4 : (Boolean) False
'--------------------------------------------------

long479 = settingRepository1.GetAttr("PRESSURE_OVER_ROTATION_ExtraSmall")
'--------------------------------------------------
' Parameter 1 : (String) "PRESSURE_OVER_ROTATION_ExtraSmall"
' Returned value : (Variant) (Long) 1
'--------------------------------------------------

Dim bSTR957
bSTR957 = ""
Dim bSTR958
bSTR958 = ""
Dim boolean479
settingRepository1.GetAttrInfo "PRESSURE_OVER_ROTATION_ExtraSmall", bSTR957, bSTR958, boolean479
'--------------------------------------------------
' Parameter 1 : (String) "PRESSURE_OVER_ROTATION_ExtraSmall"
' Parameter 2 : (String) "Default value"
' Parameter 3 : (String) "Unlocked"
' Parameter 4 : (Boolean) False
'--------------------------------------------------

long480 = settingRepository1.GetAttr("PRESSURE_OVER_ROTATION_Nanometric")
'--------------------------------------------------
' Parameter 1 : (String) "PRESSURE_OVER_ROTATION_Nanometric"
' Returned value : (Variant) (Long) 1
'--------------------------------------------------

Dim bSTR959
bSTR959 = ""
Dim bSTR960
bSTR960 = ""
Dim boolean480
settingRepository1.GetAttrInfo "PRESSURE_OVER_ROTATION_Nanometric", bSTR959, bSTR960, boolean480
'--------------------------------------------------
' Parameter 1 : (String) "PRESSURE_OVER_ROTATION_Nanometric"
' Parameter 2 : (String) "Default value"
' Parameter 3 : (String) "Unlocked"
' Parameter 4 : (Boolean) False
'--------------------------------------------------

long481 = settingRepository1.GetAttr("FORCE_OVER_VELOCITY")
'--------------------------------------------------
' Parameter 1 : (String) "FORCE_OVER_VELOCITY"
' Returned value : (Variant) (Long) 1
'--------------------------------------------------

Dim bSTR961
bSTR961 = ""
Dim bSTR962
bSTR962 = ""
Dim boolean481
settingRepository1.GetAttrInfo "FORCE_OVER_VELOCITY", bSTR961, bSTR962, boolean481
'--------------------------------------------------
' Parameter 1 : (String) "FORCE_OVER_VELOCITY"
' Parameter 2 : (String) "Default value"
' Parameter 3 : (String) "Unlocked"
' Parameter 4 : (Boolean) False
'--------------------------------------------------

long482 = settingRepository1.GetAttr("FORCE_OVER_VELOCITY_Large")
'--------------------------------------------------
' Parameter 1 : (String) "FORCE_OVER_VELOCITY_Large"
' Returned value : (Variant) (Long) 1
'--------------------------------------------------

Dim bSTR963
bSTR963 = ""
Dim bSTR964
bSTR964 = ""
Dim boolean482
settingRepository1.GetAttrInfo "FORCE_OVER_VELOCITY_Large", bSTR963, bSTR964, boolean482
'--------------------------------------------------
' Parameter 1 : (String) "FORCE_OVER_VELOCITY_Large"
' Parameter 2 : (String) "Default value"
' Parameter 3 : (String) "Unlocked"
' Parameter 4 : (Boolean) False
'--------------------------------------------------

long483 = settingRepository1.GetAttr("FORCE_OVER_VELOCITY_ExtraLarge")
'--------------------------------------------------
' Parameter 1 : (String) "FORCE_OVER_VELOCITY_ExtraLarge"
' Returned value : (Variant) (Long) 1
'--------------------------------------------------

Dim bSTR965
bSTR965 = ""
Dim bSTR966
bSTR966 = ""
Dim boolean483
settingRepository1.GetAttrInfo "FORCE_OVER_VELOCITY_ExtraLarge", bSTR965, bSTR966, boolean483
'--------------------------------------------------
' Parameter 1 : (String) "FORCE_OVER_VELOCITY_ExtraLarge"
' Parameter 2 : (String) "Default value"
' Parameter 3 : (String) "Unlocked"
' Parameter 4 : (Boolean) False
'--------------------------------------------------

long484 = settingRepository1.GetAttr("FORCE_OVER_VELOCITY_Small")
'--------------------------------------------------
' Parameter 1 : (String) "FORCE_OVER_VELOCITY_Small"
' Returned value : (Variant) (Long) 1
'--------------------------------------------------

Dim bSTR967
bSTR967 = ""
Dim bSTR968
bSTR968 = ""
Dim boolean484
settingRepository1.GetAttrInfo "FORCE_OVER_VELOCITY_Small", bSTR967, bSTR968, boolean484
'--------------------------------------------------
' Parameter 1 : (String) "FORCE_OVER_VELOCITY_Small"
' Parameter 2 : (String) "Default value"
' Parameter 3 : (String) "Unlocked"
' Parameter 4 : (Boolean) False
'--------------------------------------------------

long485 = settingRepository1.GetAttr("FORCE_OVER_VELOCITY_ExtraSmall")
'--------------------------------------------------
' Parameter 1 : (String) "FORCE_OVER_VELOCITY_ExtraSmall"
' Returned value : (Variant) (Long) 1
'--------------------------------------------------

Dim bSTR969
bSTR969 = ""
Dim bSTR970
bSTR970 = ""
Dim boolean485
settingRepository1.GetAttrInfo "FORCE_OVER_VELOCITY_ExtraSmall", bSTR969, bSTR970, boolean485
'--------------------------------------------------
' Parameter 1 : (String) "FORCE_OVER_VELOCITY_ExtraSmall"
' Parameter 2 : (String) "Default value"
' Parameter 3 : (String) "Unlocked"
' Parameter 4 : (Boolean) False
'--------------------------------------------------

long486 = settingRepository1.GetAttr("FORCE_OVER_VELOCITY_Nanometric")
'--------------------------------------------------
' Parameter 1 : (String) "FORCE_OVER_VELOCITY_Nanometric"
' Returned value : (Variant) (Long) 1
'--------------------------------------------------

Dim bSTR971
bSTR971 = ""
Dim bSTR972
bSTR972 = ""
Dim boolean486
settingRepository1.GetAttrInfo "FORCE_OVER_VELOCITY_Nanometric", bSTR971, bSTR972, boolean486
'--------------------------------------------------
' Parameter 1 : (String) "FORCE_OVER_VELOCITY_Nanometric"
' Parameter 2 : (String) "Default value"
' Parameter 3 : (String) "Unlocked"
' Parameter 4 : (Boolean) False
'--------------------------------------------------

long487 = settingRepository1.GetAttr("FORCE_OVER_PULSATION")
'--------------------------------------------------
' Parameter 1 : (String) "FORCE_OVER_PULSATION"
' Returned value : (Variant) (Long) 1
'--------------------------------------------------

Dim bSTR973
bSTR973 = ""
Dim bSTR974
bSTR974 = ""
Dim boolean487
settingRepository1.GetAttrInfo "FORCE_OVER_PULSATION", bSTR973, bSTR974, boolean487
'--------------------------------------------------
' Parameter 1 : (String) "FORCE_OVER_PULSATION"
' Parameter 2 : (String) "Default value"
' Parameter 3 : (String) "Unlocked"
' Parameter 4 : (Boolean) False
'--------------------------------------------------

long488 = settingRepository1.GetAttr("FORCE_OVER_PULSATION_Large")
'--------------------------------------------------
' Parameter 1 : (String) "FORCE_OVER_PULSATION_Large"
' Returned value : (Variant) (Long) 1
'--------------------------------------------------

Dim bSTR975
bSTR975 = ""
Dim bSTR976
bSTR976 = ""
Dim boolean488
settingRepository1.GetAttrInfo "FORCE_OVER_PULSATION_Large", bSTR975, bSTR976, boolean488
'--------------------------------------------------
' Parameter 1 : (String) "FORCE_OVER_PULSATION_Large"
' Parameter 2 : (String) "Default value"
' Parameter 3 : (String) "Unlocked"
' Parameter 4 : (Boolean) False
'--------------------------------------------------

long489 = settingRepository1.GetAttr("FORCE_OVER_PULSATION_ExtraLarge")
'--------------------------------------------------
' Parameter 1 : (String) "FORCE_OVER_PULSATION_ExtraLarge"
' Returned value : (Variant) (Long) 1
'--------------------------------------------------

Dim bSTR977
bSTR977 = ""
Dim bSTR978
bSTR978 = ""
Dim boolean489
settingRepository1.GetAttrInfo "FORCE_OVER_PULSATION_ExtraLarge", bSTR977, bSTR978, boolean489
'--------------------------------------------------
' Parameter 1 : (String) "FORCE_OVER_PULSATION_ExtraLarge"
' Parameter 2 : (String) "Default value"
' Parameter 3 : (String) "Unlocked"
' Parameter 4 : (Boolean) False
'--------------------------------------------------

long490 = settingRepository1.GetAttr("FORCE_OVER_PULSATION_Small")
'--------------------------------------------------
' Parameter 1 : (String) "FORCE_OVER_PULSATION_Small"
' Returned value : (Variant) (Long) 1
'--------------------------------------------------

Dim bSTR979
bSTR979 = ""
Dim bSTR980
bSTR980 = ""
Dim boolean490
settingRepository1.GetAttrInfo "FORCE_OVER_PULSATION_Small", bSTR979, bSTR980, boolean490
'--------------------------------------------------
' Parameter 1 : (String) "FORCE_OVER_PULSATION_Small"
' Parameter 2 : (String) "Default value"
' Parameter 3 : (String) "Unlocked"
' Parameter 4 : (Boolean) False
'--------------------------------------------------

long491 = settingRepository1.GetAttr("FORCE_OVER_PULSATION_ExtraSmall")
'--------------------------------------------------
' Parameter 1 : (String) "FORCE_OVER_PULSATION_ExtraSmall"
' Returned value : (Variant) (Long) 1
'--------------------------------------------------

Dim bSTR981
bSTR981 = ""
Dim bSTR982
bSTR982 = ""
Dim boolean491
settingRepository1.GetAttrInfo "FORCE_OVER_PULSATION_ExtraSmall", bSTR981, bSTR982, boolean491
'--------------------------------------------------
' Parameter 1 : (String) "FORCE_OVER_PULSATION_ExtraSmall"
' Parameter 2 : (String) "Default value"
' Parameter 3 : (String) "Unlocked"
' Parameter 4 : (Boolean) False
'--------------------------------------------------

long492 = settingRepository1.GetAttr("FORCE_OVER_PULSATION_Nanometric")
'--------------------------------------------------
' Parameter 1 : (String) "FORCE_OVER_PULSATION_Nanometric"
' Returned value : (Variant) (Long) 1
'--------------------------------------------------

Dim bSTR983
bSTR983 = ""
Dim bSTR984
bSTR984 = ""
Dim boolean492
settingRepository1.GetAttrInfo "FORCE_OVER_PULSATION_Nanometric", bSTR983, bSTR984, boolean492
'--------------------------------------------------
' Parameter 1 : (String) "FORCE_OVER_PULSATION_Nanometric"
' Parameter 2 : (String) "Default value"
' Parameter 3 : (String) "Unlocked"
' Parameter 4 : (Boolean) False
'--------------------------------------------------

long493 = settingRepository1.GetAttr("MOMENT_OVER_VELOCITY")
'--------------------------------------------------
' Parameter 1 : (String) "MOMENT_OVER_VELOCITY"
' Returned value : (Variant) (Long) 1
'--------------------------------------------------

Dim bSTR985
bSTR985 = ""
Dim bSTR986
bSTR986 = ""
Dim boolean493
settingRepository1.GetAttrInfo "MOMENT_OVER_VELOCITY", bSTR985, bSTR986, boolean493
'--------------------------------------------------
' Parameter 1 : (String) "MOMENT_OVER_VELOCITY"
' Parameter 2 : (String) "Default value"
' Parameter 3 : (String) "Unlocked"
' Parameter 4 : (Boolean) False
'--------------------------------------------------

long494 = settingRepository1.GetAttr("MOMENT_OVER_VELOCITY_Large")
'--------------------------------------------------
' Parameter 1 : (String) "MOMENT_OVER_VELOCITY_Large"
' Returned value : (Variant) (Long) 1
'--------------------------------------------------

Dim bSTR987
bSTR987 = ""
Dim bSTR988
bSTR988 = ""
Dim boolean494
settingRepository1.GetAttrInfo "MOMENT_OVER_VELOCITY_Large", bSTR987, bSTR988, boolean494
'--------------------------------------------------
' Parameter 1 : (String) "MOMENT_OVER_VELOCITY_Large"
' Parameter 2 : (String) "Default value"
' Parameter 3 : (String) "Unlocked"
' Parameter 4 : (Boolean) False
'--------------------------------------------------

long495 = settingRepository1.GetAttr("MOMENT_OVER_VELOCITY_ExtraLarge")
'--------------------------------------------------
' Parameter 1 : (String) "MOMENT_OVER_VELOCITY_ExtraLarge"
' Returned value : (Variant) (Long) 1
'--------------------------------------------------

Dim bSTR989
bSTR989 = ""
Dim bSTR990
bSTR990 = ""
Dim boolean495
settingRepository1.GetAttrInfo "MOMENT_OVER_VELOCITY_ExtraLarge", bSTR989, bSTR990, boolean495
'--------------------------------------------------
' Parameter 1 : (String) "MOMENT_OVER_VELOCITY_ExtraLarge"
' Parameter 2 : (String) "Default value"
' Parameter 3 : (String) "Unlocked"
' Parameter 4 : (Boolean) False
'--------------------------------------------------

long496 = settingRepository1.GetAttr("MOMENT_OVER_VELOCITY_Small")
'--------------------------------------------------
' Parameter 1 : (String) "MOMENT_OVER_VELOCITY_Small"
' Returned value : (Variant) (Long) 1
'--------------------------------------------------

Dim bSTR991
bSTR991 = ""
Dim bSTR992
bSTR992 = ""
Dim boolean496
settingRepository1.GetAttrInfo "MOMENT_OVER_VELOCITY_Small", bSTR991, bSTR992, boolean496
'--------------------------------------------------
' Parameter 1 : (String) "MOMENT_OVER_VELOCITY_Small"
' Parameter 2 : (String) "Default value"
' Parameter 3 : (String) "Unlocked"
' Parameter 4 : (Boolean) False
'--------------------------------------------------

long497 = settingRepository1.GetAttr("MOMENT_OVER_VELOCITY_ExtraSmall")
'--------------------------------------------------
' Parameter 1 : (String) "MOMENT_OVER_VELOCITY_ExtraSmall"
' Returned value : (Variant) (Long) 1
'--------------------------------------------------

Dim bSTR993
bSTR993 = ""
Dim bSTR994
bSTR994 = ""
Dim boolean497
settingRepository1.GetAttrInfo "MOMENT_OVER_VELOCITY_ExtraSmall", bSTR993, bSTR994, boolean497
'--------------------------------------------------
' Parameter 1 : (String) "MOMENT_OVER_VELOCITY_ExtraSmall"
' Parameter 2 : (String) "Default value"
' Parameter 3 : (String) "Unlocked"
' Parameter 4 : (Boolean) False
'--------------------------------------------------

long498 = settingRepository1.GetAttr("MOMENT_OVER_VELOCITY_Nanometric")
'--------------------------------------------------
' Parameter 1 : (String) "MOMENT_OVER_VELOCITY_Nanometric"
' Returned value : (Variant) (Long) 1
'--------------------------------------------------

Dim bSTR995
bSTR995 = ""
Dim bSTR996
bSTR996 = ""
Dim boolean498
settingRepository1.GetAttrInfo "MOMENT_OVER_VELOCITY_Nanometric", bSTR995, bSTR996, boolean498
'--------------------------------------------------
' Parameter 1 : (String) "MOMENT_OVER_VELOCITY_Nanometric"
' Parameter 2 : (String) "Default value"
' Parameter 3 : (String) "Unlocked"
' Parameter 4 : (Boolean) False
'--------------------------------------------------

long499 = settingRepository1.GetAttr("MOMENT_OVER_PULSATION")
'--------------------------------------------------
' Parameter 1 : (String) "MOMENT_OVER_PULSATION"
' Returned value : (Variant) (Long) 1
'--------------------------------------------------

Dim bSTR997
bSTR997 = ""
Dim bSTR998
bSTR998 = ""
Dim boolean499
settingRepository1.GetAttrInfo "MOMENT_OVER_PULSATION", bSTR997, bSTR998, boolean499
'--------------------------------------------------
' Parameter 1 : (String) "MOMENT_OVER_PULSATION"
' Parameter 2 : (String) "Default value"
' Parameter 3 : (String) "Unlocked"
' Parameter 4 : (Boolean) False
'--------------------------------------------------

long500 = settingRepository1.GetAttr("MOMENT_OVER_PULSATION_Large")
'--------------------------------------------------
' Parameter 1 : (String) "MOMENT_OVER_PULSATION_Large"
' Returned value : (Variant) (Long) 1
'--------------------------------------------------

Dim bSTR999
bSTR999 = ""
Dim bSTR1000
bSTR1000 = ""
Dim boolean500
settingRepository1.GetAttrInfo "MOMENT_OVER_PULSATION_Large", bSTR999, bSTR1000, boolean500
'--------------------------------------------------
' Parameter 1 : (String) "MOMENT_OVER_PULSATION_Large"
' Parameter 2 : (String) "Default value"
' Parameter 3 : (String) "Unlocked"
' Parameter 4 : (Boolean) False
'--------------------------------------------------

long501 = settingRepository1.GetAttr("MOMENT_OVER_PULSATION_ExtraLarge")
'--------------------------------------------------
' Parameter 1 : (String) "MOMENT_OVER_PULSATION_ExtraLarge"
' Returned value : (Variant) (Long) 1
'--------------------------------------------------

Dim bSTR1001
bSTR1001 = ""
Dim bSTR1002
bSTR1002 = ""
Dim boolean501
settingRepository1.GetAttrInfo "MOMENT_OVER_PULSATION_ExtraLarge", bSTR1001, bSTR1002, boolean501
'--------------------------------------------------
' Parameter 1 : (String) "MOMENT_OVER_PULSATION_ExtraLarge"
' Parameter 2 : (String) "Default value"
' Parameter 3 : (String) "Unlocked"
' Parameter 4 : (Boolean) False
'--------------------------------------------------

long502 = settingRepository1.GetAttr("MOMENT_OVER_PULSATION_Small")
'--------------------------------------------------
' Parameter 1 : (String) "MOMENT_OVER_PULSATION_Small"
' Returned value : (Variant) (Long) 1
'--------------------------------------------------

Dim bSTR1003
bSTR1003 = ""
Dim bSTR1004
bSTR1004 = ""
Dim boolean502
settingRepository1.GetAttrInfo "MOMENT_OVER_PULSATION_Small", bSTR1003, bSTR1004, boolean502
'--------------------------------------------------
' Parameter 1 : (String) "MOMENT_OVER_PULSATION_Small"
' Parameter 2 : (String) "Default value"
' Parameter 3 : (String) "Unlocked"
' Parameter 4 : (Boolean) False
'--------------------------------------------------

long503 = settingRepository1.GetAttr("MOMENT_OVER_PULSATION_ExtraSmall")
'--------------------------------------------------
' Parameter 1 : (String) "MOMENT_OVER_PULSATION_ExtraSmall"
' Returned value : (Variant) (Long) 1
'--------------------------------------------------

Dim bSTR1005
bSTR1005 = ""
Dim bSTR1006
bSTR1006 = ""
Dim boolean503
settingRepository1.GetAttrInfo "MOMENT_OVER_PULSATION_ExtraSmall", bSTR1005, bSTR1006, boolean503
'--------------------------------------------------
' Parameter 1 : (String) "MOMENT_OVER_PULSATION_ExtraSmall"
' Parameter 2 : (String) "Default value"
' Parameter 3 : (String) "Unlocked"
' Parameter 4 : (Boolean) False
'--------------------------------------------------

long504 = settingRepository1.GetAttr("MOMENT_OVER_PULSATION_Nanometric")
'--------------------------------------------------
' Parameter 1 : (String) "MOMENT_OVER_PULSATION_Nanometric"
' Returned value : (Variant) (Long) 1
'--------------------------------------------------

Dim bSTR1007
bSTR1007 = ""
Dim bSTR1008
bSTR1008 = ""
Dim boolean504
settingRepository1.GetAttrInfo "MOMENT_OVER_PULSATION_Nanometric", bSTR1007, bSTR1008, boolean504
'--------------------------------------------------
' Parameter 1 : (String) "MOMENT_OVER_PULSATION_Nanometric"
' Parameter 2 : (String) "Default value"
' Parameter 3 : (String) "Unlocked"
' Parameter 4 : (Boolean) False
'--------------------------------------------------

long505 = settingRepository1.GetAttr("PRESSURE_OVER_PULSATION")
'--------------------------------------------------
' Parameter 1 : (String) "PRESSURE_OVER_PULSATION"
' Returned value : (Variant) (Long) 1
'--------------------------------------------------

Dim bSTR1009
bSTR1009 = ""
Dim bSTR1010
bSTR1010 = ""
Dim boolean505
settingRepository1.GetAttrInfo "PRESSURE_OVER_PULSATION", bSTR1009, bSTR1010, boolean505
'--------------------------------------------------
' Parameter 1 : (String) "PRESSURE_OVER_PULSATION"
' Parameter 2 : (String) "Default value"
' Parameter 3 : (String) "Unlocked"
' Parameter 4 : (Boolean) False
'--------------------------------------------------

long506 = settingRepository1.GetAttr("PRESSURE_OVER_PULSATION_Large")
'--------------------------------------------------
' Parameter 1 : (String) "PRESSURE_OVER_PULSATION_Large"
' Returned value : (Variant) (Long) 1
'--------------------------------------------------

Dim bSTR1011
bSTR1011 = ""
Dim bSTR1012
bSTR1012 = ""
Dim boolean506
settingRepository1.GetAttrInfo "PRESSURE_OVER_PULSATION_Large", bSTR1011, bSTR1012, boolean506
'--------------------------------------------------
' Parameter 1 : (String) "PRESSURE_OVER_PULSATION_Large"
' Parameter 2 : (String) "Default value"
' Parameter 3 : (String) "Unlocked"
' Parameter 4 : (Boolean) False
'--------------------------------------------------

long507 = settingRepository1.GetAttr("PRESSURE_OVER_PULSATION_ExtraLarge")
'--------------------------------------------------
' Parameter 1 : (String) "PRESSURE_OVER_PULSATION_ExtraLarge"
' Returned value : (Variant) (Long) 1
'--------------------------------------------------

Dim bSTR1013
bSTR1013 = ""
Dim bSTR1014
bSTR1014 = ""
Dim boolean507
settingRepository1.GetAttrInfo "PRESSURE_OVER_PULSATION_ExtraLarge", bSTR1013, bSTR1014, boolean507
'--------------------------------------------------
' Parameter 1 : (String) "PRESSURE_OVER_PULSATION_ExtraLarge"
' Parameter 2 : (String) "Default value"
' Parameter 3 : (String) "Unlocked"
' Parameter 4 : (Boolean) False
'--------------------------------------------------

long508 = settingRepository1.GetAttr("PRESSURE_OVER_PULSATION_Small")
'--------------------------------------------------
' Parameter 1 : (String) "PRESSURE_OVER_PULSATION_Small"
' Returned value : (Variant) (Long) 1
'--------------------------------------------------

Dim bSTR1015
bSTR1015 = ""
Dim bSTR1016
bSTR1016 = ""
Dim boolean508
settingRepository1.GetAttrInfo "PRESSURE_OVER_PULSATION_Small", bSTR1015, bSTR1016, boolean508
'--------------------------------------------------
' Parameter 1 : (String) "PRESSURE_OVER_PULSATION_Small"
' Parameter 2 : (String) "Default value"
' Parameter 3 : (String) "Unlocked"
' Parameter 4 : (Boolean) False
'--------------------------------------------------

long509 = settingRepository1.GetAttr("PRESSURE_OVER_PULSATION_ExtraSmall")
'--------------------------------------------------
' Parameter 1 : (String) "PRESSURE_OVER_PULSATION_ExtraSmall"
' Returned value : (Variant) (Long) 1
'--------------------------------------------------

Dim bSTR1017
bSTR1017 = ""
Dim bSTR1018
bSTR1018 = ""
Dim boolean509
settingRepository1.GetAttrInfo "PRESSURE_OVER_PULSATION_ExtraSmall", bSTR1017, bSTR1018, boolean509
'--------------------------------------------------
' Parameter 1 : (String) "PRESSURE_OVER_PULSATION_ExtraSmall"
' Parameter 2 : (String) "Default value"
' Parameter 3 : (String) "Unlocked"
' Parameter 4 : (Boolean) False
'--------------------------------------------------

long510 = settingRepository1.GetAttr("PRESSURE_OVER_PULSATION_Nanometric")
'--------------------------------------------------
' Parameter 1 : (String) "PRESSURE_OVER_PULSATION_Nanometric"
' Returned value : (Variant) (Long) 1
'--------------------------------------------------

Dim bSTR1019
bSTR1019 = ""
Dim bSTR1020
bSTR1020 = ""
Dim boolean510
settingRepository1.GetAttrInfo "PRESSURE_OVER_PULSATION_Nanometric", bSTR1019, bSTR1020, boolean510
'--------------------------------------------------
' Parameter 1 : (String) "PRESSURE_OVER_PULSATION_Nanometric"
' Parameter 2 : (String) "Default value"
' Parameter 3 : (String) "Unlocked"
' Parameter 4 : (Boolean) False
'--------------------------------------------------

long511 = settingRepository1.GetAttr("FORCE_OVER_ACCELERATION")
'--------------------------------------------------
' Parameter 1 : (String) "FORCE_OVER_ACCELERATION"
' Returned value : (Variant) (Long) 1
'--------------------------------------------------

Dim bSTR1021
bSTR1021 = ""
Dim bSTR1022
bSTR1022 = ""
Dim boolean511
settingRepository1.GetAttrInfo "FORCE_OVER_ACCELERATION", bSTR1021, bSTR1022, boolean511
'--------------------------------------------------
' Parameter 1 : (String) "FORCE_OVER_ACCELERATION"
' Parameter 2 : (String) "Default value"
' Parameter 3 : (String) "Unlocked"
' Parameter 4 : (Boolean) False
'--------------------------------------------------

long512 = settingRepository1.GetAttr("FORCE_OVER_ACCELERATION_Large")
'--------------------------------------------------
' Parameter 1 : (String) "FORCE_OVER_ACCELERATION_Large"
' Returned value : (Variant) (Long) 1
'--------------------------------------------------

Dim bSTR1023
bSTR1023 = ""
Dim bSTR1024
bSTR1024 = ""
Dim boolean512
settingRepository1.GetAttrInfo "FORCE_OVER_ACCELERATION_Large", bSTR1023, bSTR1024, boolean512
'--------------------------------------------------
' Parameter 1 : (String) "FORCE_OVER_ACCELERATION_Large"
' Parameter 2 : (String) "Default value"
' Parameter 3 : (String) "Unlocked"
' Parameter 4 : (Boolean) False
'--------------------------------------------------

long513 = settingRepository1.GetAttr("FORCE_OVER_ACCELERATION_ExtraLarge")
'--------------------------------------------------
' Parameter 1 : (String) "FORCE_OVER_ACCELERATION_ExtraLarge"
' Returned value : (Variant) (Long) 1
'--------------------------------------------------

Dim bSTR1025
bSTR1025 = ""
Dim bSTR1026
bSTR1026 = ""
Dim boolean513
settingRepository1.GetAttrInfo "FORCE_OVER_ACCELERATION_ExtraLarge", bSTR1025, bSTR1026, boolean513
'--------------------------------------------------
' Parameter 1 : (String) "FORCE_OVER_ACCELERATION_ExtraLarge"
' Parameter 2 : (String) "Default value"
' Parameter 3 : (String) "Unlocked"
' Parameter 4 : (Boolean) False
'--------------------------------------------------

long514 = settingRepository1.GetAttr("FORCE_OVER_ACCELERATION_Small")
'--------------------------------------------------
' Parameter 1 : (String) "FORCE_OVER_ACCELERATION_Small"
' Returned value : (Variant) (Long) 1
'--------------------------------------------------

Dim bSTR1027
bSTR1027 = ""
Dim bSTR1028
bSTR1028 = ""
Dim boolean514
settingRepository1.GetAttrInfo "FORCE_OVER_ACCELERATION_Small", bSTR1027, bSTR1028, boolean514
'--------------------------------------------------
' Parameter 1 : (String) "FORCE_OVER_ACCELERATION_Small"
' Parameter 2 : (String) "Default value"
' Parameter 3 : (String) "Unlocked"
' Parameter 4 : (Boolean) False
'--------------------------------------------------

long515 = settingRepository1.GetAttr("FORCE_OVER_ACCELERATION_ExtraSmall")
'--------------------------------------------------
' Parameter 1 : (String) "FORCE_OVER_ACCELERATION_ExtraSmall"
' Returned value : (Variant) (Long) 1
'--------------------------------------------------

Dim bSTR1029
bSTR1029 = ""
Dim bSTR1030
bSTR1030 = ""
Dim boolean515
settingRepository1.GetAttrInfo "FORCE_OVER_ACCELERATION_ExtraSmall", bSTR1029, bSTR1030, boolean515
'--------------------------------------------------
' Parameter 1 : (String) "FORCE_OVER_ACCELERATION_ExtraSmall"
' Parameter 2 : (String) "Default value"
' Parameter 3 : (String) "Unlocked"
' Parameter 4 : (Boolean) False
'--------------------------------------------------

long516 = settingRepository1.GetAttr("FORCE_OVER_ACCELERATION_Nanometric")
'--------------------------------------------------
' Parameter 1 : (String) "FORCE_OVER_ACCELERATION_Nanometric"
' Returned value : (Variant) (Long) 1
'--------------------------------------------------

Dim bSTR1031
bSTR1031 = ""
Dim bSTR1032
bSTR1032 = ""
Dim boolean516
settingRepository1.GetAttrInfo "FORCE_OVER_ACCELERATION_Nanometric", bSTR1031, bSTR1032, boolean516
'--------------------------------------------------
' Parameter 1 : (String) "FORCE_OVER_ACCELERATION_Nanometric"
' Parameter 2 : (String) "Default value"
' Parameter 3 : (String) "Unlocked"
' Parameter 4 : (Boolean) False
'--------------------------------------------------

long517 = settingRepository1.GetAttr("FORCE_OVER_ROTATIONAL_ACCELERATION")
'--------------------------------------------------
' Parameter 1 : (String) "FORCE_OVER_ROTATIONAL_ACCELERATION"
' Returned value : (Variant) (Long) 1
'--------------------------------------------------

Dim bSTR1033
bSTR1033 = ""
Dim bSTR1034
bSTR1034 = ""
Dim boolean517
settingRepository1.GetAttrInfo "FORCE_OVER_ROTATIONAL_ACCELERATION", bSTR1033, bSTR1034, boolean517
'--------------------------------------------------
' Parameter 1 : (String) "FORCE_OVER_ROTATIONAL_ACCELERATION"
' Parameter 2 : (String) "Default value"
' Parameter 3 : (String) "Unlocked"
' Parameter 4 : (Boolean) False
'--------------------------------------------------

long518 = settingRepository1.GetAttr("FORCE_OVER_ROTATIONAL_ACCELERATION_Large")
'--------------------------------------------------
' Parameter 1 : (String) "FORCE_OVER_ROTATIONAL_ACCELERATION_Large"
' Returned value : (Variant) (Long) 1
'--------------------------------------------------

Dim bSTR1035
bSTR1035 = ""
Dim bSTR1036
bSTR1036 = ""
Dim boolean518
settingRepository1.GetAttrInfo "FORCE_OVER_ROTATIONAL_ACCELERATION_Large", bSTR1035, bSTR1036, boolean518
'--------------------------------------------------
' Parameter 1 : (String) "FORCE_OVER_ROTATIONAL_ACCELERATION_Large"
' Parameter 2 : (String) "Default value"
' Parameter 3 : (String) "Unlocked"
' Parameter 4 : (Boolean) False
'--------------------------------------------------

long519 = settingRepository1.GetAttr("FORCE_OVER_ROTATIONAL_ACCELERATION_ExtraLarge")
'--------------------------------------------------
' Parameter 1 : (String) "FORCE_OVER_ROTATIONAL_ACCELERATION_ExtraLarge"
' Returned value : (Variant) (Long) 1
'--------------------------------------------------

Dim bSTR1037
bSTR1037 = ""
Dim bSTR1038
bSTR1038 = ""
Dim boolean519
settingRepository1.GetAttrInfo "FORCE_OVER_ROTATIONAL_ACCELERATION_ExtraLarge", bSTR1037, bSTR1038, boolean519
'--------------------------------------------------
' Parameter 1 : (String) "FORCE_OVER_ROTATIONAL_ACCELERATION_ExtraLarge"
' Parameter 2 : (String) "Default value"
' Parameter 3 : (String) "Unlocked"
' Parameter 4 : (Boolean) False
'--------------------------------------------------

long520 = settingRepository1.GetAttr("FORCE_OVER_ROTATIONAL_ACCELERATION_Small")
'--------------------------------------------------
' Parameter 1 : (String) "FORCE_OVER_ROTATIONAL_ACCELERATION_Small"
' Returned value : (Variant) (Long) 1
'--------------------------------------------------

Dim bSTR1039
bSTR1039 = ""
Dim bSTR1040
bSTR1040 = ""
Dim boolean520
settingRepository1.GetAttrInfo "FORCE_OVER_ROTATIONAL_ACCELERATION_Small", bSTR1039, bSTR1040, boolean520
'--------------------------------------------------
' Parameter 1 : (String) "FORCE_OVER_ROTATIONAL_ACCELERATION_Small"
' Parameter 2 : (String) "Default value"
' Parameter 3 : (String) "Unlocked"
' Parameter 4 : (Boolean) False
'--------------------------------------------------

long521 = settingRepository1.GetAttr("FORCE_OVER_ROTATIONAL_ACCELERATION_ExtraSmall")
'--------------------------------------------------
' Parameter 1 : (String) "FORCE_OVER_ROTATIONAL_ACCELERATION_ExtraSmall"
' Returned value : (Variant) (Long) 1
'--------------------------------------------------

Dim bSTR1041
bSTR1041 = ""
Dim bSTR1042
bSTR1042 = ""
Dim boolean521
settingRepository1.GetAttrInfo "FORCE_OVER_ROTATIONAL_ACCELERATION_ExtraSmall", bSTR1041, bSTR1042, boolean521
'--------------------------------------------------
' Parameter 1 : (String) "FORCE_OVER_ROTATIONAL_ACCELERATION_ExtraSmall"
' Parameter 2 : (String) "Default value"
' Parameter 3 : (String) "Unlocked"
' Parameter 4 : (Boolean) False
'--------------------------------------------------

long522 = settingRepository1.GetAttr("FORCE_OVER_ROTATIONAL_ACCELERATION_Nanometric")
'--------------------------------------------------
' Parameter 1 : (String) "FORCE_OVER_ROTATIONAL_ACCELERATION_Nanometric"
' Returned value : (Variant) (Long) 1
'--------------------------------------------------

Dim bSTR1043
bSTR1043 = ""
Dim bSTR1044
bSTR1044 = ""
Dim boolean522
settingRepository1.GetAttrInfo "FORCE_OVER_ROTATIONAL_ACCELERATION_Nanometric", bSTR1043, bSTR1044, boolean522
'--------------------------------------------------
' Parameter 1 : (String) "FORCE_OVER_ROTATIONAL_ACCELERATION_Nanometric"
' Parameter 2 : (String) "Default value"
' Parameter 3 : (String) "Unlocked"
' Parameter 4 : (Boolean) False
'--------------------------------------------------

long523 = settingRepository1.GetAttr("MOMENT_OVER_ACCELERATION")
'--------------------------------------------------
' Parameter 1 : (String) "MOMENT_OVER_ACCELERATION"
' Returned value : (Variant) (Long) 1
'--------------------------------------------------

Dim bSTR1045
bSTR1045 = ""
Dim bSTR1046
bSTR1046 = ""
Dim boolean523
settingRepository1.GetAttrInfo "MOMENT_OVER_ACCELERATION", bSTR1045, bSTR1046, boolean523
'--------------------------------------------------
' Parameter 1 : (String) "MOMENT_OVER_ACCELERATION"
' Parameter 2 : (String) "Default value"
' Parameter 3 : (String) "Unlocked"
' Parameter 4 : (Boolean) False
'--------------------------------------------------

long524 = settingRepository1.GetAttr("MOMENT_OVER_ACCELERATION_Large")
'--------------------------------------------------
' Parameter 1 : (String) "MOMENT_OVER_ACCELERATION_Large"
' Returned value : (Variant) (Long) 1
'--------------------------------------------------

Dim bSTR1047
bSTR1047 = ""
Dim bSTR1048
bSTR1048 = ""
Dim boolean524
settingRepository1.GetAttrInfo "MOMENT_OVER_ACCELERATION_Large", bSTR1047, bSTR1048, boolean524
'--------------------------------------------------
' Parameter 1 : (String) "MOMENT_OVER_ACCELERATION_Large"
' Parameter 2 : (String) "Default value"
' Parameter 3 : (String) "Unlocked"
' Parameter 4 : (Boolean) False
'--------------------------------------------------

long525 = settingRepository1.GetAttr("MOMENT_OVER_ACCELERATION_ExtraLarge")
'--------------------------------------------------
' Parameter 1 : (String) "MOMENT_OVER_ACCELERATION_ExtraLarge"
' Returned value : (Variant) (Long) 1
'--------------------------------------------------

Dim bSTR1049
bSTR1049 = ""
Dim bSTR1050
bSTR1050 = ""
Dim boolean525
settingRepository1.GetAttrInfo "MOMENT_OVER_ACCELERATION_ExtraLarge", bSTR1049, bSTR1050, boolean525
'--------------------------------------------------
' Parameter 1 : (String) "MOMENT_OVER_ACCELERATION_ExtraLarge"
' Parameter 2 : (String) "Default value"
' Parameter 3 : (String) "Unlocked"
' Parameter 4 : (Boolean) False
'--------------------------------------------------

long526 = settingRepository1.GetAttr("MOMENT_OVER_ACCELERATION_Small")
'--------------------------------------------------
' Parameter 1 : (String) "MOMENT_OVER_ACCELERATION_Small"
' Returned value : (Variant) (Long) 1
'--------------------------------------------------

Dim bSTR1051
bSTR1051 = ""
Dim bSTR1052
bSTR1052 = ""
Dim boolean526
settingRepository1.GetAttrInfo "MOMENT_OVER_ACCELERATION_Small", bSTR1051, bSTR1052, boolean526
'--------------------------------------------------
' Parameter 1 : (String) "MOMENT_OVER_ACCELERATION_Small"
' Parameter 2 : (String) "Default value"
' Parameter 3 : (String) "Unlocked"
' Parameter 4 : (Boolean) False
'--------------------------------------------------

long527 = settingRepository1.GetAttr("MOMENT_OVER_ACCELERATION_ExtraSmall")
'--------------------------------------------------
' Parameter 1 : (String) "MOMENT_OVER_ACCELERATION_ExtraSmall"
' Returned value : (Variant) (Long) 1
'--------------------------------------------------

Dim bSTR1053
bSTR1053 = ""
Dim bSTR1054
bSTR1054 = ""
Dim boolean527
settingRepository1.GetAttrInfo "MOMENT_OVER_ACCELERATION_ExtraSmall", bSTR1053, bSTR1054, boolean527
'--------------------------------------------------
' Parameter 1 : (String) "MOMENT_OVER_ACCELERATION_ExtraSmall"
' Parameter 2 : (String) "Default value"
' Parameter 3 : (String) "Unlocked"
' Parameter 4 : (Boolean) False
'--------------------------------------------------

long528 = settingRepository1.GetAttr("MOMENT_OVER_ACCELERATION_Nanometric")
'--------------------------------------------------
' Parameter 1 : (String) "MOMENT_OVER_ACCELERATION_Nanometric"
' Returned value : (Variant) (Long) 1
'--------------------------------------------------

Dim bSTR1055
bSTR1055 = ""
Dim bSTR1056
bSTR1056 = ""
Dim boolean528
settingRepository1.GetAttrInfo "MOMENT_OVER_ACCELERATION_Nanometric", bSTR1055, bSTR1056, boolean528
'--------------------------------------------------
' Parameter 1 : (String) "MOMENT_OVER_ACCELERATION_Nanometric"
' Parameter 2 : (String) "Default value"
' Parameter 3 : (String) "Unlocked"
' Parameter 4 : (Boolean) False
'--------------------------------------------------

long529 = settingRepository1.GetAttr("MOMENT_OVER_ROTATIONAL_ACCELERATION")
'--------------------------------------------------
' Parameter 1 : (String) "MOMENT_OVER_ROTATIONAL_ACCELERATION"
' Returned value : (Variant) (Long) 1
'--------------------------------------------------

Dim bSTR1057
bSTR1057 = ""
Dim bSTR1058
bSTR1058 = ""
Dim boolean529
settingRepository1.GetAttrInfo "MOMENT_OVER_ROTATIONAL_ACCELERATION", bSTR1057, bSTR1058, boolean529
'--------------------------------------------------
' Parameter 1 : (String) "MOMENT_OVER_ROTATIONAL_ACCELERATION"
' Parameter 2 : (String) "Default value"
' Parameter 3 : (String) "Unlocked"
' Parameter 4 : (Boolean) False
'--------------------------------------------------

long530 = settingRepository1.GetAttr("MOMENT_OVER_ROTATIONAL_ACCELERATION_Large")
'--------------------------------------------------
' Parameter 1 : (String) "MOMENT_OVER_ROTATIONAL_ACCELERATION_Large"
' Returned value : (Variant) (Long) 1
'--------------------------------------------------

Dim bSTR1059
bSTR1059 = ""
Dim bSTR1060
bSTR1060 = ""
Dim boolean530
settingRepository1.GetAttrInfo "MOMENT_OVER_ROTATIONAL_ACCELERATION_Large", bSTR1059, bSTR1060, boolean530
'--------------------------------------------------
' Parameter 1 : (String) "MOMENT_OVER_ROTATIONAL_ACCELERATION_Large"
' Parameter 2 : (String) "Default value"
' Parameter 3 : (String) "Unlocked"
' Parameter 4 : (Boolean) False
'--------------------------------------------------

long531 = settingRepository1.GetAttr("MOMENT_OVER_ROTATIONAL_ACCELERATION_ExtraLarge")
'--------------------------------------------------
' Parameter 1 : (String) "MOMENT_OVER_ROTATIONAL_ACCELERATION_ExtraLarge"
' Returned value : (Variant) (Long) 1
'--------------------------------------------------

Dim bSTR1061
bSTR1061 = ""
Dim bSTR1062
bSTR1062 = ""
Dim boolean531
settingRepository1.GetAttrInfo "MOMENT_OVER_ROTATIONAL_ACCELERATION_ExtraLarge", bSTR1061, bSTR1062, boolean531
'--------------------------------------------------
' Parameter 1 : (String) "MOMENT_OVER_ROTATIONAL_ACCELERATION_ExtraLarge"
' Parameter 2 : (String) "Default value"
' Parameter 3 : (String) "Unlocked"
' Parameter 4 : (Boolean) False
'--------------------------------------------------

long532 = settingRepository1.GetAttr("MOMENT_OVER_ROTATIONAL_ACCELERATION_Small")
'--------------------------------------------------
' Parameter 1 : (String) "MOMENT_OVER_ROTATIONAL_ACCELERATION_Small"
' Returned value : (Variant) (Long) 1
'--------------------------------------------------

Dim bSTR1063
bSTR1063 = ""
Dim bSTR1064
bSTR1064 = ""
Dim boolean532
settingRepository1.GetAttrInfo "MOMENT_OVER_ROTATIONAL_ACCELERATION_Small", bSTR1063, bSTR1064, boolean532
'--------------------------------------------------
' Parameter 1 : (String) "MOMENT_OVER_ROTATIONAL_ACCELERATION_Small"
' Parameter 2 : (String) "Default value"
' Parameter 3 : (String) "Unlocked"
' Parameter 4 : (Boolean) False
'--------------------------------------------------

long533 = settingRepository1.GetAttr("MOMENT_OVER_ROTATIONAL_ACCELERATION_ExtraSmall")
'--------------------------------------------------
' Parameter 1 : (String) "MOMENT_OVER_ROTATIONAL_ACCELERATION_ExtraSmall"
' Returned value : (Variant) (Long) 1
'--------------------------------------------------

Dim bSTR1065
bSTR1065 = ""
Dim bSTR1066
bSTR1066 = ""
Dim boolean533
settingRepository1.GetAttrInfo "MOMENT_OVER_ROTATIONAL_ACCELERATION_ExtraSmall", bSTR1065, bSTR1066, boolean533
'--------------------------------------------------
' Parameter 1 : (String) "MOMENT_OVER_ROTATIONAL_ACCELERATION_ExtraSmall"
' Parameter 2 : (String) "Default value"
' Parameter 3 : (String) "Unlocked"
' Parameter 4 : (Boolean) False
'--------------------------------------------------

long534 = settingRepository1.GetAttr("MOMENT_OVER_ROTATIONAL_ACCELERATION_Nanometric")
'--------------------------------------------------
' Parameter 1 : (String) "MOMENT_OVER_ROTATIONAL_ACCELERATION_Nanometric"
' Returned value : (Variant) (Long) 1
'--------------------------------------------------

Dim bSTR1067
bSTR1067 = ""
Dim bSTR1068
bSTR1068 = ""
Dim boolean534
settingRepository1.GetAttrInfo "MOMENT_OVER_ROTATIONAL_ACCELERATION_Nanometric", bSTR1067, bSTR1068, boolean534
'--------------------------------------------------
' Parameter 1 : (String) "MOMENT_OVER_ROTATIONAL_ACCELERATION_Nanometric"
' Parameter 2 : (String) "Default value"
' Parameter 3 : (String) "Unlocked"
' Parameter 4 : (Boolean) False
'--------------------------------------------------

long535 = settingRepository1.GetAttr("PRESSURE_OVER_ACCELERATION")
'--------------------------------------------------
' Parameter 1 : (String) "PRESSURE_OVER_ACCELERATION"
' Returned value : (Variant) (Long) 1
'--------------------------------------------------

Dim bSTR1069
bSTR1069 = ""
Dim bSTR1070
bSTR1070 = ""
Dim boolean535
settingRepository1.GetAttrInfo "PRESSURE_OVER_ACCELERATION", bSTR1069, bSTR1070, boolean535
'--------------------------------------------------
' Parameter 1 : (String) "PRESSURE_OVER_ACCELERATION"
' Parameter 2 : (String) "Default value"
' Parameter 3 : (String) "Unlocked"
' Parameter 4 : (Boolean) False
'--------------------------------------------------

long536 = settingRepository1.GetAttr("PRESSURE_OVER_ACCELERATION_Large")
'--------------------------------------------------
' Parameter 1 : (String) "PRESSURE_OVER_ACCELERATION_Large"
' Returned value : (Variant) (Long) 1
'--------------------------------------------------

Dim bSTR1071
bSTR1071 = ""
Dim bSTR1072
bSTR1072 = ""
Dim boolean536
settingRepository1.GetAttrInfo "PRESSURE_OVER_ACCELERATION_Large", bSTR1071, bSTR1072, boolean536
'--------------------------------------------------
' Parameter 1 : (String) "PRESSURE_OVER_ACCELERATION_Large"
' Parameter 2 : (String) "Default value"
' Parameter 3 : (String) "Unlocked"
' Parameter 4 : (Boolean) False
'--------------------------------------------------

long537 = settingRepository1.GetAttr("PRESSURE_OVER_ACCELERATION_ExtraLarge")
'--------------------------------------------------
' Parameter 1 : (String) "PRESSURE_OVER_ACCELERATION_ExtraLarge"
' Returned value : (Variant) (Long) 1
'--------------------------------------------------

Dim bSTR1073
bSTR1073 = ""
Dim bSTR1074
bSTR1074 = ""
Dim boolean537
settingRepository1.GetAttrInfo "PRESSURE_OVER_ACCELERATION_ExtraLarge", bSTR1073, bSTR1074, boolean537
'--------------------------------------------------
' Parameter 1 : (String) "PRESSURE_OVER_ACCELERATION_ExtraLarge"
' Parameter 2 : (String) "Default value"
' Parameter 3 : (String) "Unlocked"
' Parameter 4 : (Boolean) False
'--------------------------------------------------

long538 = settingRepository1.GetAttr("PRESSURE_OVER_ACCELERATION_Small")
'--------------------------------------------------
' Parameter 1 : (String) "PRESSURE_OVER_ACCELERATION_Small"
' Returned value : (Variant) (Long) 1
'--------------------------------------------------

Dim bSTR1075
bSTR1075 = ""
Dim bSTR1076
bSTR1076 = ""
Dim boolean538
settingRepository1.GetAttrInfo "PRESSURE_OVER_ACCELERATION_Small", bSTR1075, bSTR1076, boolean538
'--------------------------------------------------
' Parameter 1 : (String) "PRESSURE_OVER_ACCELERATION_Small"
' Parameter 2 : (String) "Default value"
' Parameter 3 : (String) "Unlocked"
' Parameter 4 : (Boolean) False
'--------------------------------------------------

long539 = settingRepository1.GetAttr("PRESSURE_OVER_ACCELERATION_ExtraSmall")
'--------------------------------------------------
' Parameter 1 : (String) "PRESSURE_OVER_ACCELERATION_ExtraSmall"
' Returned value : (Variant) (Long) 1
'--------------------------------------------------

Dim bSTR1077
bSTR1077 = ""
Dim bSTR1078
bSTR1078 = ""
Dim boolean539
settingRepository1.GetAttrInfo "PRESSURE_OVER_ACCELERATION_ExtraSmall", bSTR1077, bSTR1078, boolean539
'--------------------------------------------------
' Parameter 1 : (String) "PRESSURE_OVER_ACCELERATION_ExtraSmall"
' Parameter 2 : (String) "Default value"
' Parameter 3 : (String) "Unlocked"
' Parameter 4 : (Boolean) False
'--------------------------------------------------

long540 = settingRepository1.GetAttr("PRESSURE_OVER_ACCELERATION_Nanometric")
'--------------------------------------------------
' Parameter 1 : (String) "PRESSURE_OVER_ACCELERATION_Nanometric"
' Returned value : (Variant) (Long) 1
'--------------------------------------------------

Dim bSTR1079
bSTR1079 = ""
Dim bSTR1080
bSTR1080 = ""
Dim boolean540
settingRepository1.GetAttrInfo "PRESSURE_OVER_ACCELERATION_Nanometric", bSTR1079, bSTR1080, boolean540
'--------------------------------------------------
' Parameter 1 : (String) "PRESSURE_OVER_ACCELERATION_Nanometric"
' Parameter 2 : (String) "Default value"
' Parameter 3 : (String) "Unlocked"
' Parameter 4 : (Boolean) False
'--------------------------------------------------

long541 = settingRepository1.GetAttr("PRESSURE_OVER_ROTATIONAL_ACCELERATION")
'--------------------------------------------------
' Parameter 1 : (String) "PRESSURE_OVER_ROTATIONAL_ACCELERATION"
' Returned value : (Variant) (Long) 1
'--------------------------------------------------

Dim bSTR1081
bSTR1081 = ""
Dim bSTR1082
bSTR1082 = ""
Dim boolean541
settingRepository1.GetAttrInfo "PRESSURE_OVER_ROTATIONAL_ACCELERATION", bSTR1081, bSTR1082, boolean541
'--------------------------------------------------
' Parameter 1 : (String) "PRESSURE_OVER_ROTATIONAL_ACCELERATION"
' Parameter 2 : (String) "Default value"
' Parameter 3 : (String) "Unlocked"
' Parameter 4 : (Boolean) False
'--------------------------------------------------

long542 = settingRepository1.GetAttr("PRESSURE_OVER_ROTATIONAL_ACCELERATION_Large")
'--------------------------------------------------
' Parameter 1 : (String) "PRESSURE_OVER_ROTATIONAL_ACCELERATION_Large"
' Returned value : (Variant) (Long) 1
'--------------------------------------------------

Dim bSTR1083
bSTR1083 = ""
Dim bSTR1084
bSTR1084 = ""
Dim boolean542
settingRepository1.GetAttrInfo "PRESSURE_OVER_ROTATIONAL_ACCELERATION_Large", bSTR1083, bSTR1084, boolean542
'--------------------------------------------------
' Parameter 1 : (String) "PRESSURE_OVER_ROTATIONAL_ACCELERATION_Large"
' Parameter 2 : (String) "Default value"
' Parameter 3 : (String) "Unlocked"
' Parameter 4 : (Boolean) False
'--------------------------------------------------

long543 = settingRepository1.GetAttr("PRESSURE_OVER_ROTATIONAL_ACCELERATION_ExtraLarge")
'--------------------------------------------------
' Parameter 1 : (String) "PRESSURE_OVER_ROTATIONAL_ACCELERATION_ExtraLarge"
' Returned value : (Variant) (Long) 1
'--------------------------------------------------

Dim bSTR1085
bSTR1085 = ""
Dim bSTR1086
bSTR1086 = ""
Dim boolean543
settingRepository1.GetAttrInfo "PRESSURE_OVER_ROTATIONAL_ACCELERATION_ExtraLarge", bSTR1085, bSTR1086, boolean543
'--------------------------------------------------
' Parameter 1 : (String) "PRESSURE_OVER_ROTATIONAL_ACCELERATION_ExtraLarge"
' Parameter 2 : (String) "Default value"
' Parameter 3 : (String) "Unlocked"
' Parameter 4 : (Boolean) False
'--------------------------------------------------

long544 = settingRepository1.GetAttr("PRESSURE_OVER_ROTATIONAL_ACCELERATION_Small")
'--------------------------------------------------
' Parameter 1 : (String) "PRESSURE_OVER_ROTATIONAL_ACCELERATION_Small"
' Returned value : (Variant) (Long) 1
'--------------------------------------------------

Dim bSTR1087
bSTR1087 = ""
Dim bSTR1088
bSTR1088 = ""
Dim boolean544
settingRepository1.GetAttrInfo "PRESSURE_OVER_ROTATIONAL_ACCELERATION_Small", bSTR1087, bSTR1088, boolean544
'--------------------------------------------------
' Parameter 1 : (String) "PRESSURE_OVER_ROTATIONAL_ACCELERATION_Small"
' Parameter 2 : (String) "Default value"
' Parameter 3 : (String) "Unlocked"
' Parameter 4 : (Boolean) False
'--------------------------------------------------

long545 = settingRepository1.GetAttr("PRESSURE_OVER_ROTATIONAL_ACCELERATION_ExtraSmall")
'--------------------------------------------------
' Parameter 1 : (String) "PRESSURE_OVER_ROTATIONAL_ACCELERATION_ExtraSmall"
' Returned value : (Variant) (Long) 1
'--------------------------------------------------

Dim bSTR1089
bSTR1089 = ""
Dim bSTR1090
bSTR1090 = ""
Dim boolean545
settingRepository1.GetAttrInfo "PRESSURE_OVER_ROTATIONAL_ACCELERATION_ExtraSmall", bSTR1089, bSTR1090, boolean545
'--------------------------------------------------
' Parameter 1 : (String) "PRESSURE_OVER_ROTATIONAL_ACCELERATION_ExtraSmall"
' Parameter 2 : (String) "Default value"
' Parameter 3 : (String) "Unlocked"
' Parameter 4 : (Boolean) False
'--------------------------------------------------

long546 = settingRepository1.GetAttr("PRESSURE_OVER_ROTATIONAL_ACCELERATION_Nanometric")
'--------------------------------------------------
' Parameter 1 : (String) "PRESSURE_OVER_ROTATIONAL_ACCELERATION_Nanometric"
' Returned value : (Variant) (Long) 1
'--------------------------------------------------

Dim bSTR1091
bSTR1091 = ""
Dim bSTR1092
bSTR1092 = ""
Dim boolean546
settingRepository1.GetAttrInfo "PRESSURE_OVER_ROTATIONAL_ACCELERATION_Nanometric", bSTR1091, bSTR1092, boolean546
'--------------------------------------------------
' Parameter 1 : (String) "PRESSURE_OVER_ROTATIONAL_ACCELERATION_Nanometric"
' Parameter 2 : (String) "Default value"
' Parameter 3 : (String) "Unlocked"
' Parameter 4 : (Boolean) False
'--------------------------------------------------

long547 = settingRepository1.GetAttr("FORCE_OVER_PRESSURE")
'--------------------------------------------------
' Parameter 1 : (String) "FORCE_OVER_PRESSURE"
' Returned value : (Variant) (Long) 1
'--------------------------------------------------

Dim bSTR1093
bSTR1093 = ""
Dim bSTR1094
bSTR1094 = ""
Dim boolean547
settingRepository1.GetAttrInfo "FORCE_OVER_PRESSURE", bSTR1093, bSTR1094, boolean547
'--------------------------------------------------
' Parameter 1 : (String) "FORCE_OVER_PRESSURE"
' Parameter 2 : (String) "Default value"
' Parameter 3 : (String) "Unlocked"
' Parameter 4 : (Boolean) False
'--------------------------------------------------

long548 = settingRepository1.GetAttr("FORCE_OVER_PRESSURE_Large")
'--------------------------------------------------
' Parameter 1 : (String) "FORCE_OVER_PRESSURE_Large"
' Returned value : (Variant) (Long) 1
'--------------------------------------------------

Dim bSTR1095
bSTR1095 = ""
Dim bSTR1096
bSTR1096 = ""
Dim boolean548
settingRepository1.GetAttrInfo "FORCE_OVER_PRESSURE_Large", bSTR1095, bSTR1096, boolean548
'--------------------------------------------------
' Parameter 1 : (String) "FORCE_OVER_PRESSURE_Large"
' Parameter 2 : (String) "Default value"
' Parameter 3 : (String) "Unlocked"
' Parameter 4 : (Boolean) False
'--------------------------------------------------

long549 = settingRepository1.GetAttr("FORCE_OVER_PRESSURE_ExtraLarge")
'--------------------------------------------------
' Parameter 1 : (String) "FORCE_OVER_PRESSURE_ExtraLarge"
' Returned value : (Variant) (Long) 1
'--------------------------------------------------

Dim bSTR1097
bSTR1097 = ""
Dim bSTR1098
bSTR1098 = ""
Dim boolean549
settingRepository1.GetAttrInfo "FORCE_OVER_PRESSURE_ExtraLarge", bSTR1097, bSTR1098, boolean549
'--------------------------------------------------
' Parameter 1 : (String) "FORCE_OVER_PRESSURE_ExtraLarge"
' Parameter 2 : (String) "Default value"
' Parameter 3 : (String) "Unlocked"
' Parameter 4 : (Boolean) False
'--------------------------------------------------

long550 = settingRepository1.GetAttr("FORCE_OVER_PRESSURE_Small")
'--------------------------------------------------
' Parameter 1 : (String) "FORCE_OVER_PRESSURE_Small"
' Returned value : (Variant) (Long) 1
'--------------------------------------------------

Dim bSTR1099
bSTR1099 = ""
Dim bSTR1100
bSTR1100 = ""
Dim boolean550
settingRepository1.GetAttrInfo "FORCE_OVER_PRESSURE_Small", bSTR1099, bSTR1100, boolean550
'--------------------------------------------------
' Parameter 1 : (String) "FORCE_OVER_PRESSURE_Small"
' Parameter 2 : (String) "Default value"
' Parameter 3 : (String) "Unlocked"
' Parameter 4 : (Boolean) False
'--------------------------------------------------

long551 = settingRepository1.GetAttr("FORCE_OVER_PRESSURE_ExtraSmall")
'--------------------------------------------------
' Parameter 1 : (String) "FORCE_OVER_PRESSURE_ExtraSmall"
' Returned value : (Variant) (Long) 1
'--------------------------------------------------

Dim bSTR1101
bSTR1101 = ""
Dim bSTR1102
bSTR1102 = ""
Dim boolean551
settingRepository1.GetAttrInfo "FORCE_OVER_PRESSURE_ExtraSmall", bSTR1101, bSTR1102, boolean551
'--------------------------------------------------
' Parameter 1 : (String) "FORCE_OVER_PRESSURE_ExtraSmall"
' Parameter 2 : (String) "Default value"
' Parameter 3 : (String) "Unlocked"
' Parameter 4 : (Boolean) False
'--------------------------------------------------

long552 = settingRepository1.GetAttr("FORCE_OVER_PRESSURE_Nanometric")
'--------------------------------------------------
' Parameter 1 : (String) "FORCE_OVER_PRESSURE_Nanometric"
' Returned value : (Variant) (Long) 1
'--------------------------------------------------

Dim bSTR1103
bSTR1103 = ""
Dim bSTR1104
bSTR1104 = ""
Dim boolean552
settingRepository1.GetAttrInfo "FORCE_OVER_PRESSURE_Nanometric", bSTR1103, bSTR1104, boolean552
'--------------------------------------------------
' Parameter 1 : (String) "FORCE_OVER_PRESSURE_Nanometric"
' Parameter 2 : (String) "Default value"
' Parameter 3 : (String) "Unlocked"
' Parameter 4 : (Boolean) False
'--------------------------------------------------

long553 = settingRepository1.GetAttr("MOMENT_OVER_PRESSURE")
'--------------------------------------------------
' Parameter 1 : (String) "MOMENT_OVER_PRESSURE"
' Returned value : (Variant) (Long) 1
'--------------------------------------------------

Dim bSTR1105
bSTR1105 = ""
Dim bSTR1106
bSTR1106 = ""
Dim boolean553
settingRepository1.GetAttrInfo "MOMENT_OVER_PRESSURE", bSTR1105, bSTR1106, boolean553
'--------------------------------------------------
' Parameter 1 : (String) "MOMENT_OVER_PRESSURE"
' Parameter 2 : (String) "Default value"
' Parameter 3 : (String) "Unlocked"
' Parameter 4 : (Boolean) False
'--------------------------------------------------

long554 = settingRepository1.GetAttr("MOMENT_OVER_PRESSURE_Large")
'--------------------------------------------------
' Parameter 1 : (String) "MOMENT_OVER_PRESSURE_Large"
' Returned value : (Variant) (Long) 1
'--------------------------------------------------

Dim bSTR1107
bSTR1107 = ""
Dim bSTR1108
bSTR1108 = ""
Dim boolean554
settingRepository1.GetAttrInfo "MOMENT_OVER_PRESSURE_Large", bSTR1107, bSTR1108, boolean554
'--------------------------------------------------
' Parameter 1 : (String) "MOMENT_OVER_PRESSURE_Large"
' Parameter 2 : (String) "Default value"
' Parameter 3 : (String) "Unlocked"
' Parameter 4 : (Boolean) False
'--------------------------------------------------

long555 = settingRepository1.GetAttr("MOMENT_OVER_PRESSURE_ExtraLarge")
'--------------------------------------------------
' Parameter 1 : (String) "MOMENT_OVER_PRESSURE_ExtraLarge"
' Returned value : (Variant) (Long) 1
'--------------------------------------------------

Dim bSTR1109
bSTR1109 = ""
Dim bSTR1110
bSTR1110 = ""
Dim boolean555
settingRepository1.GetAttrInfo "MOMENT_OVER_PRESSURE_ExtraLarge", bSTR1109, bSTR1110, boolean555
'--------------------------------------------------
' Parameter 1 : (String) "MOMENT_OVER_PRESSURE_ExtraLarge"
' Parameter 2 : (String) "Default value"
' Parameter 3 : (String) "Unlocked"
' Parameter 4 : (Boolean) False
'--------------------------------------------------

long556 = settingRepository1.GetAttr("MOMENT_OVER_PRESSURE_Small")
'--------------------------------------------------
' Parameter 1 : (String) "MOMENT_OVER_PRESSURE_Small"
' Returned value : (Variant) (Long) 1
'--------------------------------------------------

Dim bSTR1111
bSTR1111 = ""
Dim bSTR1112
bSTR1112 = ""
Dim boolean556
settingRepository1.GetAttrInfo "MOMENT_OVER_PRESSURE_Small", bSTR1111, bSTR1112, boolean556
'--------------------------------------------------
' Parameter 1 : (String) "MOMENT_OVER_PRESSURE_Small"
' Parameter 2 : (String) "Default value"
' Parameter 3 : (String) "Unlocked"
' Parameter 4 : (Boolean) False
'--------------------------------------------------

long557 = settingRepository1.GetAttr("MOMENT_OVER_PRESSURE_ExtraSmall")
'--------------------------------------------------
' Parameter 1 : (String) "MOMENT_OVER_PRESSURE_ExtraSmall"
' Returned value : (Variant) (Long) 1
'--------------------------------------------------

Dim bSTR1113
bSTR1113 = ""
Dim bSTR1114
bSTR1114 = ""
Dim boolean557
settingRepository1.GetAttrInfo "MOMENT_OVER_PRESSURE_ExtraSmall", bSTR1113, bSTR1114, boolean557
'--------------------------------------------------
' Parameter 1 : (String) "MOMENT_OVER_PRESSURE_ExtraSmall"
' Parameter 2 : (String) "Default value"
' Parameter 3 : (String) "Unlocked"
' Parameter 4 : (Boolean) False
'--------------------------------------------------

long558 = settingRepository1.GetAttr("MOMENT_OVER_PRESSURE_Nanometric")
'--------------------------------------------------
' Parameter 1 : (String) "MOMENT_OVER_PRESSURE_Nanometric"
' Returned value : (Variant) (Long) 1
'--------------------------------------------------

Dim bSTR1115
bSTR1115 = ""
Dim bSTR1116
bSTR1116 = ""
Dim boolean558
settingRepository1.GetAttrInfo "MOMENT_OVER_PRESSURE_Nanometric", bSTR1115, bSTR1116, boolean558
'--------------------------------------------------
' Parameter 1 : (String) "MOMENT_OVER_PRESSURE_Nanometric"
' Parameter 2 : (String) "Default value"
' Parameter 3 : (String) "Unlocked"
' Parameter 4 : (Boolean) False
'--------------------------------------------------

long559 = settingRepository1.GetAttr("DISPLACEMENT_OVER_PRESSURE")
'--------------------------------------------------
' Parameter 1 : (String) "DISPLACEMENT_OVER_PRESSURE"
' Returned value : (Variant) (Long) 1
'--------------------------------------------------

Dim bSTR1117
bSTR1117 = ""
Dim bSTR1118
bSTR1118 = ""
Dim boolean559
settingRepository1.GetAttrInfo "DISPLACEMENT_OVER_PRESSURE", bSTR1117, bSTR1118, boolean559
'--------------------------------------------------
' Parameter 1 : (String) "DISPLACEMENT_OVER_PRESSURE"
' Parameter 2 : (String) "Default value"
' Parameter 3 : (String) "Unlocked"
' Parameter 4 : (Boolean) False
'--------------------------------------------------

long560 = settingRepository1.GetAttr("DISPLACEMENT_OVER_PRESSURE_Large")
'--------------------------------------------------
' Parameter 1 : (String) "DISPLACEMENT_OVER_PRESSURE_Large"
' Returned value : (Variant) (Long) 1
'--------------------------------------------------

Dim bSTR1119
bSTR1119 = ""
Dim bSTR1120
bSTR1120 = ""
Dim boolean560
settingRepository1.GetAttrInfo "DISPLACEMENT_OVER_PRESSURE_Large", bSTR1119, bSTR1120, boolean560
'--------------------------------------------------
' Parameter 1 : (String) "DISPLACEMENT_OVER_PRESSURE_Large"
' Parameter 2 : (String) "Default value"
' Parameter 3 : (String) "Unlocked"
' Parameter 4 : (Boolean) False
'--------------------------------------------------

long561 = settingRepository1.GetAttr("DISPLACEMENT_OVER_PRESSURE_ExtraLarge")
'--------------------------------------------------
' Parameter 1 : (String) "DISPLACEMENT_OVER_PRESSURE_ExtraLarge"
' Returned value : (Variant) (Long) 1
'--------------------------------------------------

Dim bSTR1121
bSTR1121 = ""
Dim bSTR1122
bSTR1122 = ""
Dim boolean561
settingRepository1.GetAttrInfo "DISPLACEMENT_OVER_PRESSURE_ExtraLarge", bSTR1121, bSTR1122, boolean561
'--------------------------------------------------
' Parameter 1 : (String) "DISPLACEMENT_OVER_PRESSURE_ExtraLarge"
' Parameter 2 : (String) "Default value"
' Parameter 3 : (String) "Unlocked"
' Parameter 4 : (Boolean) False
'--------------------------------------------------

long562 = settingRepository1.GetAttr("DISPLACEMENT_OVER_PRESSURE_Small")
'--------------------------------------------------
' Parameter 1 : (String) "DISPLACEMENT_OVER_PRESSURE_Small"
' Returned value : (Variant) (Long) 1
'--------------------------------------------------

Dim bSTR1123
bSTR1123 = ""
Dim bSTR1124
bSTR1124 = ""
Dim boolean562
settingRepository1.GetAttrInfo "DISPLACEMENT_OVER_PRESSURE_Small", bSTR1123, bSTR1124, boolean562
'--------------------------------------------------
' Parameter 1 : (String) "DISPLACEMENT_OVER_PRESSURE_Small"
' Parameter 2 : (String) "Default value"
' Parameter 3 : (String) "Unlocked"
' Parameter 4 : (Boolean) False
'--------------------------------------------------

long563 = settingRepository1.GetAttr("DISPLACEMENT_OVER_PRESSURE_ExtraSmall")
'--------------------------------------------------
' Parameter 1 : (String) "DISPLACEMENT_OVER_PRESSURE_ExtraSmall"
' Returned value : (Variant) (Long) 1
'--------------------------------------------------

Dim bSTR1125
bSTR1125 = ""
Dim bSTR1126
bSTR1126 = ""
Dim boolean563
settingRepository1.GetAttrInfo "DISPLACEMENT_OVER_PRESSURE_ExtraSmall", bSTR1125, bSTR1126, boolean563
'--------------------------------------------------
' Parameter 1 : (String) "DISPLACEMENT_OVER_PRESSURE_ExtraSmall"
' Parameter 2 : (String) "Default value"
' Parameter 3 : (String) "Unlocked"
' Parameter 4 : (Boolean) False
'--------------------------------------------------

long564 = settingRepository1.GetAttr("DISPLACEMENT_OVER_PRESSURE_Nanometric")
'--------------------------------------------------
' Parameter 1 : (String) "DISPLACEMENT_OVER_PRESSURE_Nanometric"
' Returned value : (Variant) (Long) 1
'--------------------------------------------------

Dim bSTR1127
bSTR1127 = ""
Dim bSTR1128
bSTR1128 = ""
Dim boolean564
settingRepository1.GetAttrInfo "DISPLACEMENT_OVER_PRESSURE_Nanometric", bSTR1127, bSTR1128, boolean564
'--------------------------------------------------
' Parameter 1 : (String) "DISPLACEMENT_OVER_PRESSURE_Nanometric"
' Parameter 2 : (String) "Default value"
' Parameter 3 : (String) "Unlocked"
' Parameter 4 : (Boolean) False
'--------------------------------------------------

long565 = settingRepository1.GetAttr("VELOCITY_OVER_PRESSURE")
'--------------------------------------------------
' Parameter 1 : (String) "VELOCITY_OVER_PRESSURE"
' Returned value : (Variant) (Long) 1
'--------------------------------------------------

Dim bSTR1129
bSTR1129 = ""
Dim bSTR1130
bSTR1130 = ""
Dim boolean565
settingRepository1.GetAttrInfo "VELOCITY_OVER_PRESSURE", bSTR1129, bSTR1130, boolean565
'--------------------------------------------------
' Parameter 1 : (String) "VELOCITY_OVER_PRESSURE"
' Parameter 2 : (String) "Default value"
' Parameter 3 : (String) "Unlocked"
' Parameter 4 : (Boolean) False
'--------------------------------------------------

long566 = settingRepository1.GetAttr("VELOCITY_OVER_PRESSURE_Large")
'--------------------------------------------------
' Parameter 1 : (String) "VELOCITY_OVER_PRESSURE_Large"
' Returned value : (Variant) (Long) 1
'--------------------------------------------------

Dim bSTR1131
bSTR1131 = ""
Dim bSTR1132
bSTR1132 = ""
Dim boolean566
settingRepository1.GetAttrInfo "VELOCITY_OVER_PRESSURE_Large", bSTR1131, bSTR1132, boolean566
'--------------------------------------------------
' Parameter 1 : (String) "VELOCITY_OVER_PRESSURE_Large"
' Parameter 2 : (String) "Default value"
' Parameter 3 : (String) "Unlocked"
' Parameter 4 : (Boolean) False
'--------------------------------------------------

long567 = settingRepository1.GetAttr("VELOCITY_OVER_PRESSURE_ExtraLarge")
'--------------------------------------------------
' Parameter 1 : (String) "VELOCITY_OVER_PRESSURE_ExtraLarge"
' Returned value : (Variant) (Long) 1
'--------------------------------------------------

Dim bSTR1133
bSTR1133 = ""
Dim bSTR1134
bSTR1134 = ""
Dim boolean567
settingRepository1.GetAttrInfo "VELOCITY_OVER_PRESSURE_ExtraLarge", bSTR1133, bSTR1134, boolean567
'--------------------------------------------------
' Parameter 1 : (String) "VELOCITY_OVER_PRESSURE_ExtraLarge"
' Parameter 2 : (String) "Default value"
' Parameter 3 : (String) "Unlocked"
' Parameter 4 : (Boolean) False
'--------------------------------------------------

long568 = settingRepository1.GetAttr("VELOCITY_OVER_PRESSURE_Small")
'--------------------------------------------------
' Parameter 1 : (String) "VELOCITY_OVER_PRESSURE_Small"
' Returned value : (Variant) (Long) 1
'--------------------------------------------------

Dim bSTR1135
bSTR1135 = ""
Dim bSTR1136
bSTR1136 = ""
Dim boolean568
settingRepository1.GetAttrInfo "VELOCITY_OVER_PRESSURE_Small", bSTR1135, bSTR1136, boolean568
'--------------------------------------------------
' Parameter 1 : (String) "VELOCITY_OVER_PRESSURE_Small"
' Parameter 2 : (String) "Default value"
' Parameter 3 : (String) "Unlocked"
' Parameter 4 : (Boolean) False
'--------------------------------------------------

long569 = settingRepository1.GetAttr("VELOCITY_OVER_PRESSURE_ExtraSmall")
'--------------------------------------------------
' Parameter 1 : (String) "VELOCITY_OVER_PRESSURE_ExtraSmall"
' Returned value : (Variant) (Long) 1
'--------------------------------------------------

Dim bSTR1137
bSTR1137 = ""
Dim bSTR1138
bSTR1138 = ""
Dim boolean569
settingRepository1.GetAttrInfo "VELOCITY_OVER_PRESSURE_ExtraSmall", bSTR1137, bSTR1138, boolean569
'--------------------------------------------------
' Parameter 1 : (String) "VELOCITY_OVER_PRESSURE_ExtraSmall"
' Parameter 2 : (String) "Default value"
' Parameter 3 : (String) "Unlocked"
' Parameter 4 : (Boolean) False
'--------------------------------------------------

long570 = settingRepository1.GetAttr("VELOCITY_OVER_PRESSURE_Nanometric")
'--------------------------------------------------
' Parameter 1 : (String) "VELOCITY_OVER_PRESSURE_Nanometric"
' Returned value : (Variant) (Long) 1
'--------------------------------------------------

Dim bSTR1139
bSTR1139 = ""
Dim bSTR1140
bSTR1140 = ""
Dim boolean570
settingRepository1.GetAttrInfo "VELOCITY_OVER_PRESSURE_Nanometric", bSTR1139, bSTR1140, boolean570
'--------------------------------------------------
' Parameter 1 : (String) "VELOCITY_OVER_PRESSURE_Nanometric"
' Parameter 2 : (String) "Default value"
' Parameter 3 : (String) "Unlocked"
' Parameter 4 : (Boolean) False
'--------------------------------------------------

long571 = settingRepository1.GetAttr("ACCELERATION_OVER_PRESSURE")
'--------------------------------------------------
' Parameter 1 : (String) "ACCELERATION_OVER_PRESSURE"
' Returned value : (Variant) (Long) 1
'--------------------------------------------------

Dim bSTR1141
bSTR1141 = ""
Dim bSTR1142
bSTR1142 = ""
Dim boolean571
settingRepository1.GetAttrInfo "ACCELERATION_OVER_PRESSURE", bSTR1141, bSTR1142, boolean571
'--------------------------------------------------
' Parameter 1 : (String) "ACCELERATION_OVER_PRESSURE"
' Parameter 2 : (String) "Default value"
' Parameter 3 : (String) "Unlocked"
' Parameter 4 : (Boolean) False
'--------------------------------------------------

long572 = settingRepository1.GetAttr("ACCELERATION_OVER_PRESSURE_Large")
'--------------------------------------------------
' Parameter 1 : (String) "ACCELERATION_OVER_PRESSURE_Large"
' Returned value : (Variant) (Long) 1
'--------------------------------------------------

Dim bSTR1143
bSTR1143 = ""
Dim bSTR1144
bSTR1144 = ""
Dim boolean572
settingRepository1.GetAttrInfo "ACCELERATION_OVER_PRESSURE_Large", bSTR1143, bSTR1144, boolean572
'--------------------------------------------------
' Parameter 1 : (String) "ACCELERATION_OVER_PRESSURE_Large"
' Parameter 2 : (String) "Default value"
' Parameter 3 : (String) "Unlocked"
' Parameter 4 : (Boolean) False
'--------------------------------------------------

long573 = settingRepository1.GetAttr("ACCELERATION_OVER_PRESSURE_ExtraLarge")
'--------------------------------------------------
' Parameter 1 : (String) "ACCELERATION_OVER_PRESSURE_ExtraLarge"
' Returned value : (Variant) (Long) 1
'--------------------------------------------------

Dim bSTR1145
bSTR1145 = ""
Dim bSTR1146
bSTR1146 = ""
Dim boolean573
settingRepository1.GetAttrInfo "ACCELERATION_OVER_PRESSURE_ExtraLarge", bSTR1145, bSTR1146, boolean573
'--------------------------------------------------
' Parameter 1 : (String) "ACCELERATION_OVER_PRESSURE_ExtraLarge"
' Parameter 2 : (String) "Default value"
' Parameter 3 : (String) "Unlocked"
' Parameter 4 : (Boolean) False
'--------------------------------------------------

long574 = settingRepository1.GetAttr("ACCELERATION_OVER_PRESSURE_Small")
'--------------------------------------------------
' Parameter 1 : (String) "ACCELERATION_OVER_PRESSURE_Small"
' Returned value : (Variant) (Long) 1
'--------------------------------------------------

Dim bSTR1147
bSTR1147 = ""
Dim bSTR1148
bSTR1148 = ""
Dim boolean574
settingRepository1.GetAttrInfo "ACCELERATION_OVER_PRESSURE_Small", bSTR1147, bSTR1148, boolean574
'--------------------------------------------------
' Parameter 1 : (String) "ACCELERATION_OVER_PRESSURE_Small"
' Parameter 2 : (String) "Default value"
' Parameter 3 : (String) "Unlocked"
' Parameter 4 : (Boolean) False
'--------------------------------------------------

long575 = settingRepository1.GetAttr("ACCELERATION_OVER_PRESSURE_ExtraSmall")
'--------------------------------------------------
' Parameter 1 : (String) "ACCELERATION_OVER_PRESSURE_ExtraSmall"
' Returned value : (Variant) (Long) 1
'--------------------------------------------------

Dim bSTR1149
bSTR1149 = ""
Dim bSTR1150
bSTR1150 = ""
Dim boolean575
settingRepository1.GetAttrInfo "ACCELERATION_OVER_PRESSURE_ExtraSmall", bSTR1149, bSTR1150, boolean575
'--------------------------------------------------
' Parameter 1 : (String) "ACCELERATION_OVER_PRESSURE_ExtraSmall"
' Parameter 2 : (String) "Default value"
' Parameter 3 : (String) "Unlocked"
' Parameter 4 : (Boolean) False
'--------------------------------------------------

long576 = settingRepository1.GetAttr("ACCELERATION_OVER_PRESSURE_Nanometric")
'--------------------------------------------------
' Parameter 1 : (String) "ACCELERATION_OVER_PRESSURE_Nanometric"
' Returned value : (Variant) (Long) 1
'--------------------------------------------------

Dim bSTR1151
bSTR1151 = ""
Dim bSTR1152
bSTR1152 = ""
Dim boolean576
settingRepository1.GetAttrInfo "ACCELERATION_OVER_PRESSURE_Nanometric", bSTR1151, bSTR1152, boolean576
'--------------------------------------------------
' Parameter 1 : (String) "ACCELERATION_OVER_PRESSURE_Nanometric"
' Parameter 2 : (String) "Default value"
' Parameter 3 : (String) "Unlocked"
' Parameter 4 : (Boolean) False
'--------------------------------------------------

long577 = settingRepository1.GetAttr("ROTATION_OVER_PRESSURE")
'--------------------------------------------------
' Parameter 1 : (String) "ROTATION_OVER_PRESSURE"
' Returned value : (Variant) (Long) 1
'--------------------------------------------------

Dim bSTR1153
bSTR1153 = ""
Dim bSTR1154
bSTR1154 = ""
Dim boolean577
settingRepository1.GetAttrInfo "ROTATION_OVER_PRESSURE", bSTR1153, bSTR1154, boolean577
'--------------------------------------------------
' Parameter 1 : (String) "ROTATION_OVER_PRESSURE"
' Parameter 2 : (String) "Default value"
' Parameter 3 : (String) "Unlocked"
' Parameter 4 : (Boolean) False
'--------------------------------------------------

long578 = settingRepository1.GetAttr("ROTATION_OVER_PRESSURE_Large")
'--------------------------------------------------
' Parameter 1 : (String) "ROTATION_OVER_PRESSURE_Large"
' Returned value : (Variant) (Long) 1
'--------------------------------------------------

Dim bSTR1155
bSTR1155 = ""
Dim bSTR1156
bSTR1156 = ""
Dim boolean578
settingRepository1.GetAttrInfo "ROTATION_OVER_PRESSURE_Large", bSTR1155, bSTR1156, boolean578
'--------------------------------------------------
' Parameter 1 : (String) "ROTATION_OVER_PRESSURE_Large"
' Parameter 2 : (String) "Default value"
' Parameter 3 : (String) "Unlocked"
' Parameter 4 : (Boolean) False
'--------------------------------------------------

long579 = settingRepository1.GetAttr("ROTATION_OVER_PRESSURE_ExtraLarge")
'--------------------------------------------------
' Parameter 1 : (String) "ROTATION_OVER_PRESSURE_ExtraLarge"
' Returned value : (Variant) (Long) 1
'--------------------------------------------------

Dim bSTR1157
bSTR1157 = ""
Dim bSTR1158
bSTR1158 = ""
Dim boolean579
settingRepository1.GetAttrInfo "ROTATION_OVER_PRESSURE_ExtraLarge", bSTR1157, bSTR1158, boolean579
'--------------------------------------------------
' Parameter 1 : (String) "ROTATION_OVER_PRESSURE_ExtraLarge"
' Parameter 2 : (String) "Default value"
' Parameter 3 : (String) "Unlocked"
' Parameter 4 : (Boolean) False
'--------------------------------------------------

long580 = settingRepository1.GetAttr("ROTATION_OVER_PRESSURE_Small")
'--------------------------------------------------
' Parameter 1 : (String) "ROTATION_OVER_PRESSURE_Small"
' Returned value : (Variant) (Long) 1
'--------------------------------------------------

Dim bSTR1159
bSTR1159 = ""
Dim bSTR1160
bSTR1160 = ""
Dim boolean580
settingRepository1.GetAttrInfo "ROTATION_OVER_PRESSURE_Small", bSTR1159, bSTR1160, boolean580
'--------------------------------------------------
' Parameter 1 : (String) "ROTATION_OVER_PRESSURE_Small"
' Parameter 2 : (String) "Default value"
' Parameter 3 : (String) "Unlocked"
' Parameter 4 : (Boolean) False
'--------------------------------------------------

long581 = settingRepository1.GetAttr("ROTATION_OVER_PRESSURE_ExtraSmall")
'--------------------------------------------------
' Parameter 1 : (String) "ROTATION_OVER_PRESSURE_ExtraSmall"
' Returned value : (Variant) (Long) 1
'--------------------------------------------------

Dim bSTR1161
bSTR1161 = ""
Dim bSTR1162
bSTR1162 = ""
Dim boolean581
settingRepository1.GetAttrInfo "ROTATION_OVER_PRESSURE_ExtraSmall", bSTR1161, bSTR1162, boolean581
'--------------------------------------------------
' Parameter 1 : (String) "ROTATION_OVER_PRESSURE_ExtraSmall"
' Parameter 2 : (String) "Default value"
' Parameter 3 : (String) "Unlocked"
' Parameter 4 : (Boolean) False
'--------------------------------------------------

long582 = settingRepository1.GetAttr("ROTATION_OVER_PRESSURE_Nanometric")
'--------------------------------------------------
' Parameter 1 : (String) "ROTATION_OVER_PRESSURE_Nanometric"
' Returned value : (Variant) (Long) 1
'--------------------------------------------------

Dim bSTR1163
bSTR1163 = ""
Dim bSTR1164
bSTR1164 = ""
Dim boolean582
settingRepository1.GetAttrInfo "ROTATION_OVER_PRESSURE_Nanometric", bSTR1163, bSTR1164, boolean582
'--------------------------------------------------
' Parameter 1 : (String) "ROTATION_OVER_PRESSURE_Nanometric"
' Parameter 2 : (String) "Default value"
' Parameter 3 : (String) "Unlocked"
' Parameter 4 : (Boolean) False
'--------------------------------------------------

long583 = settingRepository1.GetAttr("PULSATION_OVER_PRESSURE")
'--------------------------------------------------
' Parameter 1 : (String) "PULSATION_OVER_PRESSURE"
' Returned value : (Variant) (Long) 1
'--------------------------------------------------

Dim bSTR1165
bSTR1165 = ""
Dim bSTR1166
bSTR1166 = ""
Dim boolean583
settingRepository1.GetAttrInfo "PULSATION_OVER_PRESSURE", bSTR1165, bSTR1166, boolean583
'--------------------------------------------------
' Parameter 1 : (String) "PULSATION_OVER_PRESSURE"
' Parameter 2 : (String) "Default value"
' Parameter 3 : (String) "Unlocked"
' Parameter 4 : (Boolean) False
'--------------------------------------------------

long584 = settingRepository1.GetAttr("PULSATION_OVER_PRESSURE_Large")
'--------------------------------------------------
' Parameter 1 : (String) "PULSATION_OVER_PRESSURE_Large"
' Returned value : (Variant) (Long) 1
'--------------------------------------------------

Dim bSTR1167
bSTR1167 = ""
Dim bSTR1168
bSTR1168 = ""
Dim boolean584
settingRepository1.GetAttrInfo "PULSATION_OVER_PRESSURE_Large", bSTR1167, bSTR1168, boolean584
'--------------------------------------------------
' Parameter 1 : (String) "PULSATION_OVER_PRESSURE_Large"
' Parameter 2 : (String) "Default value"
' Parameter 3 : (String) "Unlocked"
' Parameter 4 : (Boolean) False
'--------------------------------------------------

long585 = settingRepository1.GetAttr("PULSATION_OVER_PRESSURE_ExtraLarge")
'--------------------------------------------------
' Parameter 1 : (String) "PULSATION_OVER_PRESSURE_ExtraLarge"
' Returned value : (Variant) (Long) 1
'--------------------------------------------------

Dim bSTR1169
bSTR1169 = ""
Dim bSTR1170
bSTR1170 = ""
Dim boolean585
settingRepository1.GetAttrInfo "PULSATION_OVER_PRESSURE_ExtraLarge", bSTR1169, bSTR1170, boolean585
'--------------------------------------------------
' Parameter 1 : (String) "PULSATION_OVER_PRESSURE_ExtraLarge"
' Parameter 2 : (String) "Default value"
' Parameter 3 : (String) "Unlocked"
' Parameter 4 : (Boolean) False
'--------------------------------------------------

long586 = settingRepository1.GetAttr("PULSATION_OVER_PRESSURE_Small")
'--------------------------------------------------
' Parameter 1 : (String) "PULSATION_OVER_PRESSURE_Small"
' Returned value : (Variant) (Long) 1
'--------------------------------------------------

Dim bSTR1171
bSTR1171 = ""
Dim bSTR1172
bSTR1172 = ""
Dim boolean586
settingRepository1.GetAttrInfo "PULSATION_OVER_PRESSURE_Small", bSTR1171, bSTR1172, boolean586
'--------------------------------------------------
' Parameter 1 : (String) "PULSATION_OVER_PRESSURE_Small"
' Parameter 2 : (String) "Default value"
' Parameter 3 : (String) "Unlocked"
' Parameter 4 : (Boolean) False
'--------------------------------------------------

long587 = settingRepository1.GetAttr("PULSATION_OVER_PRESSURE_ExtraSmall")
'--------------------------------------------------
' Parameter 1 : (String) "PULSATION_OVER_PRESSURE_ExtraSmall"
' Returned value : (Variant) (Long) 1
'--------------------------------------------------

Dim bSTR1173
bSTR1173 = ""
Dim bSTR1174
bSTR1174 = ""
Dim boolean587
settingRepository1.GetAttrInfo "PULSATION_OVER_PRESSURE_ExtraSmall", bSTR1173, bSTR1174, boolean587
'--------------------------------------------------
' Parameter 1 : (String) "PULSATION_OVER_PRESSURE_ExtraSmall"
' Parameter 2 : (String) "Default value"
' Parameter 3 : (String) "Unlocked"
' Parameter 4 : (Boolean) False
'--------------------------------------------------

long588 = settingRepository1.GetAttr("PULSATION_OVER_PRESSURE_Nanometric")
'--------------------------------------------------
' Parameter 1 : (String) "PULSATION_OVER_PRESSURE_Nanometric"
' Returned value : (Variant) (Long) 1
'--------------------------------------------------

Dim bSTR1175
bSTR1175 = ""
Dim bSTR1176
bSTR1176 = ""
Dim boolean588
settingRepository1.GetAttrInfo "PULSATION_OVER_PRESSURE_Nanometric", bSTR1175, bSTR1176, boolean588
'--------------------------------------------------
' Parameter 1 : (String) "PULSATION_OVER_PRESSURE_Nanometric"
' Parameter 2 : (String) "Default value"
' Parameter 3 : (String) "Unlocked"
' Parameter 4 : (Boolean) False
'--------------------------------------------------

long589 = settingRepository1.GetAttr("ROTATIONAL_ACCELERATION_OVER_PRESSURE")
'--------------------------------------------------
' Parameter 1 : (String) "ROTATIONAL_ACCELERATION_OVER_PRESSURE"
' Returned value : (Variant) (Long) 1
'--------------------------------------------------

Dim bSTR1177
bSTR1177 = ""
Dim bSTR1178
bSTR1178 = ""
Dim boolean589
settingRepository1.GetAttrInfo "ROTATIONAL_ACCELERATION_OVER_PRESSURE", bSTR1177, bSTR1178, boolean589
'--------------------------------------------------
' Parameter 1 : (String) "ROTATIONAL_ACCELERATION_OVER_PRESSURE"
' Parameter 2 : (String) "Default value"
' Parameter 3 : (String) "Unlocked"
' Parameter 4 : (Boolean) False
'--------------------------------------------------

long590 = settingRepository1.GetAttr("ROTATIONAL_ACCELERATION_OVER_PRESSURE_Large")
'--------------------------------------------------
' Parameter 1 : (String) "ROTATIONAL_ACCELERATION_OVER_PRESSURE_Large"
' Returned value : (Variant) (Long) 1
'--------------------------------------------------

Dim bSTR1179
bSTR1179 = ""
Dim bSTR1180
bSTR1180 = ""
Dim boolean590
settingRepository1.GetAttrInfo "ROTATIONAL_ACCELERATION_OVER_PRESSURE_Large", bSTR1179, bSTR1180, boolean590
'--------------------------------------------------
' Parameter 1 : (String) "ROTATIONAL_ACCELERATION_OVER_PRESSURE_Large"
' Parameter 2 : (String) "Default value"
' Parameter 3 : (String) "Unlocked"
' Parameter 4 : (Boolean) False
'--------------------------------------------------

long591 = settingRepository1.GetAttr("ROTATIONAL_ACCELERATION_OVER_PRESSURE_ExtraLarge")
'--------------------------------------------------
' Parameter 1 : (String) "ROTATIONAL_ACCELERATION_OVER_PRESSURE_ExtraLarge"
' Returned value : (Variant) (Long) 1
'--------------------------------------------------

Dim bSTR1181
bSTR1181 = ""
Dim bSTR1182
bSTR1182 = ""
Dim boolean591
settingRepository1.GetAttrInfo "ROTATIONAL_ACCELERATION_OVER_PRESSURE_ExtraLarge", bSTR1181, bSTR1182, boolean591
'--------------------------------------------------
' Parameter 1 : (String) "ROTATIONAL_ACCELERATION_OVER_PRESSURE_ExtraLarge"
' Parameter 2 : (String) "Default value"
' Parameter 3 : (String) "Unlocked"
' Parameter 4 : (Boolean) False
'--------------------------------------------------

long592 = settingRepository1.GetAttr("ROTATIONAL_ACCELERATION_OVER_PRESSURE_Small")
'--------------------------------------------------
' Parameter 1 : (String) "ROTATIONAL_ACCELERATION_OVER_PRESSURE_Small"
' Returned value : (Variant) (Long) 1
'--------------------------------------------------

Dim bSTR1183
bSTR1183 = ""
Dim bSTR1184
bSTR1184 = ""
Dim boolean592
settingRepository1.GetAttrInfo "ROTATIONAL_ACCELERATION_OVER_PRESSURE_Small", bSTR1183, bSTR1184, boolean592
'--------------------------------------------------
' Parameter 1 : (String) "ROTATIONAL_ACCELERATION_OVER_PRESSURE_Small"
' Parameter 2 : (String) "Default value"
' Parameter 3 : (String) "Unlocked"
' Parameter 4 : (Boolean) False
'--------------------------------------------------

long593 = settingRepository1.GetAttr("ROTATIONAL_ACCELERATION_OVER_PRESSURE_ExtraSmall")
'--------------------------------------------------
' Parameter 1 : (String) "ROTATIONAL_ACCELERATION_OVER_PRESSURE_ExtraSmall"
' Returned value : (Variant) (Long) 1
'--------------------------------------------------

Dim bSTR1185
bSTR1185 = ""
Dim bSTR1186
bSTR1186 = ""
Dim boolean593
settingRepository1.GetAttrInfo "ROTATIONAL_ACCELERATION_OVER_PRESSURE_ExtraSmall", bSTR1185, bSTR1186, boolean593
'--------------------------------------------------
' Parameter 1 : (String) "ROTATIONAL_ACCELERATION_OVER_PRESSURE_ExtraSmall"
' Parameter 2 : (String) "Default value"
' Parameter 3 : (String) "Unlocked"
' Parameter 4 : (Boolean) False
'--------------------------------------------------

long594 = settingRepository1.GetAttr("ROTATIONAL_ACCELERATION_OVER_PRESSURE_Nanometric")
'--------------------------------------------------
' Parameter 1 : (String) "ROTATIONAL_ACCELERATION_OVER_PRESSURE_Nanometric"
' Returned value : (Variant) (Long) 1
'--------------------------------------------------

Dim bSTR1187
bSTR1187 = ""
Dim bSTR1188
bSTR1188 = ""
Dim boolean594
settingRepository1.GetAttrInfo "ROTATIONAL_ACCELERATION_OVER_PRESSURE_Nanometric", bSTR1187, bSTR1188, boolean594
'--------------------------------------------------
' Parameter 1 : (String) "ROTATIONAL_ACCELERATION_OVER_PRESSURE_Nanometric"
' Parameter 2 : (String) "Default value"
' Parameter 3 : (String) "Unlocked"
' Parameter 4 : (Boolean) False
'--------------------------------------------------

long595 = settingRepository1.GetAttr("FORCE_OVER_VOLUME_VELOCITY")
'--------------------------------------------------
' Parameter 1 : (String) "FORCE_OVER_VOLUME_VELOCITY"
' Returned value : (Variant) (Long) 1
'--------------------------------------------------

Dim bSTR1189
bSTR1189 = ""
Dim bSTR1190
bSTR1190 = ""
Dim boolean595
settingRepository1.GetAttrInfo "FORCE_OVER_VOLUME_VELOCITY", bSTR1189, bSTR1190, boolean595
'--------------------------------------------------
' Parameter 1 : (String) "FORCE_OVER_VOLUME_VELOCITY"
' Parameter 2 : (String) "Default value"
' Parameter 3 : (String) "Unlocked"
' Parameter 4 : (Boolean) False
'--------------------------------------------------

long596 = settingRepository1.GetAttr("FORCE_OVER_VOLUME_VELOCITY_Large")
'--------------------------------------------------
' Parameter 1 : (String) "FORCE_OVER_VOLUME_VELOCITY_Large"
' Returned value : (Variant) (Long) 1
'--------------------------------------------------

Dim bSTR1191
bSTR1191 = ""
Dim bSTR1192
bSTR1192 = ""
Dim boolean596
settingRepository1.GetAttrInfo "FORCE_OVER_VOLUME_VELOCITY_Large", bSTR1191, bSTR1192, boolean596
'--------------------------------------------------
' Parameter 1 : (String) "FORCE_OVER_VOLUME_VELOCITY_Large"
' Parameter 2 : (String) "Default value"
' Parameter 3 : (String) "Unlocked"
' Parameter 4 : (Boolean) False
'--------------------------------------------------

long597 = settingRepository1.GetAttr("FORCE_OVER_VOLUME_VELOCITY_ExtraLarge")
'--------------------------------------------------
' Parameter 1 : (String) "FORCE_OVER_VOLUME_VELOCITY_ExtraLarge"
' Returned value : (Variant) (Long) 1
'--------------------------------------------------

Dim bSTR1193
bSTR1193 = ""
Dim bSTR1194
bSTR1194 = ""
Dim boolean597
settingRepository1.GetAttrInfo "FORCE_OVER_VOLUME_VELOCITY_ExtraLarge", bSTR1193, bSTR1194, boolean597
'--------------------------------------------------
' Parameter 1 : (String) "FORCE_OVER_VOLUME_VELOCITY_ExtraLarge"
' Parameter 2 : (String) "Default value"
' Parameter 3 : (String) "Unlocked"
' Parameter 4 : (Boolean) False
'--------------------------------------------------

long598 = settingRepository1.GetAttr("FORCE_OVER_VOLUME_VELOCITY_Small")
'--------------------------------------------------
' Parameter 1 : (String) "FORCE_OVER_VOLUME_VELOCITY_Small"
' Returned value : (Variant) (Long) 1
'--------------------------------------------------

Dim bSTR1195
bSTR1195 = ""
Dim bSTR1196
bSTR1196 = ""
Dim boolean598
settingRepository1.GetAttrInfo "FORCE_OVER_VOLUME_VELOCITY_Small", bSTR1195, bSTR1196, boolean598
'--------------------------------------------------
' Parameter 1 : (String) "FORCE_OVER_VOLUME_VELOCITY_Small"
' Parameter 2 : (String) "Default value"
' Parameter 3 : (String) "Unlocked"
' Parameter 4 : (Boolean) False
'--------------------------------------------------

long599 = settingRepository1.GetAttr("FORCE_OVER_VOLUME_VELOCITY_ExtraSmall")
'--------------------------------------------------
' Parameter 1 : (String) "FORCE_OVER_VOLUME_VELOCITY_ExtraSmall"
' Returned value : (Variant) (Long) 1
'--------------------------------------------------

Dim bSTR1197
bSTR1197 = ""
Dim bSTR1198
bSTR1198 = ""
Dim boolean599
settingRepository1.GetAttrInfo "FORCE_OVER_VOLUME_VELOCITY_ExtraSmall", bSTR1197, bSTR1198, boolean599
'--------------------------------------------------
' Parameter 1 : (String) "FORCE_OVER_VOLUME_VELOCITY_ExtraSmall"
' Parameter 2 : (String) "Default value"
' Parameter 3 : (String) "Unlocked"
' Parameter 4 : (Boolean) False
'--------------------------------------------------

long600 = settingRepository1.GetAttr("FORCE_OVER_VOLUME_VELOCITY_Nanometric")
'--------------------------------------------------
' Parameter 1 : (String) "FORCE_OVER_VOLUME_VELOCITY_Nanometric"
' Returned value : (Variant) (Long) 1
'--------------------------------------------------

Dim bSTR1199
bSTR1199 = ""
Dim bSTR1200
bSTR1200 = ""
Dim boolean600
settingRepository1.GetAttrInfo "FORCE_OVER_VOLUME_VELOCITY_Nanometric", bSTR1199, bSTR1200, boolean600
'--------------------------------------------------
' Parameter 1 : (String) "FORCE_OVER_VOLUME_VELOCITY_Nanometric"
' Parameter 2 : (String) "Default value"
' Parameter 3 : (String) "Unlocked"
' Parameter 4 : (Boolean) False
'--------------------------------------------------

long601 = settingRepository1.GetAttr("MOMENT_OVER_VOLUME_VELOCITY")
'--------------------------------------------------
' Parameter 1 : (String) "MOMENT_OVER_VOLUME_VELOCITY"
' Returned value : (Variant) (Long) 1
'--------------------------------------------------

Dim bSTR1201
bSTR1201 = ""
Dim bSTR1202
bSTR1202 = ""
Dim boolean601
settingRepository1.GetAttrInfo "MOMENT_OVER_VOLUME_VELOCITY", bSTR1201, bSTR1202, boolean601
'--------------------------------------------------
' Parameter 1 : (String) "MOMENT_OVER_VOLUME_VELOCITY"
' Parameter 2 : (String) "Default value"
' Parameter 3 : (String) "Unlocked"
' Parameter 4 : (Boolean) False
'--------------------------------------------------

long602 = settingRepository1.GetAttr("MOMENT_OVER_VOLUME_VELOCITY_Large")
'--------------------------------------------------
' Parameter 1 : (String) "MOMENT_OVER_VOLUME_VELOCITY_Large"
' Returned value : (Variant) (Long) 1
'--------------------------------------------------

Dim bSTR1203
bSTR1203 = ""
Dim bSTR1204
bSTR1204 = ""
Dim boolean602
settingRepository1.GetAttrInfo "MOMENT_OVER_VOLUME_VELOCITY_Large", bSTR1203, bSTR1204, boolean602
'--------------------------------------------------
' Parameter 1 : (String) "MOMENT_OVER_VOLUME_VELOCITY_Large"
' Parameter 2 : (String) "Default value"
' Parameter 3 : (String) "Unlocked"
' Parameter 4 : (Boolean) False
'--------------------------------------------------

long603 = settingRepository1.GetAttr("MOMENT_OVER_VOLUME_VELOCITY_ExtraLarge")
'--------------------------------------------------
' Parameter 1 : (String) "MOMENT_OVER_VOLUME_VELOCITY_ExtraLarge"
' Returned value : (Variant) (Long) 1
'--------------------------------------------------

Dim bSTR1205
bSTR1205 = ""
Dim bSTR1206
bSTR1206 = ""
Dim boolean603
settingRepository1.GetAttrInfo "MOMENT_OVER_VOLUME_VELOCITY_ExtraLarge", bSTR1205, bSTR1206, boolean603
'--------------------------------------------------
' Parameter 1 : (String) "MOMENT_OVER_VOLUME_VELOCITY_ExtraLarge"
' Parameter 2 : (String) "Default value"
' Parameter 3 : (String) "Unlocked"
' Parameter 4 : (Boolean) False
'--------------------------------------------------

long604 = settingRepository1.GetAttr("MOMENT_OVER_VOLUME_VELOCITY_Small")
'--------------------------------------------------
' Parameter 1 : (String) "MOMENT_OVER_VOLUME_VELOCITY_Small"
' Returned value : (Variant) (Long) 1
'--------------------------------------------------

Dim bSTR1207
bSTR1207 = ""
Dim bSTR1208
bSTR1208 = ""
Dim boolean604
settingRepository1.GetAttrInfo "MOMENT_OVER_VOLUME_VELOCITY_Small", bSTR1207, bSTR1208, boolean604
'--------------------------------------------------
' Parameter 1 : (String) "MOMENT_OVER_VOLUME_VELOCITY_Small"
' Parameter 2 : (String) "Default value"
' Parameter 3 : (String) "Unlocked"
' Parameter 4 : (Boolean) False
'--------------------------------------------------

long605 = settingRepository1.GetAttr("MOMENT_OVER_VOLUME_VELOCITY_ExtraSmall")
'--------------------------------------------------
' Parameter 1 : (String) "MOMENT_OVER_VOLUME_VELOCITY_ExtraSmall"
' Returned value : (Variant) (Long) 1
'--------------------------------------------------

Dim bSTR1209
bSTR1209 = ""
Dim bSTR1210
bSTR1210 = ""
Dim boolean605
settingRepository1.GetAttrInfo "MOMENT_OVER_VOLUME_VELOCITY_ExtraSmall", bSTR1209, bSTR1210, boolean605
'--------------------------------------------------
' Parameter 1 : (String) "MOMENT_OVER_VOLUME_VELOCITY_ExtraSmall"
' Parameter 2 : (String) "Default value"
' Parameter 3 : (String) "Unlocked"
' Parameter 4 : (Boolean) False
'--------------------------------------------------

long606 = settingRepository1.GetAttr("MOMENT_OVER_VOLUME_VELOCITY_Nanometric")
'--------------------------------------------------
' Parameter 1 : (String) "MOMENT_OVER_VOLUME_VELOCITY_Nanometric"
' Returned value : (Variant) (Long) 1
'--------------------------------------------------

Dim bSTR1211
bSTR1211 = ""
Dim bSTR1212
bSTR1212 = ""
Dim boolean606
settingRepository1.GetAttrInfo "MOMENT_OVER_VOLUME_VELOCITY_Nanometric", bSTR1211, bSTR1212, boolean606
'--------------------------------------------------
' Parameter 1 : (String) "MOMENT_OVER_VOLUME_VELOCITY_Nanometric"
' Parameter 2 : (String) "Default value"
' Parameter 3 : (String) "Unlocked"
' Parameter 4 : (Boolean) False
'--------------------------------------------------

long607 = settingRepository1.GetAttr("DISPLACEMENT_OVER_VOLUME_VELOCITY")
'--------------------------------------------------
' Parameter 1 : (String) "DISPLACEMENT_OVER_VOLUME_VELOCITY"
' Returned value : (Variant) (Long) 1
'--------------------------------------------------

Dim bSTR1213
bSTR1213 = ""
Dim bSTR1214
bSTR1214 = ""
Dim boolean607
settingRepository1.GetAttrInfo "DISPLACEMENT_OVER_VOLUME_VELOCITY", bSTR1213, bSTR1214, boolean607
'--------------------------------------------------
' Parameter 1 : (String) "DISPLACEMENT_OVER_VOLUME_VELOCITY"
' Parameter 2 : (String) "Default value"
' Parameter 3 : (String) "Unlocked"
' Parameter 4 : (Boolean) False
'--------------------------------------------------

long608 = settingRepository1.GetAttr("DISPLACEMENT_OVER_VOLUME_VELOCITY_Large")
'--------------------------------------------------
' Parameter 1 : (String) "DISPLACEMENT_OVER_VOLUME_VELOCITY_Large"
' Returned value : (Variant) (Long) 1
'--------------------------------------------------

Dim bSTR1215
bSTR1215 = ""
Dim bSTR1216
bSTR1216 = ""
Dim boolean608
settingRepository1.GetAttrInfo "DISPLACEMENT_OVER_VOLUME_VELOCITY_Large", bSTR1215, bSTR1216, boolean608
'--------------------------------------------------
' Parameter 1 : (String) "DISPLACEMENT_OVER_VOLUME_VELOCITY_Large"
' Parameter 2 : (String) "Default value"
' Parameter 3 : (String) "Unlocked"
' Parameter 4 : (Boolean) False
'--------------------------------------------------

long609 = settingRepository1.GetAttr("DISPLACEMENT_OVER_VOLUME_VELOCITY_ExtraLarge")
'--------------------------------------------------
' Parameter 1 : (String) "DISPLACEMENT_OVER_VOLUME_VELOCITY_ExtraLarge"
' Returned value : (Variant) (Long) 1
'--------------------------------------------------

Dim bSTR1217
bSTR1217 = ""
Dim bSTR1218
bSTR1218 = ""
Dim boolean609
settingRepository1.GetAttrInfo "DISPLACEMENT_OVER_VOLUME_VELOCITY_ExtraLarge", bSTR1217, bSTR1218, boolean609
'--------------------------------------------------
' Parameter 1 : (String) "DISPLACEMENT_OVER_VOLUME_VELOCITY_ExtraLarge"
' Parameter 2 : (String) "Default value"
' Parameter 3 : (String) "Unlocked"
' Parameter 4 : (Boolean) False
'--------------------------------------------------

long610 = settingRepository1.GetAttr("DISPLACEMENT_OVER_VOLUME_VELOCITY_Small")
'--------------------------------------------------
' Parameter 1 : (String) "DISPLACEMENT_OVER_VOLUME_VELOCITY_Small"
' Returned value : (Variant) (Long) 1
'--------------------------------------------------

Dim bSTR1219
bSTR1219 = ""
Dim bSTR1220
bSTR1220 = ""
Dim boolean610
settingRepository1.GetAttrInfo "DISPLACEMENT_OVER_VOLUME_VELOCITY_Small", bSTR1219, bSTR1220, boolean610
'--------------------------------------------------
' Parameter 1 : (String) "DISPLACEMENT_OVER_VOLUME_VELOCITY_Small"
' Parameter 2 : (String) "Default value"
' Parameter 3 : (String) "Unlocked"
' Parameter 4 : (Boolean) False
'--------------------------------------------------

long611 = settingRepository1.GetAttr("DISPLACEMENT_OVER_VOLUME_VELOCITY_ExtraSmall")
'--------------------------------------------------
' Parameter 1 : (String) "DISPLACEMENT_OVER_VOLUME_VELOCITY_ExtraSmall"
' Returned value : (Variant) (Long) 1
'--------------------------------------------------

Dim bSTR1221
bSTR1221 = ""
Dim bSTR1222
bSTR1222 = ""
Dim boolean611
settingRepository1.GetAttrInfo "DISPLACEMENT_OVER_VOLUME_VELOCITY_ExtraSmall", bSTR1221, bSTR1222, boolean611
'--------------------------------------------------
' Parameter 1 : (String) "DISPLACEMENT_OVER_VOLUME_VELOCITY_ExtraSmall"
' Parameter 2 : (String) "Default value"
' Parameter 3 : (String) "Unlocked"
' Parameter 4 : (Boolean) False
'--------------------------------------------------

long612 = settingRepository1.GetAttr("DISPLACEMENT_OVER_VOLUME_VELOCITY_Nanometric")
'--------------------------------------------------
' Parameter 1 : (String) "DISPLACEMENT_OVER_VOLUME_VELOCITY_Nanometric"
' Returned value : (Variant) (Long) 1
'--------------------------------------------------

Dim bSTR1223
bSTR1223 = ""
Dim bSTR1224
bSTR1224 = ""
Dim boolean612
settingRepository1.GetAttrInfo "DISPLACEMENT_OVER_VOLUME_VELOCITY_Nanometric", bSTR1223, bSTR1224, boolean612
'--------------------------------------------------
' Parameter 1 : (String) "DISPLACEMENT_OVER_VOLUME_VELOCITY_Nanometric"
' Parameter 2 : (String) "Default value"
' Parameter 3 : (String) "Unlocked"
' Parameter 4 : (Boolean) False
'--------------------------------------------------

long613 = settingRepository1.GetAttr("VELOCITY_OVER_VOLUME_VELOCITY")
'--------------------------------------------------
' Parameter 1 : (String) "VELOCITY_OVER_VOLUME_VELOCITY"
' Returned value : (Variant) (Long) 1
'--------------------------------------------------

Dim bSTR1225
bSTR1225 = ""
Dim bSTR1226
bSTR1226 = ""
Dim boolean613
settingRepository1.GetAttrInfo "VELOCITY_OVER_VOLUME_VELOCITY", bSTR1225, bSTR1226, boolean613
'--------------------------------------------------
' Parameter 1 : (String) "VELOCITY_OVER_VOLUME_VELOCITY"
' Parameter 2 : (String) "Default value"
' Parameter 3 : (String) "Unlocked"
' Parameter 4 : (Boolean) False
'--------------------------------------------------

long614 = settingRepository1.GetAttr("VELOCITY_OVER_VOLUME_VELOCITY_Large")
'--------------------------------------------------
' Parameter 1 : (String) "VELOCITY_OVER_VOLUME_VELOCITY_Large"
' Returned value : (Variant) (Long) 1
'--------------------------------------------------

Dim bSTR1227
bSTR1227 = ""
Dim bSTR1228
bSTR1228 = ""
Dim boolean614
settingRepository1.GetAttrInfo "VELOCITY_OVER_VOLUME_VELOCITY_Large", bSTR1227, bSTR1228, boolean614
'--------------------------------------------------
' Parameter 1 : (String) "VELOCITY_OVER_VOLUME_VELOCITY_Large"
' Parameter 2 : (String) "Default value"
' Parameter 3 : (String) "Unlocked"
' Parameter 4 : (Boolean) False
'--------------------------------------------------

long615 = settingRepository1.GetAttr("VELOCITY_OVER_VOLUME_VELOCITY_ExtraLarge")
'--------------------------------------------------
' Parameter 1 : (String) "VELOCITY_OVER_VOLUME_VELOCITY_ExtraLarge"
' Returned value : (Variant) (Long) 1
'--------------------------------------------------

Dim bSTR1229
bSTR1229 = ""
Dim bSTR1230
bSTR1230 = ""
Dim boolean615
settingRepository1.GetAttrInfo "VELOCITY_OVER_VOLUME_VELOCITY_ExtraLarge", bSTR1229, bSTR1230, boolean615
'--------------------------------------------------
' Parameter 1 : (String) "VELOCITY_OVER_VOLUME_VELOCITY_ExtraLarge"
' Parameter 2 : (String) "Default value"
' Parameter 3 : (String) "Unlocked"
' Parameter 4 : (Boolean) False
'--------------------------------------------------

long616 = settingRepository1.GetAttr("VELOCITY_OVER_VOLUME_VELOCITY_Small")
'--------------------------------------------------
' Parameter 1 : (String) "VELOCITY_OVER_VOLUME_VELOCITY_Small"
' Returned value : (Variant) (Long) 1
'--------------------------------------------------

Dim bSTR1231
bSTR1231 = ""
Dim bSTR1232
bSTR1232 = ""
Dim boolean616
settingRepository1.GetAttrInfo "VELOCITY_OVER_VOLUME_VELOCITY_Small", bSTR1231, bSTR1232, boolean616
'--------------------------------------------------
' Parameter 1 : (String) "VELOCITY_OVER_VOLUME_VELOCITY_Small"
' Parameter 2 : (String) "Default value"
' Parameter 3 : (String) "Unlocked"
' Parameter 4 : (Boolean) False
'--------------------------------------------------

long617 = settingRepository1.GetAttr("VELOCITY_OVER_VOLUME_VELOCITY_ExtraSmall")
'--------------------------------------------------
' Parameter 1 : (String) "VELOCITY_OVER_VOLUME_VELOCITY_ExtraSmall"
' Returned value : (Variant) (Long) 1
'--------------------------------------------------

Dim bSTR1233
bSTR1233 = ""
Dim bSTR1234
bSTR1234 = ""
Dim boolean617
settingRepository1.GetAttrInfo "VELOCITY_OVER_VOLUME_VELOCITY_ExtraSmall", bSTR1233, bSTR1234, boolean617
'--------------------------------------------------
' Parameter 1 : (String) "VELOCITY_OVER_VOLUME_VELOCITY_ExtraSmall"
' Parameter 2 : (String) "Default value"
' Parameter 3 : (String) "Unlocked"
' Parameter 4 : (Boolean) False
'--------------------------------------------------

long618 = settingRepository1.GetAttr("VELOCITY_OVER_VOLUME_VELOCITY_Nanometric")
'--------------------------------------------------
' Parameter 1 : (String) "VELOCITY_OVER_VOLUME_VELOCITY_Nanometric"
' Returned value : (Variant) (Long) 1
'--------------------------------------------------

Dim bSTR1235
bSTR1235 = ""
Dim bSTR1236
bSTR1236 = ""
Dim boolean618
settingRepository1.GetAttrInfo "VELOCITY_OVER_VOLUME_VELOCITY_Nanometric", bSTR1235, bSTR1236, boolean618
'--------------------------------------------------
' Parameter 1 : (String) "VELOCITY_OVER_VOLUME_VELOCITY_Nanometric"
' Parameter 2 : (String) "Default value"
' Parameter 3 : (String) "Unlocked"
' Parameter 4 : (Boolean) False
'--------------------------------------------------

long619 = settingRepository1.GetAttr("ACCELERATION_OVER_VOLUME_VELOCITY")
'--------------------------------------------------
' Parameter 1 : (String) "ACCELERATION_OVER_VOLUME_VELOCITY"
' Returned value : (Variant) (Long) 1
'--------------------------------------------------

Dim bSTR1237
bSTR1237 = ""
Dim bSTR1238
bSTR1238 = ""
Dim boolean619
settingRepository1.GetAttrInfo "ACCELERATION_OVER_VOLUME_VELOCITY", bSTR1237, bSTR1238, boolean619
'--------------------------------------------------
' Parameter 1 : (String) "ACCELERATION_OVER_VOLUME_VELOCITY"
' Parameter 2 : (String) "Default value"
' Parameter 3 : (String) "Unlocked"
' Parameter 4 : (Boolean) False
'--------------------------------------------------

long620 = settingRepository1.GetAttr("ACCELERATION_OVER_VOLUME_VELOCITY_Large")
'--------------------------------------------------
' Parameter 1 : (String) "ACCELERATION_OVER_VOLUME_VELOCITY_Large"
' Returned value : (Variant) (Long) 1
'--------------------------------------------------

Dim bSTR1239
bSTR1239 = ""
Dim bSTR1240
bSTR1240 = ""
Dim boolean620
settingRepository1.GetAttrInfo "ACCELERATION_OVER_VOLUME_VELOCITY_Large", bSTR1239, bSTR1240, boolean620
'--------------------------------------------------
' Parameter 1 : (String) "ACCELERATION_OVER_VOLUME_VELOCITY_Large"
' Parameter 2 : (String) "Default value"
' Parameter 3 : (String) "Unlocked"
' Parameter 4 : (Boolean) False
'--------------------------------------------------

long621 = settingRepository1.GetAttr("ACCELERATION_OVER_VOLUME_VELOCITY_ExtraLarge")
'--------------------------------------------------
' Parameter 1 : (String) "ACCELERATION_OVER_VOLUME_VELOCITY_ExtraLarge"
' Returned value : (Variant) (Long) 1
'--------------------------------------------------

Dim bSTR1241
bSTR1241 = ""
Dim bSTR1242
bSTR1242 = ""
Dim boolean621
settingRepository1.GetAttrInfo "ACCELERATION_OVER_VOLUME_VELOCITY_ExtraLarge", bSTR1241, bSTR1242, boolean621
'--------------------------------------------------
' Parameter 1 : (String) "ACCELERATION_OVER_VOLUME_VELOCITY_ExtraLarge"
' Parameter 2 : (String) "Default value"
' Parameter 3 : (String) "Unlocked"
' Parameter 4 : (Boolean) False
'--------------------------------------------------

long622 = settingRepository1.GetAttr("ACCELERATION_OVER_VOLUME_VELOCITY_Small")
'--------------------------------------------------
' Parameter 1 : (String) "ACCELERATION_OVER_VOLUME_VELOCITY_Small"
' Returned value : (Variant) (Long) 1
'--------------------------------------------------

Dim bSTR1243
bSTR1243 = ""
Dim bSTR1244
bSTR1244 = ""
Dim boolean622
settingRepository1.GetAttrInfo "ACCELERATION_OVER_VOLUME_VELOCITY_Small", bSTR1243, bSTR1244, boolean622
'--------------------------------------------------
' Parameter 1 : (String) "ACCELERATION_OVER_VOLUME_VELOCITY_Small"
' Parameter 2 : (String) "Default value"
' Parameter 3 : (String) "Unlocked"
' Parameter 4 : (Boolean) False
'--------------------------------------------------

long623 = settingRepository1.GetAttr("ACCELERATION_OVER_VOLUME_VELOCITY_ExtraSmall")
'--------------------------------------------------
' Parameter 1 : (String) "ACCELERATION_OVER_VOLUME_VELOCITY_ExtraSmall"
' Returned value : (Variant) (Long) 1
'--------------------------------------------------

Dim bSTR1245
bSTR1245 = ""
Dim bSTR1246
bSTR1246 = ""
Dim boolean623
settingRepository1.GetAttrInfo "ACCELERATION_OVER_VOLUME_VELOCITY_ExtraSmall", bSTR1245, bSTR1246, boolean623
'--------------------------------------------------
' Parameter 1 : (String) "ACCELERATION_OVER_VOLUME_VELOCITY_ExtraSmall"
' Parameter 2 : (String) "Default value"
' Parameter 3 : (String) "Unlocked"
' Parameter 4 : (Boolean) False
'--------------------------------------------------

long624 = settingRepository1.GetAttr("ACCELERATION_OVER_VOLUME_VELOCITY_Nanometric")
'--------------------------------------------------
' Parameter 1 : (String) "ACCELERATION_OVER_VOLUME_VELOCITY_Nanometric"
' Returned value : (Variant) (Long) 1
'--------------------------------------------------

Dim bSTR1247
bSTR1247 = ""
Dim bSTR1248
bSTR1248 = ""
Dim boolean624
settingRepository1.GetAttrInfo "ACCELERATION_OVER_VOLUME_VELOCITY_Nanometric", bSTR1247, bSTR1248, boolean624
'--------------------------------------------------
' Parameter 1 : (String) "ACCELERATION_OVER_VOLUME_VELOCITY_Nanometric"
' Parameter 2 : (String) "Default value"
' Parameter 3 : (String) "Unlocked"
' Parameter 4 : (Boolean) False
'--------------------------------------------------

long625 = settingRepository1.GetAttr("ROTATION_OVER_VOLUME_VELOCITY")
'--------------------------------------------------
' Parameter 1 : (String) "ROTATION_OVER_VOLUME_VELOCITY"
' Returned value : (Variant) (Long) 1
'--------------------------------------------------

Dim bSTR1249
bSTR1249 = ""
Dim bSTR1250
bSTR1250 = ""
Dim boolean625
settingRepository1.GetAttrInfo "ROTATION_OVER_VOLUME_VELOCITY", bSTR1249, bSTR1250, boolean625
'--------------------------------------------------
' Parameter 1 : (String) "ROTATION_OVER_VOLUME_VELOCITY"
' Parameter 2 : (String) "Default value"
' Parameter 3 : (String) "Unlocked"
' Parameter 4 : (Boolean) False
'--------------------------------------------------

long626 = settingRepository1.GetAttr("ROTATION_OVER_VOLUME_VELOCITY_Large")
'--------------------------------------------------
' Parameter 1 : (String) "ROTATION_OVER_VOLUME_VELOCITY_Large"
' Returned value : (Variant) (Long) 1
'--------------------------------------------------

Dim bSTR1251
bSTR1251 = ""
Dim bSTR1252
bSTR1252 = ""
Dim boolean626
settingRepository1.GetAttrInfo "ROTATION_OVER_VOLUME_VELOCITY_Large", bSTR1251, bSTR1252, boolean626
'--------------------------------------------------
' Parameter 1 : (String) "ROTATION_OVER_VOLUME_VELOCITY_Large"
' Parameter 2 : (String) "Default value"
' Parameter 3 : (String) "Unlocked"
' Parameter 4 : (Boolean) False
'--------------------------------------------------

long627 = settingRepository1.GetAttr("ROTATION_OVER_VOLUME_VELOCITY_ExtraLarge")
'--------------------------------------------------
' Parameter 1 : (String) "ROTATION_OVER_VOLUME_VELOCITY_ExtraLarge"
' Returned value : (Variant) (Long) 1
'--------------------------------------------------

Dim bSTR1253
bSTR1253 = ""
Dim bSTR1254
bSTR1254 = ""
Dim boolean627
settingRepository1.GetAttrInfo "ROTATION_OVER_VOLUME_VELOCITY_ExtraLarge", bSTR1253, bSTR1254, boolean627
'--------------------------------------------------
' Parameter 1 : (String) "ROTATION_OVER_VOLUME_VELOCITY_ExtraLarge"
' Parameter 2 : (String) "Default value"
' Parameter 3 : (String) "Unlocked"
' Parameter 4 : (Boolean) False
'--------------------------------------------------

long628 = settingRepository1.GetAttr("ROTATION_OVER_VOLUME_VELOCITY_Small")
'--------------------------------------------------
' Parameter 1 : (String) "ROTATION_OVER_VOLUME_VELOCITY_Small"
' Returned value : (Variant) (Long) 1
'--------------------------------------------------

Dim bSTR1255
bSTR1255 = ""
Dim bSTR1256
bSTR1256 = ""
Dim boolean628
settingRepository1.GetAttrInfo "ROTATION_OVER_VOLUME_VELOCITY_Small", bSTR1255, bSTR1256, boolean628
'--------------------------------------------------
' Parameter 1 : (String) "ROTATION_OVER_VOLUME_VELOCITY_Small"
' Parameter 2 : (String) "Default value"
' Parameter 3 : (String) "Unlocked"
' Parameter 4 : (Boolean) False
'--------------------------------------------------

long629 = settingRepository1.GetAttr("ROTATION_OVER_VOLUME_VELOCITY_ExtraSmall")
'--------------------------------------------------
' Parameter 1 : (String) "ROTATION_OVER_VOLUME_VELOCITY_ExtraSmall"
' Returned value : (Variant) (Long) 1
'--------------------------------------------------

Dim bSTR1257
bSTR1257 = ""
Dim bSTR1258
bSTR1258 = ""
Dim boolean629
settingRepository1.GetAttrInfo "ROTATION_OVER_VOLUME_VELOCITY_ExtraSmall", bSTR1257, bSTR1258, boolean629
'--------------------------------------------------
' Parameter 1 : (String) "ROTATION_OVER_VOLUME_VELOCITY_ExtraSmall"
' Parameter 2 : (String) "Default value"
' Parameter 3 : (String) "Unlocked"
' Parameter 4 : (Boolean) False
'--------------------------------------------------

long630 = settingRepository1.GetAttr("ROTATION_OVER_VOLUME_VELOCITY_Nanometric")
'--------------------------------------------------
' Parameter 1 : (String) "ROTATION_OVER_VOLUME_VELOCITY_Nanometric"
' Returned value : (Variant) (Long) 1
'--------------------------------------------------

Dim bSTR1259
bSTR1259 = ""
Dim bSTR1260
bSTR1260 = ""
Dim boolean630
settingRepository1.GetAttrInfo "ROTATION_OVER_VOLUME_VELOCITY_Nanometric", bSTR1259, bSTR1260, boolean630
'--------------------------------------------------
' Parameter 1 : (String) "ROTATION_OVER_VOLUME_VELOCITY_Nanometric"
' Parameter 2 : (String) "Default value"
' Parameter 3 : (String) "Unlocked"
' Parameter 4 : (Boolean) False
'--------------------------------------------------

long631 = settingRepository1.GetAttr("PULSATION_OVER_VOLUME_VELOCITY")
'--------------------------------------------------
' Parameter 1 : (String) "PULSATION_OVER_VOLUME_VELOCITY"
' Returned value : (Variant) (Long) 1
'--------------------------------------------------

Dim bSTR1261
bSTR1261 = ""
Dim bSTR1262
bSTR1262 = ""
Dim boolean631
settingRepository1.GetAttrInfo "PULSATION_OVER_VOLUME_VELOCITY", bSTR1261, bSTR1262, boolean631
'--------------------------------------------------
' Parameter 1 : (String) "PULSATION_OVER_VOLUME_VELOCITY"
' Parameter 2 : (String) "Default value"
' Parameter 3 : (String) "Unlocked"
' Parameter 4 : (Boolean) False
'--------------------------------------------------

long632 = settingRepository1.GetAttr("PULSATION_OVER_VOLUME_VELOCITY_Large")
'--------------------------------------------------
' Parameter 1 : (String) "PULSATION_OVER_VOLUME_VELOCITY_Large"
' Returned value : (Variant) (Long) 1
'--------------------------------------------------

Dim bSTR1263
bSTR1263 = ""
Dim bSTR1264
bSTR1264 = ""
Dim boolean632
settingRepository1.GetAttrInfo "PULSATION_OVER_VOLUME_VELOCITY_Large", bSTR1263, bSTR1264, boolean632
'--------------------------------------------------
' Parameter 1 : (String) "PULSATION_OVER_VOLUME_VELOCITY_Large"
' Parameter 2 : (String) "Default value"
' Parameter 3 : (String) "Unlocked"
' Parameter 4 : (Boolean) False
'--------------------------------------------------

long633 = settingRepository1.GetAttr("PULSATION_OVER_VOLUME_VELOCITY_ExtraLarge")
'--------------------------------------------------
' Parameter 1 : (String) "PULSATION_OVER_VOLUME_VELOCITY_ExtraLarge"
' Returned value : (Variant) (Long) 1
'--------------------------------------------------

Dim bSTR1265
bSTR1265 = ""
Dim bSTR1266
bSTR1266 = ""
Dim boolean633
settingRepository1.GetAttrInfo "PULSATION_OVER_VOLUME_VELOCITY_ExtraLarge", bSTR1265, bSTR1266, boolean633
'--------------------------------------------------
' Parameter 1 : (String) "PULSATION_OVER_VOLUME_VELOCITY_ExtraLarge"
' Parameter 2 : (String) "Default value"
' Parameter 3 : (String) "Unlocked"
' Parameter 4 : (Boolean) False
'--------------------------------------------------

long634 = settingRepository1.GetAttr("PULSATION_OVER_VOLUME_VELOCITY_Small")
'--------------------------------------------------
' Parameter 1 : (String) "PULSATION_OVER_VOLUME_VELOCITY_Small"
' Returned value : (Variant) (Long) 1
'--------------------------------------------------

Dim bSTR1267
bSTR1267 = ""
Dim bSTR1268
bSTR1268 = ""
Dim boolean634
settingRepository1.GetAttrInfo "PULSATION_OVER_VOLUME_VELOCITY_Small", bSTR1267, bSTR1268, boolean634
'--------------------------------------------------
' Parameter 1 : (String) "PULSATION_OVER_VOLUME_VELOCITY_Small"
' Parameter 2 : (String) "Default value"
' Parameter 3 : (String) "Unlocked"
' Parameter 4 : (Boolean) False
'--------------------------------------------------

long635 = settingRepository1.GetAttr("PULSATION_OVER_VOLUME_VELOCITY_ExtraSmall")
'--------------------------------------------------
' Parameter 1 : (String) "PULSATION_OVER_VOLUME_VELOCITY_ExtraSmall"
' Returned value : (Variant) (Long) 1
'--------------------------------------------------

Dim bSTR1269
bSTR1269 = ""
Dim bSTR1270
bSTR1270 = ""
Dim boolean635
settingRepository1.GetAttrInfo "PULSATION_OVER_VOLUME_VELOCITY_ExtraSmall", bSTR1269, bSTR1270, boolean635
'--------------------------------------------------
' Parameter 1 : (String) "PULSATION_OVER_VOLUME_VELOCITY_ExtraSmall"
' Parameter 2 : (String) "Default value"
' Parameter 3 : (String) "Unlocked"
' Parameter 4 : (Boolean) False
'--------------------------------------------------

long636 = settingRepository1.GetAttr("PULSATION_OVER_VOLUME_VELOCITY_Nanometric")
'--------------------------------------------------
' Parameter 1 : (String) "PULSATION_OVER_VOLUME_VELOCITY_Nanometric"
' Returned value : (Variant) (Long) 1
'--------------------------------------------------

Dim bSTR1271
bSTR1271 = ""
Dim bSTR1272
bSTR1272 = ""
Dim boolean636
settingRepository1.GetAttrInfo "PULSATION_OVER_VOLUME_VELOCITY_Nanometric", bSTR1271, bSTR1272, boolean636
'--------------------------------------------------
' Parameter 1 : (String) "PULSATION_OVER_VOLUME_VELOCITY_Nanometric"
' Parameter 2 : (String) "Default value"
' Parameter 3 : (String) "Unlocked"
' Parameter 4 : (Boolean) False
'--------------------------------------------------

long637 = settingRepository1.GetAttr("ROTATIONAL_ACCELERATION_OVER_VOLUME_VELOCITY")
'--------------------------------------------------
' Parameter 1 : (String) "ROTATIONAL_ACCELERATION_OVER_VOLUME_VELOCITY"
' Returned value : (Variant) (Long) 1
'--------------------------------------------------

Dim bSTR1273
bSTR1273 = ""
Dim bSTR1274
bSTR1274 = ""
Dim boolean637
settingRepository1.GetAttrInfo "ROTATIONAL_ACCELERATION_OVER_VOLUME_VELOCITY", bSTR1273, bSTR1274, boolean637
'--------------------------------------------------
' Parameter 1 : (String) "ROTATIONAL_ACCELERATION_OVER_VOLUME_VELOCITY"
' Parameter 2 : (String) "Default value"
' Parameter 3 : (String) "Unlocked"
' Parameter 4 : (Boolean) False
'--------------------------------------------------

long638 = settingRepository1.GetAttr("ROTATIONAL_ACCELERATION_OVER_VOLUME_VELOCITY_Large")
'--------------------------------------------------
' Parameter 1 : (String) "ROTATIONAL_ACCELERATION_OVER_VOLUME_VELOCITY_Large"
' Returned value : (Variant) (Long) 1
'--------------------------------------------------

Dim bSTR1275
bSTR1275 = ""
Dim bSTR1276
bSTR1276 = ""
Dim boolean638
settingRepository1.GetAttrInfo "ROTATIONAL_ACCELERATION_OVER_VOLUME_VELOCITY_Large", bSTR1275, bSTR1276, boolean638
'--------------------------------------------------
' Parameter 1 : (String) "ROTATIONAL_ACCELERATION_OVER_VOLUME_VELOCITY_Large"
' Parameter 2 : (String) "Default value"
' Parameter 3 : (String) "Unlocked"
' Parameter 4 : (Boolean) False
'--------------------------------------------------

long639 = settingRepository1.GetAttr("ROTATIONAL_ACCELERATION_OVER_VOLUME_VELOCITY_ExtraLarge")
'--------------------------------------------------
' Parameter 1 : (String) "ROTATIONAL_ACCELERATION_OVER_VOLUME_VELOCITY_ExtraLarge"
' Returned value : (Variant) (Long) 1
'--------------------------------------------------

Dim bSTR1277
bSTR1277 = ""
Dim bSTR1278
bSTR1278 = ""
Dim boolean639
settingRepository1.GetAttrInfo "ROTATIONAL_ACCELERATION_OVER_VOLUME_VELOCITY_ExtraLarge", bSTR1277, bSTR1278, boolean639
'--------------------------------------------------
' Parameter 1 : (String) "ROTATIONAL_ACCELERATION_OVER_VOLUME_VELOCITY_ExtraLarge"
' Parameter 2 : (String) "Default value"
' Parameter 3 : (String) "Unlocked"
' Parameter 4 : (Boolean) False
'--------------------------------------------------

long640 = settingRepository1.GetAttr("ROTATIONAL_ACCELERATION_OVER_VOLUME_VELOCITY_Small")
'--------------------------------------------------
' Parameter 1 : (String) "ROTATIONAL_ACCELERATION_OVER_VOLUME_VELOCITY_Small"
' Returned value : (Variant) (Long) 1
'--------------------------------------------------

Dim bSTR1279
bSTR1279 = ""
Dim bSTR1280
bSTR1280 = ""
Dim boolean640
settingRepository1.GetAttrInfo "ROTATIONAL_ACCELERATION_OVER_VOLUME_VELOCITY_Small", bSTR1279, bSTR1280, boolean640
'--------------------------------------------------
' Parameter 1 : (String) "ROTATIONAL_ACCELERATION_OVER_VOLUME_VELOCITY_Small"
' Parameter 2 : (String) "Default value"
' Parameter 3 : (String) "Unlocked"
' Parameter 4 : (Boolean) False
'--------------------------------------------------

long641 = settingRepository1.GetAttr("ROTATIONAL_ACCELERATION_OVER_VOLUME_VELOCITY_ExtraSmall")
'--------------------------------------------------
' Parameter 1 : (String) "ROTATIONAL_ACCELERATION_OVER_VOLUME_VELOCITY_ExtraSmall"
' Returned value : (Variant) (Long) 1
'--------------------------------------------------

Dim bSTR1281
bSTR1281 = ""
Dim bSTR1282
bSTR1282 = ""
Dim boolean641
settingRepository1.GetAttrInfo "ROTATIONAL_ACCELERATION_OVER_VOLUME_VELOCITY_ExtraSmall", bSTR1281, bSTR1282, boolean641
'--------------------------------------------------
' Parameter 1 : (String) "ROTATIONAL_ACCELERATION_OVER_VOLUME_VELOCITY_ExtraSmall"
' Parameter 2 : (String) "Default value"
' Parameter 3 : (String) "Unlocked"
' Parameter 4 : (Boolean) False
'--------------------------------------------------

long642 = settingRepository1.GetAttr("ROTATIONAL_ACCELERATION_OVER_VOLUME_VELOCITY_Nanometric")
'--------------------------------------------------
' Parameter 1 : (String) "ROTATIONAL_ACCELERATION_OVER_VOLUME_VELOCITY_Nanometric"
' Returned value : (Variant) (Long) 1
'--------------------------------------------------

Dim bSTR1283
bSTR1283 = ""
Dim bSTR1284
bSTR1284 = ""
Dim boolean642
settingRepository1.GetAttrInfo "ROTATIONAL_ACCELERATION_OVER_VOLUME_VELOCITY_Nanometric", bSTR1283, bSTR1284, boolean642
'--------------------------------------------------
' Parameter 1 : (String) "ROTATIONAL_ACCELERATION_OVER_VOLUME_VELOCITY_Nanometric"
' Parameter 2 : (String) "Default value"
' Parameter 3 : (String) "Unlocked"
' Parameter 4 : (Boolean) False
'--------------------------------------------------

long643 = settingRepository1.GetAttr("FORCE_OVER_VOLUME_ACCELERATION")
'--------------------------------------------------
' Parameter 1 : (String) "FORCE_OVER_VOLUME_ACCELERATION"
' Returned value : (Variant) (Long) 1
'--------------------------------------------------

Dim bSTR1285
bSTR1285 = ""
Dim bSTR1286
bSTR1286 = ""
Dim boolean643
settingRepository1.GetAttrInfo "FORCE_OVER_VOLUME_ACCELERATION", bSTR1285, bSTR1286, boolean643
'--------------------------------------------------
' Parameter 1 : (String) "FORCE_OVER_VOLUME_ACCELERATION"
' Parameter 2 : (String) "Default value"
' Parameter 3 : (String) "Unlocked"
' Parameter 4 : (Boolean) False
'--------------------------------------------------

long644 = settingRepository1.GetAttr("FORCE_OVER_VOLUME_ACCELERATION_Large")
'--------------------------------------------------
' Parameter 1 : (String) "FORCE_OVER_VOLUME_ACCELERATION_Large"
' Returned value : (Variant) (Long) 1
'--------------------------------------------------

Dim bSTR1287
bSTR1287 = ""
Dim bSTR1288
bSTR1288 = ""
Dim boolean644
settingRepository1.GetAttrInfo "FORCE_OVER_VOLUME_ACCELERATION_Large", bSTR1287, bSTR1288, boolean644
'--------------------------------------------------
' Parameter 1 : (String) "FORCE_OVER_VOLUME_ACCELERATION_Large"
' Parameter 2 : (String) "Default value"
' Parameter 3 : (String) "Unlocked"
' Parameter 4 : (Boolean) False
'--------------------------------------------------

long645 = settingRepository1.GetAttr("FORCE_OVER_VOLUME_ACCELERATION_ExtraLarge")
'--------------------------------------------------
' Parameter 1 : (String) "FORCE_OVER_VOLUME_ACCELERATION_ExtraLarge"
' Returned value : (Variant) (Long) 1
'--------------------------------------------------

Dim bSTR1289
bSTR1289 = ""
Dim bSTR1290
bSTR1290 = ""
Dim boolean645
settingRepository1.GetAttrInfo "FORCE_OVER_VOLUME_ACCELERATION_ExtraLarge", bSTR1289, bSTR1290, boolean645
'--------------------------------------------------
' Parameter 1 : (String) "FORCE_OVER_VOLUME_ACCELERATION_ExtraLarge"
' Parameter 2 : (String) "Default value"
' Parameter 3 : (String) "Unlocked"
' Parameter 4 : (Boolean) False
'--------------------------------------------------

long646 = settingRepository1.GetAttr("FORCE_OVER_VOLUME_ACCELERATION_Small")
'--------------------------------------------------
' Parameter 1 : (String) "FORCE_OVER_VOLUME_ACCELERATION_Small"
' Returned value : (Variant) (Long) 1
'--------------------------------------------------

Dim bSTR1291
bSTR1291 = ""
Dim bSTR1292
bSTR1292 = ""
Dim boolean646
settingRepository1.GetAttrInfo "FORCE_OVER_VOLUME_ACCELERATION_Small", bSTR1291, bSTR1292, boolean646
'--------------------------------------------------
' Parameter 1 : (String) "FORCE_OVER_VOLUME_ACCELERATION_Small"
' Parameter 2 : (String) "Default value"
' Parameter 3 : (String) "Unlocked"
' Parameter 4 : (Boolean) False
'--------------------------------------------------

long647 = settingRepository1.GetAttr("FORCE_OVER_VOLUME_ACCELERATION_ExtraSmall")
'--------------------------------------------------
' Parameter 1 : (String) "FORCE_OVER_VOLUME_ACCELERATION_ExtraSmall"
' Returned value : (Variant) (Long) 1
'--------------------------------------------------

Dim bSTR1293
bSTR1293 = ""
Dim bSTR1294
bSTR1294 = ""
Dim boolean647
settingRepository1.GetAttrInfo "FORCE_OVER_VOLUME_ACCELERATION_ExtraSmall", bSTR1293, bSTR1294, boolean647
'--------------------------------------------------
' Parameter 1 : (String) "FORCE_OVER_VOLUME_ACCELERATION_ExtraSmall"
' Parameter 2 : (String) "Default value"
' Parameter 3 : (String) "Unlocked"
' Parameter 4 : (Boolean) False
'--------------------------------------------------

long648 = settingRepository1.GetAttr("FORCE_OVER_VOLUME_ACCELERATION_Nanometric")
'--------------------------------------------------
' Parameter 1 : (String) "FORCE_OVER_VOLUME_ACCELERATION_Nanometric"
' Returned value : (Variant) (Long) 1
'--------------------------------------------------

Dim bSTR1295
bSTR1295 = ""
Dim bSTR1296
bSTR1296 = ""
Dim boolean648
settingRepository1.GetAttrInfo "FORCE_OVER_VOLUME_ACCELERATION_Nanometric", bSTR1295, bSTR1296, boolean648
'--------------------------------------------------
' Parameter 1 : (String) "FORCE_OVER_VOLUME_ACCELERATION_Nanometric"
' Parameter 2 : (String) "Default value"
' Parameter 3 : (String) "Unlocked"
' Parameter 4 : (Boolean) False
'--------------------------------------------------

long649 = settingRepository1.GetAttr("MOMENT_OVER_VOLUME_ACCELERATION")
'--------------------------------------------------
' Parameter 1 : (String) "MOMENT_OVER_VOLUME_ACCELERATION"
' Returned value : (Variant) (Long) 1
'--------------------------------------------------

Dim bSTR1297
bSTR1297 = ""
Dim bSTR1298
bSTR1298 = ""
Dim boolean649
settingRepository1.GetAttrInfo "MOMENT_OVER_VOLUME_ACCELERATION", bSTR1297, bSTR1298, boolean649
'--------------------------------------------------
' Parameter 1 : (String) "MOMENT_OVER_VOLUME_ACCELERATION"
' Parameter 2 : (String) "Default value"
' Parameter 3 : (String) "Unlocked"
' Parameter 4 : (Boolean) False
'--------------------------------------------------

long650 = settingRepository1.GetAttr("MOMENT_OVER_VOLUME_ACCELERATION_Large")
'--------------------------------------------------
' Parameter 1 : (String) "MOMENT_OVER_VOLUME_ACCELERATION_Large"
' Returned value : (Variant) (Long) 1
'--------------------------------------------------

Dim bSTR1299
bSTR1299 = ""
Dim bSTR1300
bSTR1300 = ""
Dim boolean650
settingRepository1.GetAttrInfo "MOMENT_OVER_VOLUME_ACCELERATION_Large", bSTR1299, bSTR1300, boolean650
'--------------------------------------------------
' Parameter 1 : (String) "MOMENT_OVER_VOLUME_ACCELERATION_Large"
' Parameter 2 : (String) "Default value"
' Parameter 3 : (String) "Unlocked"
' Parameter 4 : (Boolean) False
'--------------------------------------------------

long651 = settingRepository1.GetAttr("MOMENT_OVER_VOLUME_ACCELERATION_ExtraLarge")
'--------------------------------------------------
' Parameter 1 : (String) "MOMENT_OVER_VOLUME_ACCELERATION_ExtraLarge"
' Returned value : (Variant) (Long) 1
'--------------------------------------------------

Dim bSTR1301
bSTR1301 = ""
Dim bSTR1302
bSTR1302 = ""
Dim boolean651
settingRepository1.GetAttrInfo "MOMENT_OVER_VOLUME_ACCELERATION_ExtraLarge", bSTR1301, bSTR1302, boolean651
'--------------------------------------------------
' Parameter 1 : (String) "MOMENT_OVER_VOLUME_ACCELERATION_ExtraLarge"
' Parameter 2 : (String) "Default value"
' Parameter 3 : (String) "Unlocked"
' Parameter 4 : (Boolean) False
'--------------------------------------------------

long652 = settingRepository1.GetAttr("MOMENT_OVER_VOLUME_ACCELERATION_Small")
'--------------------------------------------------
' Parameter 1 : (String) "MOMENT_OVER_VOLUME_ACCELERATION_Small"
' Returned value : (Variant) (Long) 1
'--------------------------------------------------

Dim bSTR1303
bSTR1303 = ""
Dim bSTR1304
bSTR1304 = ""
Dim boolean652
settingRepository1.GetAttrInfo "MOMENT_OVER_VOLUME_ACCELERATION_Small", bSTR1303, bSTR1304, boolean652
'--------------------------------------------------
' Parameter 1 : (String) "MOMENT_OVER_VOLUME_ACCELERATION_Small"
' Parameter 2 : (String) "Default value"
' Parameter 3 : (String) "Unlocked"
' Parameter 4 : (Boolean) False
'--------------------------------------------------

long653 = settingRepository1.GetAttr("MOMENT_OVER_VOLUME_ACCELERATION_ExtraSmall")
'--------------------------------------------------
' Parameter 1 : (String) "MOMENT_OVER_VOLUME_ACCELERATION_ExtraSmall"
' Returned value : (Variant) (Long) 1
'--------------------------------------------------

Dim bSTR1305
bSTR1305 = ""
Dim bSTR1306
bSTR1306 = ""
Dim boolean653
settingRepository1.GetAttrInfo "MOMENT_OVER_VOLUME_ACCELERATION_ExtraSmall", bSTR1305, bSTR1306, boolean653
'--------------------------------------------------
' Parameter 1 : (String) "MOMENT_OVER_VOLUME_ACCELERATION_ExtraSmall"
' Parameter 2 : (String) "Default value"
' Parameter 3 : (String) "Unlocked"
' Parameter 4 : (Boolean) False
'--------------------------------------------------

long654 = settingRepository1.GetAttr("MOMENT_OVER_VOLUME_ACCELERATION_Nanometric")
'--------------------------------------------------
' Parameter 1 : (String) "MOMENT_OVER_VOLUME_ACCELERATION_Nanometric"
' Returned value : (Variant) (Long) 1
'--------------------------------------------------

Dim bSTR1307
bSTR1307 = ""
Dim bSTR1308
bSTR1308 = ""
Dim boolean654
settingRepository1.GetAttrInfo "MOMENT_OVER_VOLUME_ACCELERATION_Nanometric", bSTR1307, bSTR1308, boolean654
'--------------------------------------------------
' Parameter 1 : (String) "MOMENT_OVER_VOLUME_ACCELERATION_Nanometric"
' Parameter 2 : (String) "Default value"
' Parameter 3 : (String) "Unlocked"
' Parameter 4 : (Boolean) False
'--------------------------------------------------

long655 = settingRepository1.GetAttr("DISPLACEMENT_OVER_VOLUME_ACCELERATION")
'--------------------------------------------------
' Parameter 1 : (String) "DISPLACEMENT_OVER_VOLUME_ACCELERATION"
' Returned value : (Variant) (Long) 1
'--------------------------------------------------

Dim bSTR1309
bSTR1309 = ""
Dim bSTR1310
bSTR1310 = ""
Dim boolean655
settingRepository1.GetAttrInfo "DISPLACEMENT_OVER_VOLUME_ACCELERATION", bSTR1309, bSTR1310, boolean655
'--------------------------------------------------
' Parameter 1 : (String) "DISPLACEMENT_OVER_VOLUME_ACCELERATION"
' Parameter 2 : (String) "Default value"
' Parameter 3 : (String) "Unlocked"
' Parameter 4 : (Boolean) False
'--------------------------------------------------

long656 = settingRepository1.GetAttr("DISPLACEMENT_OVER_VOLUME_ACCELERATION_Large")
'--------------------------------------------------
' Parameter 1 : (String) "DISPLACEMENT_OVER_VOLUME_ACCELERATION_Large"
' Returned value : (Variant) (Long) 1
'--------------------------------------------------

Dim bSTR1311
bSTR1311 = ""
Dim bSTR1312
bSTR1312 = ""
Dim boolean656
settingRepository1.GetAttrInfo "DISPLACEMENT_OVER_VOLUME_ACCELERATION_Large", bSTR1311, bSTR1312, boolean656
'--------------------------------------------------
' Parameter 1 : (String) "DISPLACEMENT_OVER_VOLUME_ACCELERATION_Large"
' Parameter 2 : (String) "Default value"
' Parameter 3 : (String) "Unlocked"
' Parameter 4 : (Boolean) False
'--------------------------------------------------

long657 = settingRepository1.GetAttr("DISPLACEMENT_OVER_VOLUME_ACCELERATION_ExtraLarge")
'--------------------------------------------------
' Parameter 1 : (String) "DISPLACEMENT_OVER_VOLUME_ACCELERATION_ExtraLarge"
' Returned value : (Variant) (Long) 1
'--------------------------------------------------

Dim bSTR1313
bSTR1313 = ""
Dim bSTR1314
bSTR1314 = ""
Dim boolean657
settingRepository1.GetAttrInfo "DISPLACEMENT_OVER_VOLUME_ACCELERATION_ExtraLarge", bSTR1313, bSTR1314, boolean657
'--------------------------------------------------
' Parameter 1 : (String) "DISPLACEMENT_OVER_VOLUME_ACCELERATION_ExtraLarge"
' Parameter 2 : (String) "Default value"
' Parameter 3 : (String) "Unlocked"
' Parameter 4 : (Boolean) False
'--------------------------------------------------

long658 = settingRepository1.GetAttr("DISPLACEMENT_OVER_VOLUME_ACCELERATION_Small")
'--------------------------------------------------
' Parameter 1 : (String) "DISPLACEMENT_OVER_VOLUME_ACCELERATION_Small"
' Returned value : (Variant) (Long) 1
'--------------------------------------------------

Dim bSTR1315
bSTR1315 = ""
Dim bSTR1316
bSTR1316 = ""
Dim boolean658
settingRepository1.GetAttrInfo "DISPLACEMENT_OVER_VOLUME_ACCELERATION_Small", bSTR1315, bSTR1316, boolean658
'--------------------------------------------------
' Parameter 1 : (String) "DISPLACEMENT_OVER_VOLUME_ACCELERATION_Small"
' Parameter 2 : (String) "Default value"
' Parameter 3 : (String) "Unlocked"
' Parameter 4 : (Boolean) False
'--------------------------------------------------

long659 = settingRepository1.GetAttr("DISPLACEMENT_OVER_VOLUME_ACCELERATION_ExtraSmall")
'--------------------------------------------------
' Parameter 1 : (String) "DISPLACEMENT_OVER_VOLUME_ACCELERATION_ExtraSmall"
' Returned value : (Variant) (Long) 1
'--------------------------------------------------

Dim bSTR1317
bSTR1317 = ""
Dim bSTR1318
bSTR1318 = ""
Dim boolean659
settingRepository1.GetAttrInfo "DISPLACEMENT_OVER_VOLUME_ACCELERATION_ExtraSmall", bSTR1317, bSTR1318, boolean659
'--------------------------------------------------
' Parameter 1 : (String) "DISPLACEMENT_OVER_VOLUME_ACCELERATION_ExtraSmall"
' Parameter 2 : (String) "Default value"
' Parameter 3 : (String) "Unlocked"
' Parameter 4 : (Boolean) False
'--------------------------------------------------

long660 = settingRepository1.GetAttr("DISPLACEMENT_OVER_VOLUME_ACCELERATION_Nanometric")
'--------------------------------------------------
' Parameter 1 : (String) "DISPLACEMENT_OVER_VOLUME_ACCELERATION_Nanometric"
' Returned value : (Variant) (Long) 1
'--------------------------------------------------

Dim bSTR1319
bSTR1319 = ""
Dim bSTR1320
bSTR1320 = ""
Dim boolean660
settingRepository1.GetAttrInfo "DISPLACEMENT_OVER_VOLUME_ACCELERATION_Nanometric", bSTR1319, bSTR1320, boolean660
'--------------------------------------------------
' Parameter 1 : (String) "DISPLACEMENT_OVER_VOLUME_ACCELERATION_Nanometric"
' Parameter 2 : (String) "Default value"
' Parameter 3 : (String) "Unlocked"
' Parameter 4 : (Boolean) False
'--------------------------------------------------

long661 = settingRepository1.GetAttr("VELOCITY_OVER_VOLUME_ACCELERATION")
'--------------------------------------------------
' Parameter 1 : (String) "VELOCITY_OVER_VOLUME_ACCELERATION"
' Returned value : (Variant) (Long) 1
'--------------------------------------------------

Dim bSTR1321
bSTR1321 = ""
Dim bSTR1322
bSTR1322 = ""
Dim boolean661
settingRepository1.GetAttrInfo "VELOCITY_OVER_VOLUME_ACCELERATION", bSTR1321, bSTR1322, boolean661
'--------------------------------------------------
' Parameter 1 : (String) "VELOCITY_OVER_VOLUME_ACCELERATION"
' Parameter 2 : (String) "Default value"
' Parameter 3 : (String) "Unlocked"
' Parameter 4 : (Boolean) False
'--------------------------------------------------

long662 = settingRepository1.GetAttr("VELOCITY_OVER_VOLUME_ACCELERATION_Large")
'--------------------------------------------------
' Parameter 1 : (String) "VELOCITY_OVER_VOLUME_ACCELERATION_Large"
' Returned value : (Variant) (Long) 1
'--------------------------------------------------

Dim bSTR1323
bSTR1323 = ""
Dim bSTR1324
bSTR1324 = ""
Dim boolean662
settingRepository1.GetAttrInfo "VELOCITY_OVER_VOLUME_ACCELERATION_Large", bSTR1323, bSTR1324, boolean662
'--------------------------------------------------
' Parameter 1 : (String) "VELOCITY_OVER_VOLUME_ACCELERATION_Large"
' Parameter 2 : (String) "Default value"
' Parameter 3 : (String) "Unlocked"
' Parameter 4 : (Boolean) False
'--------------------------------------------------

long663 = settingRepository1.GetAttr("VELOCITY_OVER_VOLUME_ACCELERATION_ExtraLarge")
'--------------------------------------------------
' Parameter 1 : (String) "VELOCITY_OVER_VOLUME_ACCELERATION_ExtraLarge"
' Returned value : (Variant) (Long) 1
'--------------------------------------------------

Dim bSTR1325
bSTR1325 = ""
Dim bSTR1326
bSTR1326 = ""
Dim boolean663
settingRepository1.GetAttrInfo "VELOCITY_OVER_VOLUME_ACCELERATION_ExtraLarge", bSTR1325, bSTR1326, boolean663
'--------------------------------------------------
' Parameter 1 : (String) "VELOCITY_OVER_VOLUME_ACCELERATION_ExtraLarge"
' Parameter 2 : (String) "Default value"
' Parameter 3 : (String) "Unlocked"
' Parameter 4 : (Boolean) False
'--------------------------------------------------

long664 = settingRepository1.GetAttr("VELOCITY_OVER_VOLUME_ACCELERATION_Small")
'--------------------------------------------------
' Parameter 1 : (String) "VELOCITY_OVER_VOLUME_ACCELERATION_Small"
' Returned value : (Variant) (Long) 1
'--------------------------------------------------

Dim bSTR1327
bSTR1327 = ""
Dim bSTR1328
bSTR1328 = ""
Dim boolean664
settingRepository1.GetAttrInfo "VELOCITY_OVER_VOLUME_ACCELERATION_Small", bSTR1327, bSTR1328, boolean664
'--------------------------------------------------
' Parameter 1 : (String) "VELOCITY_OVER_VOLUME_ACCELERATION_Small"
' Parameter 2 : (String) "Default value"
' Parameter 3 : (String) "Unlocked"
' Parameter 4 : (Boolean) False
'--------------------------------------------------

long665 = settingRepository1.GetAttr("VELOCITY_OVER_VOLUME_ACCELERATION_ExtraSmall")
'--------------------------------------------------
' Parameter 1 : (String) "VELOCITY_OVER_VOLUME_ACCELERATION_ExtraSmall"
' Returned value : (Variant) (Long) 1
'--------------------------------------------------

Dim bSTR1329
bSTR1329 = ""
Dim bSTR1330
bSTR1330 = ""
Dim boolean665
settingRepository1.GetAttrInfo "VELOCITY_OVER_VOLUME_ACCELERATION_ExtraSmall", bSTR1329, bSTR1330, boolean665
'--------------------------------------------------
' Parameter 1 : (String) "VELOCITY_OVER_VOLUME_ACCELERATION_ExtraSmall"
' Parameter 2 : (String) "Default value"
' Parameter 3 : (String) "Unlocked"
' Parameter 4 : (Boolean) False
'--------------------------------------------------

long666 = settingRepository1.GetAttr("VELOCITY_OVER_VOLUME_ACCELERATION_Nanometric")
'--------------------------------------------------
' Parameter 1 : (String) "VELOCITY_OVER_VOLUME_ACCELERATION_Nanometric"
' Returned value : (Variant) (Long) 1
'--------------------------------------------------

Dim bSTR1331
bSTR1331 = ""
Dim bSTR1332
bSTR1332 = ""
Dim boolean666
settingRepository1.GetAttrInfo "VELOCITY_OVER_VOLUME_ACCELERATION_Nanometric", bSTR1331, bSTR1332, boolean666
'--------------------------------------------------
' Parameter 1 : (String) "VELOCITY_OVER_VOLUME_ACCELERATION_Nanometric"
' Parameter 2 : (String) "Default value"
' Parameter 3 : (String) "Unlocked"
' Parameter 4 : (Boolean) False
'--------------------------------------------------

long667 = settingRepository1.GetAttr("ACCELERATION_OVER_VOLUME_ACCELERATION")
'--------------------------------------------------
' Parameter 1 : (String) "ACCELERATION_OVER_VOLUME_ACCELERATION"
' Returned value : (Variant) (Long) 1
'--------------------------------------------------

Dim bSTR1333
bSTR1333 = ""
Dim bSTR1334
bSTR1334 = ""
Dim boolean667
settingRepository1.GetAttrInfo "ACCELERATION_OVER_VOLUME_ACCELERATION", bSTR1333, bSTR1334, boolean667
'--------------------------------------------------
' Parameter 1 : (String) "ACCELERATION_OVER_VOLUME_ACCELERATION"
' Parameter 2 : (String) "Default value"
' Parameter 3 : (String) "Unlocked"
' Parameter 4 : (Boolean) False
'--------------------------------------------------

long668 = settingRepository1.GetAttr("ACCELERATION_OVER_VOLUME_ACCELERATION_Large")
'--------------------------------------------------
' Parameter 1 : (String) "ACCELERATION_OVER_VOLUME_ACCELERATION_Large"
' Returned value : (Variant) (Long) 1
'--------------------------------------------------

Dim bSTR1335
bSTR1335 = ""
Dim bSTR1336
bSTR1336 = ""
Dim boolean668
settingRepository1.GetAttrInfo "ACCELERATION_OVER_VOLUME_ACCELERATION_Large", bSTR1335, bSTR1336, boolean668
'--------------------------------------------------
' Parameter 1 : (String) "ACCELERATION_OVER_VOLUME_ACCELERATION_Large"
' Parameter 2 : (String) "Default value"
' Parameter 3 : (String) "Unlocked"
' Parameter 4 : (Boolean) False
'--------------------------------------------------

long669 = settingRepository1.GetAttr("ACCELERATION_OVER_VOLUME_ACCELERATION_ExtraLarge")
'--------------------------------------------------
' Parameter 1 : (String) "ACCELERATION_OVER_VOLUME_ACCELERATION_ExtraLarge"
' Returned value : (Variant) (Long) 1
'--------------------------------------------------

Dim bSTR1337
bSTR1337 = ""
Dim bSTR1338
bSTR1338 = ""
Dim boolean669
settingRepository1.GetAttrInfo "ACCELERATION_OVER_VOLUME_ACCELERATION_ExtraLarge", bSTR1337, bSTR1338, boolean669
'--------------------------------------------------
' Parameter 1 : (String) "ACCELERATION_OVER_VOLUME_ACCELERATION_ExtraLarge"
' Parameter 2 : (String) "Default value"
' Parameter 3 : (String) "Unlocked"
' Parameter 4 : (Boolean) False
'--------------------------------------------------

long670 = settingRepository1.GetAttr("ACCELERATION_OVER_VOLUME_ACCELERATION_Small")
'--------------------------------------------------
' Parameter 1 : (String) "ACCELERATION_OVER_VOLUME_ACCELERATION_Small"
' Returned value : (Variant) (Long) 1
'--------------------------------------------------

Dim bSTR1339
bSTR1339 = ""
Dim bSTR1340
bSTR1340 = ""
Dim boolean670
settingRepository1.GetAttrInfo "ACCELERATION_OVER_VOLUME_ACCELERATION_Small", bSTR1339, bSTR1340, boolean670
'--------------------------------------------------
' Parameter 1 : (String) "ACCELERATION_OVER_VOLUME_ACCELERATION_Small"
' Parameter 2 : (String) "Default value"
' Parameter 3 : (String) "Unlocked"
' Parameter 4 : (Boolean) False
'--------------------------------------------------

long671 = settingRepository1.GetAttr("ACCELERATION_OVER_VOLUME_ACCELERATION_ExtraSmall")
'--------------------------------------------------
' Parameter 1 : (String) "ACCELERATION_OVER_VOLUME_ACCELERATION_ExtraSmall"
' Returned value : (Variant) (Long) 1
'--------------------------------------------------

Dim bSTR1341
bSTR1341 = ""
Dim bSTR1342
bSTR1342 = ""
Dim boolean671
settingRepository1.GetAttrInfo "ACCELERATION_OVER_VOLUME_ACCELERATION_ExtraSmall", bSTR1341, bSTR1342, boolean671
'--------------------------------------------------
' Parameter 1 : (String) "ACCELERATION_OVER_VOLUME_ACCELERATION_ExtraSmall"
' Parameter 2 : (String) "Default value"
' Parameter 3 : (String) "Unlocked"
' Parameter 4 : (Boolean) False
'--------------------------------------------------

long672 = settingRepository1.GetAttr("ACCELERATION_OVER_VOLUME_ACCELERATION_Nanometric")
'--------------------------------------------------
' Parameter 1 : (String) "ACCELERATION_OVER_VOLUME_ACCELERATION_Nanometric"
' Returned value : (Variant) (Long) 1
'--------------------------------------------------

Dim bSTR1343
bSTR1343 = ""
Dim bSTR1344
bSTR1344 = ""
Dim boolean672
settingRepository1.GetAttrInfo "ACCELERATION_OVER_VOLUME_ACCELERATION_Nanometric", bSTR1343, bSTR1344, boolean672
'--------------------------------------------------
' Parameter 1 : (String) "ACCELERATION_OVER_VOLUME_ACCELERATION_Nanometric"
' Parameter 2 : (String) "Default value"
' Parameter 3 : (String) "Unlocked"
' Parameter 4 : (Boolean) False
'--------------------------------------------------

long673 = settingRepository1.GetAttr("ROTATION_OVER_VOLUME_ACCELERATION")
'--------------------------------------------------
' Parameter 1 : (String) "ROTATION_OVER_VOLUME_ACCELERATION"
' Returned value : (Variant) (Long) 1
'--------------------------------------------------

Dim bSTR1345
bSTR1345 = ""
Dim bSTR1346
bSTR1346 = ""
Dim boolean673
settingRepository1.GetAttrInfo "ROTATION_OVER_VOLUME_ACCELERATION", bSTR1345, bSTR1346, boolean673
'--------------------------------------------------
' Parameter 1 : (String) "ROTATION_OVER_VOLUME_ACCELERATION"
' Parameter 2 : (String) "Default value"
' Parameter 3 : (String) "Unlocked"
' Parameter 4 : (Boolean) False
'--------------------------------------------------

long674 = settingRepository1.GetAttr("ROTATION_OVER_VOLUME_ACCELERATION_Large")
'--------------------------------------------------
' Parameter 1 : (String) "ROTATION_OVER_VOLUME_ACCELERATION_Large"
' Returned value : (Variant) (Long) 1
'--------------------------------------------------

Dim bSTR1347
bSTR1347 = ""
Dim bSTR1348
bSTR1348 = ""
Dim boolean674
settingRepository1.GetAttrInfo "ROTATION_OVER_VOLUME_ACCELERATION_Large", bSTR1347, bSTR1348, boolean674
'--------------------------------------------------
' Parameter 1 : (String) "ROTATION_OVER_VOLUME_ACCELERATION_Large"
' Parameter 2 : (String) "Default value"
' Parameter 3 : (String) "Unlocked"
' Parameter 4 : (Boolean) False
'--------------------------------------------------

long675 = settingRepository1.GetAttr("ROTATION_OVER_VOLUME_ACCELERATION_ExtraLarge")
'--------------------------------------------------
' Parameter 1 : (String) "ROTATION_OVER_VOLUME_ACCELERATION_ExtraLarge"
' Returned value : (Variant) (Long) 1
'--------------------------------------------------

Dim bSTR1349
bSTR1349 = ""
Dim bSTR1350
bSTR1350 = ""
Dim boolean675
settingRepository1.GetAttrInfo "ROTATION_OVER_VOLUME_ACCELERATION_ExtraLarge", bSTR1349, bSTR1350, boolean675
'--------------------------------------------------
' Parameter 1 : (String) "ROTATION_OVER_VOLUME_ACCELERATION_ExtraLarge"
' Parameter 2 : (String) "Default value"
' Parameter 3 : (String) "Unlocked"
' Parameter 4 : (Boolean) False
'--------------------------------------------------

long676 = settingRepository1.GetAttr("ROTATION_OVER_VOLUME_ACCELERATION_Small")
'--------------------------------------------------
' Parameter 1 : (String) "ROTATION_OVER_VOLUME_ACCELERATION_Small"
' Returned value : (Variant) (Long) 1
'--------------------------------------------------

Dim bSTR1351
bSTR1351 = ""
Dim bSTR1352
bSTR1352 = ""
Dim boolean676
settingRepository1.GetAttrInfo "ROTATION_OVER_VOLUME_ACCELERATION_Small", bSTR1351, bSTR1352, boolean676
'--------------------------------------------------
' Parameter 1 : (String) "ROTATION_OVER_VOLUME_ACCELERATION_Small"
' Parameter 2 : (String) "Default value"
' Parameter 3 : (String) "Unlocked"
' Parameter 4 : (Boolean) False
'--------------------------------------------------

long677 = settingRepository1.GetAttr("ROTATION_OVER_VOLUME_ACCELERATION_ExtraSmall")
'--------------------------------------------------
' Parameter 1 : (String) "ROTATION_OVER_VOLUME_ACCELERATION_ExtraSmall"
' Returned value : (Variant) (Long) 1
'--------------------------------------------------

Dim bSTR1353
bSTR1353 = ""
Dim bSTR1354
bSTR1354 = ""
Dim boolean677
settingRepository1.GetAttrInfo "ROTATION_OVER_VOLUME_ACCELERATION_ExtraSmall", bSTR1353, bSTR1354, boolean677
'--------------------------------------------------
' Parameter 1 : (String) "ROTATION_OVER_VOLUME_ACCELERATION_ExtraSmall"
' Parameter 2 : (String) "Default value"
' Parameter 3 : (String) "Unlocked"
' Parameter 4 : (Boolean) False
'--------------------------------------------------

long678 = settingRepository1.GetAttr("ROTATION_OVER_VOLUME_ACCELERATION_Nanometric")
'--------------------------------------------------
' Parameter 1 : (String) "ROTATION_OVER_VOLUME_ACCELERATION_Nanometric"
' Returned value : (Variant) (Long) 1
'--------------------------------------------------

Dim bSTR1355
bSTR1355 = ""
Dim bSTR1356
bSTR1356 = ""
Dim boolean678
settingRepository1.GetAttrInfo "ROTATION_OVER_VOLUME_ACCELERATION_Nanometric", bSTR1355, bSTR1356, boolean678
'--------------------------------------------------
' Parameter 1 : (String) "ROTATION_OVER_VOLUME_ACCELERATION_Nanometric"
' Parameter 2 : (String) "Default value"
' Parameter 3 : (String) "Unlocked"
' Parameter 4 : (Boolean) False
'--------------------------------------------------

long679 = settingRepository1.GetAttr("PULSATION_OVER_VOLUME_ACCELERATION")
'--------------------------------------------------
' Parameter 1 : (String) "PULSATION_OVER_VOLUME_ACCELERATION"
' Returned value : (Variant) (Long) 1
'--------------------------------------------------

Dim bSTR1357
bSTR1357 = ""
Dim bSTR1358
bSTR1358 = ""
Dim boolean679
settingRepository1.GetAttrInfo "PULSATION_OVER_VOLUME_ACCELERATION", bSTR1357, bSTR1358, boolean679
'--------------------------------------------------
' Parameter 1 : (String) "PULSATION_OVER_VOLUME_ACCELERATION"
' Parameter 2 : (String) "Default value"
' Parameter 3 : (String) "Unlocked"
' Parameter 4 : (Boolean) False
'--------------------------------------------------

long680 = settingRepository1.GetAttr("PULSATION_OVER_VOLUME_ACCELERATION_Large")
'--------------------------------------------------
' Parameter 1 : (String) "PULSATION_OVER_VOLUME_ACCELERATION_Large"
' Returned value : (Variant) (Long) 1
'--------------------------------------------------

Dim bSTR1359
bSTR1359 = ""
Dim bSTR1360
bSTR1360 = ""
Dim boolean680
settingRepository1.GetAttrInfo "PULSATION_OVER_VOLUME_ACCELERATION_Large", bSTR1359, bSTR1360, boolean680
'--------------------------------------------------
' Parameter 1 : (String) "PULSATION_OVER_VOLUME_ACCELERATION_Large"
' Parameter 2 : (String) "Default value"
' Parameter 3 : (String) "Unlocked"
' Parameter 4 : (Boolean) False
'--------------------------------------------------

long681 = settingRepository1.GetAttr("PULSATION_OVER_VOLUME_ACCELERATION_ExtraLarge")
'--------------------------------------------------
' Parameter 1 : (String) "PULSATION_OVER_VOLUME_ACCELERATION_ExtraLarge"
' Returned value : (Variant) (Long) 1
'--------------------------------------------------

Dim bSTR1361
bSTR1361 = ""
Dim bSTR1362
bSTR1362 = ""
Dim boolean681
settingRepository1.GetAttrInfo "PULSATION_OVER_VOLUME_ACCELERATION_ExtraLarge", bSTR1361, bSTR1362, boolean681
'--------------------------------------------------
' Parameter 1 : (String) "PULSATION_OVER_VOLUME_ACCELERATION_ExtraLarge"
' Parameter 2 : (String) "Default value"
' Parameter 3 : (String) "Unlocked"
' Parameter 4 : (Boolean) False
'--------------------------------------------------

long682 = settingRepository1.GetAttr("PULSATION_OVER_VOLUME_ACCELERATION_Small")
'--------------------------------------------------
' Parameter 1 : (String) "PULSATION_OVER_VOLUME_ACCELERATION_Small"
' Returned value : (Variant) (Long) 1
'--------------------------------------------------

Dim bSTR1363
bSTR1363 = ""
Dim bSTR1364
bSTR1364 = ""
Dim boolean682
settingRepository1.GetAttrInfo "PULSATION_OVER_VOLUME_ACCELERATION_Small", bSTR1363, bSTR1364, boolean682
'--------------------------------------------------
' Parameter 1 : (String) "PULSATION_OVER_VOLUME_ACCELERATION_Small"
' Parameter 2 : (String) "Default value"
' Parameter 3 : (String) "Unlocked"
' Parameter 4 : (Boolean) False
'--------------------------------------------------

long683 = settingRepository1.GetAttr("PULSATION_OVER_VOLUME_ACCELERATION_ExtraSmall")
'--------------------------------------------------
' Parameter 1 : (String) "PULSATION_OVER_VOLUME_ACCELERATION_ExtraSmall"
' Returned value : (Variant) (Long) 1
'--------------------------------------------------

Dim bSTR1365
bSTR1365 = ""
Dim bSTR1366
bSTR1366 = ""
Dim boolean683
settingRepository1.GetAttrInfo "PULSATION_OVER_VOLUME_ACCELERATION_ExtraSmall", bSTR1365, bSTR1366, boolean683
'--------------------------------------------------
' Parameter 1 : (String) "PULSATION_OVER_VOLUME_ACCELERATION_ExtraSmall"
' Parameter 2 : (String) "Default value"
' Parameter 3 : (String) "Unlocked"
' Parameter 4 : (Boolean) False
'--------------------------------------------------

long684 = settingRepository1.GetAttr("PULSATION_OVER_VOLUME_ACCELERATION_Nanometric")
'--------------------------------------------------
' Parameter 1 : (String) "PULSATION_OVER_VOLUME_ACCELERATION_Nanometric"
' Returned value : (Variant) (Long) 1
'--------------------------------------------------

Dim bSTR1367
bSTR1367 = ""
Dim bSTR1368
bSTR1368 = ""
Dim boolean684
settingRepository1.GetAttrInfo "PULSATION_OVER_VOLUME_ACCELERATION_Nanometric", bSTR1367, bSTR1368, boolean684
'--------------------------------------------------
' Parameter 1 : (String) "PULSATION_OVER_VOLUME_ACCELERATION_Nanometric"
' Parameter 2 : (String) "Default value"
' Parameter 3 : (String) "Unlocked"
' Parameter 4 : (Boolean) False
'--------------------------------------------------

long685 = settingRepository1.GetAttr("ROTATIONAL_ACCELERATION_OVER_VOLUME_ACCELERATION")
'--------------------------------------------------
' Parameter 1 : (String) "ROTATIONAL_ACCELERATION_OVER_VOLUME_ACCELERATION"
' Returned value : (Variant) (Long) 1
'--------------------------------------------------

Dim bSTR1369
bSTR1369 = ""
Dim bSTR1370
bSTR1370 = ""
Dim boolean685
settingRepository1.GetAttrInfo "ROTATIONAL_ACCELERATION_OVER_VOLUME_ACCELERATION", bSTR1369, bSTR1370, boolean685
'--------------------------------------------------
' Parameter 1 : (String) "ROTATIONAL_ACCELERATION_OVER_VOLUME_ACCELERATION"
' Parameter 2 : (String) "Default value"
' Parameter 3 : (String) "Unlocked"
' Parameter 4 : (Boolean) False
'--------------------------------------------------

long686 = settingRepository1.GetAttr("ROTATIONAL_ACCELERATION_OVER_VOLUME_ACCELERATION_Large")
'--------------------------------------------------
' Parameter 1 : (String) "ROTATIONAL_ACCELERATION_OVER_VOLUME_ACCELERATION_Large"
' Returned value : (Variant) (Long) 1
'--------------------------------------------------

Dim bSTR1371
bSTR1371 = ""
Dim bSTR1372
bSTR1372 = ""
Dim boolean686
settingRepository1.GetAttrInfo "ROTATIONAL_ACCELERATION_OVER_VOLUME_ACCELERATION_Large", bSTR1371, bSTR1372, boolean686
'--------------------------------------------------
' Parameter 1 : (String) "ROTATIONAL_ACCELERATION_OVER_VOLUME_ACCELERATION_Large"
' Parameter 2 : (String) "Default value"
' Parameter 3 : (String) "Unlocked"
' Parameter 4 : (Boolean) False
'--------------------------------------------------

long687 = settingRepository1.GetAttr("ROTATIONAL_ACCELERATION_OVER_VOLUME_ACCELERATION_ExtraLarge")
'--------------------------------------------------
' Parameter 1 : (String) "ROTATIONAL_ACCELERATION_OVER_VOLUME_ACCELERATION_ExtraLarge"
' Returned value : (Variant) (Long) 1
'--------------------------------------------------

Dim bSTR1373
bSTR1373 = ""
Dim bSTR1374
bSTR1374 = ""
Dim boolean687
settingRepository1.GetAttrInfo "ROTATIONAL_ACCELERATION_OVER_VOLUME_ACCELERATION_ExtraLarge", bSTR1373, bSTR1374, boolean687
'--------------------------------------------------
' Parameter 1 : (String) "ROTATIONAL_ACCELERATION_OVER_VOLUME_ACCELERATION_ExtraLarge"
' Parameter 2 : (String) "Default value"
' Parameter 3 : (String) "Unlocked"
' Parameter 4 : (Boolean) False
'--------------------------------------------------

long688 = settingRepository1.GetAttr("ROTATIONAL_ACCELERATION_OVER_VOLUME_ACCELERATION_Small")
'--------------------------------------------------
' Parameter 1 : (String) "ROTATIONAL_ACCELERATION_OVER_VOLUME_ACCELERATION_Small"
' Returned value : (Variant) (Long) 1
'--------------------------------------------------

Dim bSTR1375
bSTR1375 = ""
Dim bSTR1376
bSTR1376 = ""
Dim boolean688
settingRepository1.GetAttrInfo "ROTATIONAL_ACCELERATION_OVER_VOLUME_ACCELERATION_Small", bSTR1375, bSTR1376, boolean688
'--------------------------------------------------
' Parameter 1 : (String) "ROTATIONAL_ACCELERATION_OVER_VOLUME_ACCELERATION_Small"
' Parameter 2 : (String) "Default value"
' Parameter 3 : (String) "Unlocked"
' Parameter 4 : (Boolean) False
'--------------------------------------------------

long689 = settingRepository1.GetAttr("ROTATIONAL_ACCELERATION_OVER_VOLUME_ACCELERATION_ExtraSmall")
'--------------------------------------------------
' Parameter 1 : (String) "ROTATIONAL_ACCELERATION_OVER_VOLUME_ACCELERATION_ExtraSmall"
' Returned value : (Variant) (Long) 1
'--------------------------------------------------

Dim bSTR1377
bSTR1377 = ""
Dim bSTR1378
bSTR1378 = ""
Dim boolean689
settingRepository1.GetAttrInfo "ROTATIONAL_ACCELERATION_OVER_VOLUME_ACCELERATION_ExtraSmall", bSTR1377, bSTR1378, boolean689
'--------------------------------------------------
' Parameter 1 : (String) "ROTATIONAL_ACCELERATION_OVER_VOLUME_ACCELERATION_ExtraSmall"
' Parameter 2 : (String) "Default value"
' Parameter 3 : (String) "Unlocked"
' Parameter 4 : (Boolean) False
'--------------------------------------------------

long690 = settingRepository1.GetAttr("ROTATIONAL_ACCELERATION_OVER_VOLUME_ACCELERATION_Nanometric")
'--------------------------------------------------
' Parameter 1 : (String) "ROTATIONAL_ACCELERATION_OVER_VOLUME_ACCELERATION_Nanometric"
' Returned value : (Variant) (Long) 1
'--------------------------------------------------

Dim bSTR1379
bSTR1379 = ""
Dim bSTR1380
bSTR1380 = ""
Dim boolean690
settingRepository1.GetAttrInfo "ROTATIONAL_ACCELERATION_OVER_VOLUME_ACCELERATION_Nanometric", bSTR1379, bSTR1380, boolean690
'--------------------------------------------------
' Parameter 1 : (String) "ROTATIONAL_ACCELERATION_OVER_VOLUME_ACCELERATION_Nanometric"
' Parameter 2 : (String) "Default value"
' Parameter 3 : (String) "Unlocked"
' Parameter 4 : (Boolean) False
'--------------------------------------------------

long691 = settingRepository1.GetAttr("JERK")
'--------------------------------------------------
' Parameter 1 : (String) "JERK"
' Returned value : (Variant) (Long) 1
'--------------------------------------------------

Dim bSTR1381
bSTR1381 = ""
Dim bSTR1382
bSTR1382 = ""
Dim boolean691
settingRepository1.GetAttrInfo "JERK", bSTR1381, bSTR1382, boolean691
'--------------------------------------------------
' Parameter 1 : (String) "JERK"
' Parameter 2 : (String) "Default value"
' Parameter 3 : (String) "Unlocked"
' Parameter 4 : (Boolean) False
'--------------------------------------------------

long692 = settingRepository1.GetAttr("JERK_Large")
'--------------------------------------------------
' Parameter 1 : (String) "JERK_Large"
' Returned value : (Variant) (Long) 1
'--------------------------------------------------

Dim bSTR1383
bSTR1383 = ""
Dim bSTR1384
bSTR1384 = ""
Dim boolean692
settingRepository1.GetAttrInfo "JERK_Large", bSTR1383, bSTR1384, boolean692
'--------------------------------------------------
' Parameter 1 : (String) "JERK_Large"
' Parameter 2 : (String) "Default value"
' Parameter 3 : (String) "Unlocked"
' Parameter 4 : (Boolean) False
'--------------------------------------------------

long693 = settingRepository1.GetAttr("JERK_ExtraLarge")
'--------------------------------------------------
' Parameter 1 : (String) "JERK_ExtraLarge"
' Returned value : (Variant) (Long) 1
'--------------------------------------------------

Dim bSTR1385
bSTR1385 = ""
Dim bSTR1386
bSTR1386 = ""
Dim boolean693
settingRepository1.GetAttrInfo "JERK_ExtraLarge", bSTR1385, bSTR1386, boolean693
'--------------------------------------------------
' Parameter 1 : (String) "JERK_ExtraLarge"
' Parameter 2 : (String) "Default value"
' Parameter 3 : (String) "Unlocked"
' Parameter 4 : (Boolean) False
'--------------------------------------------------

long694 = settingRepository1.GetAttr("JERK_Small")
'--------------------------------------------------
' Parameter 1 : (String) "JERK_Small"
' Returned value : (Variant) (Long) 1
'--------------------------------------------------

Dim bSTR1387
bSTR1387 = ""
Dim bSTR1388
bSTR1388 = ""
Dim boolean694
settingRepository1.GetAttrInfo "JERK_Small", bSTR1387, bSTR1388, boolean694
'--------------------------------------------------
' Parameter 1 : (String) "JERK_Small"
' Parameter 2 : (String) "Default value"
' Parameter 3 : (String) "Unlocked"
' Parameter 4 : (Boolean) False
'--------------------------------------------------

long695 = settingRepository1.GetAttr("JERK_ExtraSmall")
'--------------------------------------------------
' Parameter 1 : (String) "JERK_ExtraSmall"
' Returned value : (Variant) (Long) 1
'--------------------------------------------------

Dim bSTR1389
bSTR1389 = ""
Dim bSTR1390
bSTR1390 = ""
Dim boolean695
settingRepository1.GetAttrInfo "JERK_ExtraSmall", bSTR1389, bSTR1390, boolean695
'--------------------------------------------------
' Parameter 1 : (String) "JERK_ExtraSmall"
' Parameter 2 : (String) "Default value"
' Parameter 3 : (String) "Unlocked"
' Parameter 4 : (Boolean) False
'--------------------------------------------------

long696 = settingRepository1.GetAttr("JERK_Nanometric")
'--------------------------------------------------
' Parameter 1 : (String) "JERK_Nanometric"
' Returned value : (Variant) (Long) 1
'--------------------------------------------------

Dim bSTR1391
bSTR1391 = ""
Dim bSTR1392
bSTR1392 = ""
Dim boolean696
settingRepository1.GetAttrInfo "JERK_Nanometric", bSTR1391, bSTR1392, boolean696
'--------------------------------------------------
' Parameter 1 : (String) "JERK_Nanometric"
' Parameter 2 : (String) "Default value"
' Parameter 3 : (String) "Unlocked"
' Parameter 4 : (Boolean) False
'--------------------------------------------------

long697 = settingRepository1.GetAttr("ANGULARJERK")
'--------------------------------------------------
' Parameter 1 : (String) "ANGULARJERK"
' Returned value : (Variant) (Long) 1
'--------------------------------------------------

Dim bSTR1393
bSTR1393 = ""
Dim bSTR1394
bSTR1394 = ""
Dim boolean697
settingRepository1.GetAttrInfo "ANGULARJERK", bSTR1393, bSTR1394, boolean697
'--------------------------------------------------
' Parameter 1 : (String) "ANGULARJERK"
' Parameter 2 : (String) "Default value"
' Parameter 3 : (String) "Unlocked"
' Parameter 4 : (Boolean) False
'--------------------------------------------------

long698 = settingRepository1.GetAttr("ANGULARJERK_Large")
'--------------------------------------------------
' Parameter 1 : (String) "ANGULARJERK_Large"
' Returned value : (Variant) (Long) 1
'--------------------------------------------------

Dim bSTR1395
bSTR1395 = ""
Dim bSTR1396
bSTR1396 = ""
Dim boolean698
settingRepository1.GetAttrInfo "ANGULARJERK_Large", bSTR1395, bSTR1396, boolean698
'--------------------------------------------------
' Parameter 1 : (String) "ANGULARJERK_Large"
' Parameter 2 : (String) "Default value"
' Parameter 3 : (String) "Unlocked"
' Parameter 4 : (Boolean) False
'--------------------------------------------------

long699 = settingRepository1.GetAttr("ANGULARJERK_ExtraLarge")
'--------------------------------------------------
' Parameter 1 : (String) "ANGULARJERK_ExtraLarge"
' Returned value : (Variant) (Long) 1
'--------------------------------------------------

Dim bSTR1397
bSTR1397 = ""
Dim bSTR1398
bSTR1398 = ""
Dim boolean699
settingRepository1.GetAttrInfo "ANGULARJERK_ExtraLarge", bSTR1397, bSTR1398, boolean699
'--------------------------------------------------
' Parameter 1 : (String) "ANGULARJERK_ExtraLarge"
' Parameter 2 : (String) "Default value"
' Parameter 3 : (String) "Unlocked"
' Parameter 4 : (Boolean) False
'--------------------------------------------------

long700 = settingRepository1.GetAttr("ANGULARJERK_Small")
'--------------------------------------------------
' Parameter 1 : (String) "ANGULARJERK_Small"
' Returned value : (Variant) (Long) 1
'--------------------------------------------------

Dim bSTR1399
bSTR1399 = ""
Dim bSTR1400
bSTR1400 = ""
Dim boolean700
settingRepository1.GetAttrInfo "ANGULARJERK_Small", bSTR1399, bSTR1400, boolean700
'--------------------------------------------------
' Parameter 1 : (String) "ANGULARJERK_Small"
' Parameter 2 : (String) "Default value"
' Parameter 3 : (String) "Unlocked"
' Parameter 4 : (Boolean) False
'--------------------------------------------------

long701 = settingRepository1.GetAttr("ANGULARJERK_ExtraSmall")
'--------------------------------------------------
' Parameter 1 : (String) "ANGULARJERK_ExtraSmall"
' Returned value : (Variant) (Long) 1
'--------------------------------------------------

Dim bSTR1401
bSTR1401 = ""
Dim bSTR1402
bSTR1402 = ""
Dim boolean701
settingRepository1.GetAttrInfo "ANGULARJERK_ExtraSmall", bSTR1401, bSTR1402, boolean701
'--------------------------------------------------
' Parameter 1 : (String) "ANGULARJERK_ExtraSmall"
' Parameter 2 : (String) "Default value"
' Parameter 3 : (String) "Unlocked"
' Parameter 4 : (Boolean) False
'--------------------------------------------------

long702 = settingRepository1.GetAttr("ANGULARJERK_Nanometric")
'--------------------------------------------------
' Parameter 1 : (String) "ANGULARJERK_Nanometric"
' Returned value : (Variant) (Long) 1
'--------------------------------------------------

Dim bSTR1403
bSTR1403 = ""
Dim bSTR1404
bSTR1404 = ""
Dim boolean702
settingRepository1.GetAttrInfo "ANGULARJERK_Nanometric", bSTR1403, bSTR1404, boolean702
'--------------------------------------------------
' Parameter 1 : (String) "ANGULARJERK_Nanometric"
' Parameter 2 : (String) "Default value"
' Parameter 3 : (String) "Unlocked"
' Parameter 4 : (Boolean) False
'--------------------------------------------------

long703 = settingRepository1.GetAttr("MOMENTUM")
'--------------------------------------------------
' Parameter 1 : (String) "MOMENTUM"
' Returned value : (Variant) (Long) 1
'--------------------------------------------------

Dim bSTR1405
bSTR1405 = ""
Dim bSTR1406
bSTR1406 = ""
Dim boolean703
settingRepository1.GetAttrInfo "MOMENTUM", bSTR1405, bSTR1406, boolean703
'--------------------------------------------------
' Parameter 1 : (String) "MOMENTUM"
' Parameter 2 : (String) "Default value"
' Parameter 3 : (String) "Unlocked"
' Parameter 4 : (Boolean) False
'--------------------------------------------------

long704 = settingRepository1.GetAttr("MOMENTUM_Large")
'--------------------------------------------------
' Parameter 1 : (String) "MOMENTUM_Large"
' Returned value : (Variant) (Long) 1
'--------------------------------------------------

Dim bSTR1407
bSTR1407 = ""
Dim bSTR1408
bSTR1408 = ""
Dim boolean704
settingRepository1.GetAttrInfo "MOMENTUM_Large", bSTR1407, bSTR1408, boolean704
'--------------------------------------------------
' Parameter 1 : (String) "MOMENTUM_Large"
' Parameter 2 : (String) "Default value"
' Parameter 3 : (String) "Unlocked"
' Parameter 4 : (Boolean) False
'--------------------------------------------------

long705 = settingRepository1.GetAttr("MOMENTUM_ExtraLarge")
'--------------------------------------------------
' Parameter 1 : (String) "MOMENTUM_ExtraLarge"
' Returned value : (Variant) (Long) 1
'--------------------------------------------------

Dim bSTR1409
bSTR1409 = ""
Dim bSTR1410
bSTR1410 = ""
Dim boolean705
settingRepository1.GetAttrInfo "MOMENTUM_ExtraLarge", bSTR1409, bSTR1410, boolean705
'--------------------------------------------------
' Parameter 1 : (String) "MOMENTUM_ExtraLarge"
' Parameter 2 : (String) "Default value"
' Parameter 3 : (String) "Unlocked"
' Parameter 4 : (Boolean) False
'--------------------------------------------------

long706 = settingRepository1.GetAttr("MOMENTUM_Small")
'--------------------------------------------------
' Parameter 1 : (String) "MOMENTUM_Small"
' Returned value : (Variant) (Long) 1
'--------------------------------------------------

Dim bSTR1411
bSTR1411 = ""
Dim bSTR1412
bSTR1412 = ""
Dim boolean706
settingRepository1.GetAttrInfo "MOMENTUM_Small", bSTR1411, bSTR1412, boolean706
'--------------------------------------------------
' Parameter 1 : (String) "MOMENTUM_Small"
' Parameter 2 : (String) "Default value"
' Parameter 3 : (String) "Unlocked"
' Parameter 4 : (Boolean) False
'--------------------------------------------------

long707 = settingRepository1.GetAttr("MOMENTUM_ExtraSmall")
'--------------------------------------------------
' Parameter 1 : (String) "MOMENTUM_ExtraSmall"
' Returned value : (Variant) (Long) 1
'--------------------------------------------------

Dim bSTR1413
bSTR1413 = ""
Dim bSTR1414
bSTR1414 = ""
Dim boolean707
settingRepository1.GetAttrInfo "MOMENTUM_ExtraSmall", bSTR1413, bSTR1414, boolean707
'--------------------------------------------------
' Parameter 1 : (String) "MOMENTUM_ExtraSmall"
' Parameter 2 : (String) "Default value"
' Parameter 3 : (String) "Unlocked"
' Parameter 4 : (Boolean) False
'--------------------------------------------------

long708 = settingRepository1.GetAttr("MOMENTUM_Nanometric")
'--------------------------------------------------
' Parameter 1 : (String) "MOMENTUM_Nanometric"
' Returned value : (Variant) (Long) 1
'--------------------------------------------------

Dim bSTR1415
bSTR1415 = ""
Dim bSTR1416
bSTR1416 = ""
Dim boolean708
settingRepository1.GetAttrInfo "MOMENTUM_Nanometric", bSTR1415, bSTR1416, boolean708
'--------------------------------------------------
' Parameter 1 : (String) "MOMENTUM_Nanometric"
' Parameter 2 : (String) "Default value"
' Parameter 3 : (String) "Unlocked"
' Parameter 4 : (Boolean) False
'--------------------------------------------------

long709 = settingRepository1.GetAttr("HERTZSQUARE")
'--------------------------------------------------
' Parameter 1 : (String) "HERTZSQUARE"
' Returned value : (Variant) (Long) 1
'--------------------------------------------------

Dim bSTR1417
bSTR1417 = ""
Dim bSTR1418
bSTR1418 = ""
Dim boolean709
settingRepository1.GetAttrInfo "HERTZSQUARE", bSTR1417, bSTR1418, boolean709
'--------------------------------------------------
' Parameter 1 : (String) "HERTZSQUARE"
' Parameter 2 : (String) "Default value"
' Parameter 3 : (String) "Unlocked"
' Parameter 4 : (Boolean) False
'--------------------------------------------------

long710 = settingRepository1.GetAttr("HERTZSQUARE_Large")
'--------------------------------------------------
' Parameter 1 : (String) "HERTZSQUARE_Large"
' Returned value : (Variant) (Long) 1
'--------------------------------------------------

Dim bSTR1419
bSTR1419 = ""
Dim bSTR1420
bSTR1420 = ""
Dim boolean710
settingRepository1.GetAttrInfo "HERTZSQUARE_Large", bSTR1419, bSTR1420, boolean710
'--------------------------------------------------
' Parameter 1 : (String) "HERTZSQUARE_Large"
' Parameter 2 : (String) "Default value"
' Parameter 3 : (String) "Unlocked"
' Parameter 4 : (Boolean) False
'--------------------------------------------------

long711 = settingRepository1.GetAttr("HERTZSQUARE_ExtraLarge")
'--------------------------------------------------
' Parameter 1 : (String) "HERTZSQUARE_ExtraLarge"
' Returned value : (Variant) (Long) 1
'--------------------------------------------------

Dim bSTR1421
bSTR1421 = ""
Dim bSTR1422
bSTR1422 = ""
Dim boolean711
settingRepository1.GetAttrInfo "HERTZSQUARE_ExtraLarge", bSTR1421, bSTR1422, boolean711
'--------------------------------------------------
' Parameter 1 : (String) "HERTZSQUARE_ExtraLarge"
' Parameter 2 : (String) "Default value"
' Parameter 3 : (String) "Unlocked"
' Parameter 4 : (Boolean) False
'--------------------------------------------------

long712 = settingRepository1.GetAttr("HERTZSQUARE_Small")
'--------------------------------------------------
' Parameter 1 : (String) "HERTZSQUARE_Small"
' Returned value : (Variant) (Long) 1
'--------------------------------------------------

Dim bSTR1423
bSTR1423 = ""
Dim bSTR1424
bSTR1424 = ""
Dim boolean712
settingRepository1.GetAttrInfo "HERTZSQUARE_Small", bSTR1423, bSTR1424, boolean712
'--------------------------------------------------
' Parameter 1 : (String) "HERTZSQUARE_Small"
' Parameter 2 : (String) "Default value"
' Parameter 3 : (String) "Unlocked"
' Parameter 4 : (Boolean) False
'--------------------------------------------------

long713 = settingRepository1.GetAttr("HERTZSQUARE_ExtraSmall")
'--------------------------------------------------
' Parameter 1 : (String) "HERTZSQUARE_ExtraSmall"
' Returned value : (Variant) (Long) 1
'--------------------------------------------------

Dim bSTR1425
bSTR1425 = ""
Dim bSTR1426
bSTR1426 = ""
Dim boolean713
settingRepository1.GetAttrInfo "HERTZSQUARE_ExtraSmall", bSTR1425, bSTR1426, boolean713
'--------------------------------------------------
' Parameter 1 : (String) "HERTZSQUARE_ExtraSmall"
' Parameter 2 : (String) "Default value"
' Parameter 3 : (String) "Unlocked"
' Parameter 4 : (Boolean) False
'--------------------------------------------------

long714 = settingRepository1.GetAttr("HERTZSQUARE_Nanometric")
'--------------------------------------------------
' Parameter 1 : (String) "HERTZSQUARE_Nanometric"
' Returned value : (Variant) (Long) 1
'--------------------------------------------------

Dim bSTR1427
bSTR1427 = ""
Dim bSTR1428
bSTR1428 = ""
Dim boolean714
settingRepository1.GetAttrInfo "HERTZSQUARE_Nanometric", bSTR1427, bSTR1428, boolean714
'--------------------------------------------------
' Parameter 1 : (String) "HERTZSQUARE_Nanometric"
' Parameter 2 : (String) "Default value"
' Parameter 3 : (String) "Unlocked"
' Parameter 4 : (Boolean) False
'--------------------------------------------------

long715 = settingRepository1.GetAttr("HERTZCUBE")
'--------------------------------------------------
' Parameter 1 : (String) "HERTZCUBE"
' Returned value : (Variant) (Long) 1
'--------------------------------------------------

Dim bSTR1429
bSTR1429 = ""
Dim bSTR1430
bSTR1430 = ""
Dim boolean715
settingRepository1.GetAttrInfo "HERTZCUBE", bSTR1429, bSTR1430, boolean715
'--------------------------------------------------
' Parameter 1 : (String) "HERTZCUBE"
' Parameter 2 : (String) "Default value"
' Parameter 3 : (String) "Unlocked"
' Parameter 4 : (Boolean) False
'--------------------------------------------------

long716 = settingRepository1.GetAttr("HERTZCUBE_Large")
'--------------------------------------------------
' Parameter 1 : (String) "HERTZCUBE_Large"
' Returned value : (Variant) (Long) 1
'--------------------------------------------------

Dim bSTR1431
bSTR1431 = ""
Dim bSTR1432
bSTR1432 = ""
Dim boolean716
settingRepository1.GetAttrInfo "HERTZCUBE_Large", bSTR1431, bSTR1432, boolean716
'--------------------------------------------------
' Parameter 1 : (String) "HERTZCUBE_Large"
' Parameter 2 : (String) "Default value"
' Parameter 3 : (String) "Unlocked"
' Parameter 4 : (Boolean) False
'--------------------------------------------------

long717 = settingRepository1.GetAttr("HERTZCUBE_ExtraLarge")
'--------------------------------------------------
' Parameter 1 : (String) "HERTZCUBE_ExtraLarge"
' Returned value : (Variant) (Long) 1
'--------------------------------------------------

Dim bSTR1433
bSTR1433 = ""
Dim bSTR1434
bSTR1434 = ""
Dim boolean717
settingRepository1.GetAttrInfo "HERTZCUBE_ExtraLarge", bSTR1433, bSTR1434, boolean717
'--------------------------------------------------
' Parameter 1 : (String) "HERTZCUBE_ExtraLarge"
' Parameter 2 : (String) "Default value"
' Parameter 3 : (String) "Unlocked"
' Parameter 4 : (Boolean) False
'--------------------------------------------------

long718 = settingRepository1.GetAttr("HERTZCUBE_Small")
'--------------------------------------------------
' Parameter 1 : (String) "HERTZCUBE_Small"
' Returned value : (Variant) (Long) 1
'--------------------------------------------------

Dim bSTR1435
bSTR1435 = ""
Dim bSTR1436
bSTR1436 = ""
Dim boolean718
settingRepository1.GetAttrInfo "HERTZCUBE_Small", bSTR1435, bSTR1436, boolean718
'--------------------------------------------------
' Parameter 1 : (String) "HERTZCUBE_Small"
' Parameter 2 : (String) "Default value"
' Parameter 3 : (String) "Unlocked"
' Parameter 4 : (Boolean) False
'--------------------------------------------------

long719 = settingRepository1.GetAttr("HERTZCUBE_ExtraSmall")
'--------------------------------------------------
' Parameter 1 : (String) "HERTZCUBE_ExtraSmall"
' Returned value : (Variant) (Long) 1
'--------------------------------------------------

Dim bSTR1437
bSTR1437 = ""
Dim bSTR1438
bSTR1438 = ""
Dim boolean719
settingRepository1.GetAttrInfo "HERTZCUBE_ExtraSmall", bSTR1437, bSTR1438, boolean719
'--------------------------------------------------
' Parameter 1 : (String) "HERTZCUBE_ExtraSmall"
' Parameter 2 : (String) "Default value"
' Parameter 3 : (String) "Unlocked"
' Parameter 4 : (Boolean) False
'--------------------------------------------------

long720 = settingRepository1.GetAttr("HERTZCUBE_Nanometric")
'--------------------------------------------------
' Parameter 1 : (String) "HERTZCUBE_Nanometric"
' Returned value : (Variant) (Long) 1
'--------------------------------------------------

Dim bSTR1439
bSTR1439 = ""
Dim bSTR1440
bSTR1440 = ""
Dim boolean720
settingRepository1.GetAttrInfo "HERTZCUBE_Nanometric", bSTR1439, bSTR1440, boolean720
'--------------------------------------------------
' Parameter 1 : (String) "HERTZCUBE_Nanometric"
' Parameter 2 : (String) "Default value"
' Parameter 3 : (String) "Unlocked"
' Parameter 4 : (Boolean) False
'--------------------------------------------------

long721 = settingRepository1.GetAttr("PER_ANGLE")
'--------------------------------------------------
' Parameter 1 : (String) "PER_ANGLE"
' Returned value : (Variant) (Long) 1
'--------------------------------------------------

Dim bSTR1441
bSTR1441 = ""
Dim bSTR1442
bSTR1442 = ""
Dim boolean721
settingRepository1.GetAttrInfo "PER_ANGLE", bSTR1441, bSTR1442, boolean721
'--------------------------------------------------
' Parameter 1 : (String) "PER_ANGLE"
' Parameter 2 : (String) "Default value"
' Parameter 3 : (String) "Unlocked"
' Parameter 4 : (Boolean) False
'--------------------------------------------------

long722 = settingRepository1.GetAttr("PER_ANGLE_Large")
'--------------------------------------------------
' Parameter 1 : (String) "PER_ANGLE_Large"
' Returned value : (Variant) (Long) 1
'--------------------------------------------------

Dim bSTR1443
bSTR1443 = ""
Dim bSTR1444
bSTR1444 = ""
Dim boolean722
settingRepository1.GetAttrInfo "PER_ANGLE_Large", bSTR1443, bSTR1444, boolean722
'--------------------------------------------------
' Parameter 1 : (String) "PER_ANGLE_Large"
' Parameter 2 : (String) "Default value"
' Parameter 3 : (String) "Unlocked"
' Parameter 4 : (Boolean) False
'--------------------------------------------------

long723 = settingRepository1.GetAttr("PER_ANGLE_ExtraLarge")
'--------------------------------------------------
' Parameter 1 : (String) "PER_ANGLE_ExtraLarge"
' Returned value : (Variant) (Long) 1
'--------------------------------------------------

Dim bSTR1445
bSTR1445 = ""
Dim bSTR1446
bSTR1446 = ""
Dim boolean723
settingRepository1.GetAttrInfo "PER_ANGLE_ExtraLarge", bSTR1445, bSTR1446, boolean723
'--------------------------------------------------
' Parameter 1 : (String) "PER_ANGLE_ExtraLarge"
' Parameter 2 : (String) "Default value"
' Parameter 3 : (String) "Unlocked"
' Parameter 4 : (Boolean) False
'--------------------------------------------------

long724 = settingRepository1.GetAttr("PER_ANGLE_Small")
'--------------------------------------------------
' Parameter 1 : (String) "PER_ANGLE_Small"
' Returned value : (Variant) (Long) 1
'--------------------------------------------------

Dim bSTR1447
bSTR1447 = ""
Dim bSTR1448
bSTR1448 = ""
Dim boolean724
settingRepository1.GetAttrInfo "PER_ANGLE_Small", bSTR1447, bSTR1448, boolean724
'--------------------------------------------------
' Parameter 1 : (String) "PER_ANGLE_Small"
' Parameter 2 : (String) "Default value"
' Parameter 3 : (String) "Unlocked"
' Parameter 4 : (Boolean) False
'--------------------------------------------------

long725 = settingRepository1.GetAttr("PER_ANGLE_ExtraSmall")
'--------------------------------------------------
' Parameter 1 : (String) "PER_ANGLE_ExtraSmall"
' Returned value : (Variant) (Long) 1
'--------------------------------------------------

Dim bSTR1449
bSTR1449 = ""
Dim bSTR1450
bSTR1450 = ""
Dim boolean725
settingRepository1.GetAttrInfo "PER_ANGLE_ExtraSmall", bSTR1449, bSTR1450, boolean725
'--------------------------------------------------
' Parameter 1 : (String) "PER_ANGLE_ExtraSmall"
' Parameter 2 : (String) "Default value"
' Parameter 3 : (String) "Unlocked"
' Parameter 4 : (Boolean) False
'--------------------------------------------------

long726 = settingRepository1.GetAttr("PER_ANGLE_Nanometric")
'--------------------------------------------------
' Parameter 1 : (String) "PER_ANGLE_Nanometric"
' Returned value : (Variant) (Long) 1
'--------------------------------------------------

Dim bSTR1451
bSTR1451 = ""
Dim bSTR1452
bSTR1452 = ""
Dim boolean726
settingRepository1.GetAttrInfo "PER_ANGLE_Nanometric", bSTR1451, bSTR1452, boolean726
'--------------------------------------------------
' Parameter 1 : (String) "PER_ANGLE_Nanometric"
' Parameter 2 : (String) "Default value"
' Parameter 3 : (String) "Unlocked"
' Parameter 4 : (Boolean) False
'--------------------------------------------------

long727 = settingRepository1.GetAttr("PER_ANGLE_SQUARE")
'--------------------------------------------------
' Parameter 1 : (String) "PER_ANGLE_SQUARE"
' Returned value : (Variant) (Long) 1
'--------------------------------------------------

Dim bSTR1453
bSTR1453 = ""
Dim bSTR1454
bSTR1454 = ""
Dim boolean727
settingRepository1.GetAttrInfo "PER_ANGLE_SQUARE", bSTR1453, bSTR1454, boolean727
'--------------------------------------------------
' Parameter 1 : (String) "PER_ANGLE_SQUARE"
' Parameter 2 : (String) "Default value"
' Parameter 3 : (String) "Unlocked"
' Parameter 4 : (Boolean) False
'--------------------------------------------------

long728 = settingRepository1.GetAttr("PER_ANGLE_SQUARE_Large")
'--------------------------------------------------
' Parameter 1 : (String) "PER_ANGLE_SQUARE_Large"
' Returned value : (Variant) (Long) 1
'--------------------------------------------------

Dim bSTR1455
bSTR1455 = ""
Dim bSTR1456
bSTR1456 = ""
Dim boolean728
settingRepository1.GetAttrInfo "PER_ANGLE_SQUARE_Large", bSTR1455, bSTR1456, boolean728
'--------------------------------------------------
' Parameter 1 : (String) "PER_ANGLE_SQUARE_Large"
' Parameter 2 : (String) "Default value"
' Parameter 3 : (String) "Unlocked"
' Parameter 4 : (Boolean) False
'--------------------------------------------------

long729 = settingRepository1.GetAttr("PER_ANGLE_SQUARE_ExtraLarge")
'--------------------------------------------------
' Parameter 1 : (String) "PER_ANGLE_SQUARE_ExtraLarge"
' Returned value : (Variant) (Long) 1
'--------------------------------------------------

Dim bSTR1457
bSTR1457 = ""
Dim bSTR1458
bSTR1458 = ""
Dim boolean729
settingRepository1.GetAttrInfo "PER_ANGLE_SQUARE_ExtraLarge", bSTR1457, bSTR1458, boolean729
'--------------------------------------------------
' Parameter 1 : (String) "PER_ANGLE_SQUARE_ExtraLarge"
' Parameter 2 : (String) "Default value"
' Parameter 3 : (String) "Unlocked"
' Parameter 4 : (Boolean) False
'--------------------------------------------------

long730 = settingRepository1.GetAttr("PER_ANGLE_SQUARE_Small")
'--------------------------------------------------
' Parameter 1 : (String) "PER_ANGLE_SQUARE_Small"
' Returned value : (Variant) (Long) 1
'--------------------------------------------------

Dim bSTR1459
bSTR1459 = ""
Dim bSTR1460
bSTR1460 = ""
Dim boolean730
settingRepository1.GetAttrInfo "PER_ANGLE_SQUARE_Small", bSTR1459, bSTR1460, boolean730
'--------------------------------------------------
' Parameter 1 : (String) "PER_ANGLE_SQUARE_Small"
' Parameter 2 : (String) "Default value"
' Parameter 3 : (String) "Unlocked"
' Parameter 4 : (Boolean) False
'--------------------------------------------------

long731 = settingRepository1.GetAttr("PER_ANGLE_SQUARE_ExtraSmall")
'--------------------------------------------------
' Parameter 1 : (String) "PER_ANGLE_SQUARE_ExtraSmall"
' Returned value : (Variant) (Long) 1
'--------------------------------------------------

Dim bSTR1461
bSTR1461 = ""
Dim bSTR1462
bSTR1462 = ""
Dim boolean731
settingRepository1.GetAttrInfo "PER_ANGLE_SQUARE_ExtraSmall", bSTR1461, bSTR1462, boolean731
'--------------------------------------------------
' Parameter 1 : (String) "PER_ANGLE_SQUARE_ExtraSmall"
' Parameter 2 : (String) "Default value"
' Parameter 3 : (String) "Unlocked"
' Parameter 4 : (Boolean) False
'--------------------------------------------------

long732 = settingRepository1.GetAttr("PER_ANGLE_SQUARE_Nanometric")
'--------------------------------------------------
' Parameter 1 : (String) "PER_ANGLE_SQUARE_Nanometric"
' Returned value : (Variant) (Long) 1
'--------------------------------------------------

Dim bSTR1463
bSTR1463 = ""
Dim bSTR1464
bSTR1464 = ""
Dim boolean732
settingRepository1.GetAttrInfo "PER_ANGLE_SQUARE_Nanometric", bSTR1463, bSTR1464, boolean732
'--------------------------------------------------
' Parameter 1 : (String) "PER_ANGLE_SQUARE_Nanometric"
' Parameter 2 : (String) "Default value"
' Parameter 3 : (String) "Unlocked"
' Parameter 4 : (Boolean) False
'--------------------------------------------------

long733 = settingRepository1.GetAttr("ACOUSTIC_MONOPOLE_AMPLITUDE")
'--------------------------------------------------
' Parameter 1 : (String) "ACOUSTIC_MONOPOLE_AMPLITUDE"
' Returned value : (Variant) (Long) 1
'--------------------------------------------------

Dim bSTR1465
bSTR1465 = ""
Dim bSTR1466
bSTR1466 = ""
Dim boolean733
settingRepository1.GetAttrInfo "ACOUSTIC_MONOPOLE_AMPLITUDE", bSTR1465, bSTR1466, boolean733
'--------------------------------------------------
' Parameter 1 : (String) "ACOUSTIC_MONOPOLE_AMPLITUDE"
' Parameter 2 : (String) "Default value"
' Parameter 3 : (String) "Unlocked"
' Parameter 4 : (Boolean) False
'--------------------------------------------------

long734 = settingRepository1.GetAttr("ACOUSTIC_MONOPOLE_AMPLITUDE_Large")
'--------------------------------------------------
' Parameter 1 : (String) "ACOUSTIC_MONOPOLE_AMPLITUDE_Large"
' Returned value : (Variant) (Long) 1
'--------------------------------------------------

Dim bSTR1467
bSTR1467 = ""
Dim bSTR1468
bSTR1468 = ""
Dim boolean734
settingRepository1.GetAttrInfo "ACOUSTIC_MONOPOLE_AMPLITUDE_Large", bSTR1467, bSTR1468, boolean734
'--------------------------------------------------
' Parameter 1 : (String) "ACOUSTIC_MONOPOLE_AMPLITUDE_Large"
' Parameter 2 : (String) "Default value"
' Parameter 3 : (String) "Unlocked"
' Parameter 4 : (Boolean) False
'--------------------------------------------------

long735 = settingRepository1.GetAttr("ACOUSTIC_MONOPOLE_AMPLITUDE_ExtraLarge")
'--------------------------------------------------
' Parameter 1 : (String) "ACOUSTIC_MONOPOLE_AMPLITUDE_ExtraLarge"
' Returned value : (Variant) (Long) 1
'--------------------------------------------------

Dim bSTR1469
bSTR1469 = ""
Dim bSTR1470
bSTR1470 = ""
Dim boolean735
settingRepository1.GetAttrInfo "ACOUSTIC_MONOPOLE_AMPLITUDE_ExtraLarge", bSTR1469, bSTR1470, boolean735
'--------------------------------------------------
' Parameter 1 : (String) "ACOUSTIC_MONOPOLE_AMPLITUDE_ExtraLarge"
' Parameter 2 : (String) "Default value"
' Parameter 3 : (String) "Unlocked"
' Parameter 4 : (Boolean) False
'--------------------------------------------------

long736 = settingRepository1.GetAttr("ACOUSTIC_MONOPOLE_AMPLITUDE_Small")
'--------------------------------------------------
' Parameter 1 : (String) "ACOUSTIC_MONOPOLE_AMPLITUDE_Small"
' Returned value : (Variant) (Long) 1
'--------------------------------------------------

Dim bSTR1471
bSTR1471 = ""
Dim bSTR1472
bSTR1472 = ""
Dim boolean736
settingRepository1.GetAttrInfo "ACOUSTIC_MONOPOLE_AMPLITUDE_Small", bSTR1471, bSTR1472, boolean736
'--------------------------------------------------
' Parameter 1 : (String) "ACOUSTIC_MONOPOLE_AMPLITUDE_Small"
' Parameter 2 : (String) "Default value"
' Parameter 3 : (String) "Unlocked"
' Parameter 4 : (Boolean) False
'--------------------------------------------------

long737 = settingRepository1.GetAttr("ACOUSTIC_MONOPOLE_AMPLITUDE_ExtraSmall")
'--------------------------------------------------
' Parameter 1 : (String) "ACOUSTIC_MONOPOLE_AMPLITUDE_ExtraSmall"
' Returned value : (Variant) (Long) 1
'--------------------------------------------------

Dim bSTR1473
bSTR1473 = ""
Dim bSTR1474
bSTR1474 = ""
Dim boolean737
settingRepository1.GetAttrInfo "ACOUSTIC_MONOPOLE_AMPLITUDE_ExtraSmall", bSTR1473, bSTR1474, boolean737
'--------------------------------------------------
' Parameter 1 : (String) "ACOUSTIC_MONOPOLE_AMPLITUDE_ExtraSmall"
' Parameter 2 : (String) "Default value"
' Parameter 3 : (String) "Unlocked"
' Parameter 4 : (Boolean) False
'--------------------------------------------------

long738 = settingRepository1.GetAttr("ACOUSTIC_MONOPOLE_AMPLITUDE_Nanometric")
'--------------------------------------------------
' Parameter 1 : (String) "ACOUSTIC_MONOPOLE_AMPLITUDE_Nanometric"
' Returned value : (Variant) (Long) 1
'--------------------------------------------------

Dim bSTR1475
bSTR1475 = ""
Dim bSTR1476
bSTR1476 = ""
Dim boolean738
settingRepository1.GetAttrInfo "ACOUSTIC_MONOPOLE_AMPLITUDE_Nanometric", bSTR1475, bSTR1476, boolean738
'--------------------------------------------------
' Parameter 1 : (String) "ACOUSTIC_MONOPOLE_AMPLITUDE_Nanometric"
' Parameter 2 : (String) "Default value"
' Parameter 3 : (String) "Unlocked"
' Parameter 4 : (Boolean) False
'--------------------------------------------------

long739 = settingRepository1.GetAttr("ACOUSTIC_DIPOLE_AMPLITUDE")
'--------------------------------------------------
' Parameter 1 : (String) "ACOUSTIC_DIPOLE_AMPLITUDE"
' Returned value : (Variant) (Long) 1
'--------------------------------------------------

Dim bSTR1477
bSTR1477 = ""
Dim bSTR1478
bSTR1478 = ""
Dim boolean739
settingRepository1.GetAttrInfo "ACOUSTIC_DIPOLE_AMPLITUDE", bSTR1477, bSTR1478, boolean739
'--------------------------------------------------
' Parameter 1 : (String) "ACOUSTIC_DIPOLE_AMPLITUDE"
' Parameter 2 : (String) "Default value"
' Parameter 3 : (String) "Unlocked"
' Parameter 4 : (Boolean) False
'--------------------------------------------------

long740 = settingRepository1.GetAttr("ACOUSTIC_DIPOLE_AMPLITUDE_Large")
'--------------------------------------------------
' Parameter 1 : (String) "ACOUSTIC_DIPOLE_AMPLITUDE_Large"
' Returned value : (Variant) (Long) 1
'--------------------------------------------------

Dim bSTR1479
bSTR1479 = ""
Dim bSTR1480
bSTR1480 = ""
Dim boolean740
settingRepository1.GetAttrInfo "ACOUSTIC_DIPOLE_AMPLITUDE_Large", bSTR1479, bSTR1480, boolean740
'--------------------------------------------------
' Parameter 1 : (String) "ACOUSTIC_DIPOLE_AMPLITUDE_Large"
' Parameter 2 : (String) "Default value"
' Parameter 3 : (String) "Unlocked"
' Parameter 4 : (Boolean) False
'--------------------------------------------------

long741 = settingRepository1.GetAttr("ACOUSTIC_DIPOLE_AMPLITUDE_ExtraLarge")
'--------------------------------------------------
' Parameter 1 : (String) "ACOUSTIC_DIPOLE_AMPLITUDE_ExtraLarge"
' Returned value : (Variant) (Long) 1
'--------------------------------------------------

Dim bSTR1481
bSTR1481 = ""
Dim bSTR1482
bSTR1482 = ""
Dim boolean741
settingRepository1.GetAttrInfo "ACOUSTIC_DIPOLE_AMPLITUDE_ExtraLarge", bSTR1481, bSTR1482, boolean741
'--------------------------------------------------
' Parameter 1 : (String) "ACOUSTIC_DIPOLE_AMPLITUDE_ExtraLarge"
' Parameter 2 : (String) "Default value"
' Parameter 3 : (String) "Unlocked"
' Parameter 4 : (Boolean) False
'--------------------------------------------------

long742 = settingRepository1.GetAttr("ACOUSTIC_DIPOLE_AMPLITUDE_Small")
'--------------------------------------------------
' Parameter 1 : (String) "ACOUSTIC_DIPOLE_AMPLITUDE_Small"
' Returned value : (Variant) (Long) 1
'--------------------------------------------------

Dim bSTR1483
bSTR1483 = ""
Dim bSTR1484
bSTR1484 = ""
Dim boolean742
settingRepository1.GetAttrInfo "ACOUSTIC_DIPOLE_AMPLITUDE_Small", bSTR1483, bSTR1484, boolean742
'--------------------------------------------------
' Parameter 1 : (String) "ACOUSTIC_DIPOLE_AMPLITUDE_Small"
' Parameter 2 : (String) "Default value"
' Parameter 3 : (String) "Unlocked"
' Parameter 4 : (Boolean) False
'--------------------------------------------------

long743 = settingRepository1.GetAttr("ACOUSTIC_DIPOLE_AMPLITUDE_ExtraSmall")
'--------------------------------------------------
' Parameter 1 : (String) "ACOUSTIC_DIPOLE_AMPLITUDE_ExtraSmall"
' Returned value : (Variant) (Long) 1
'--------------------------------------------------

Dim bSTR1485
bSTR1485 = ""
Dim bSTR1486
bSTR1486 = ""
Dim boolean743
settingRepository1.GetAttrInfo "ACOUSTIC_DIPOLE_AMPLITUDE_ExtraSmall", bSTR1485, bSTR1486, boolean743
'--------------------------------------------------
' Parameter 1 : (String) "ACOUSTIC_DIPOLE_AMPLITUDE_ExtraSmall"
' Parameter 2 : (String) "Default value"
' Parameter 3 : (String) "Unlocked"
' Parameter 4 : (Boolean) False
'--------------------------------------------------

long744 = settingRepository1.GetAttr("ACOUSTIC_DIPOLE_AMPLITUDE_Nanometric")
'--------------------------------------------------
' Parameter 1 : (String) "ACOUSTIC_DIPOLE_AMPLITUDE_Nanometric"
' Returned value : (Variant) (Long) 1
'--------------------------------------------------

Dim bSTR1487
bSTR1487 = ""
Dim bSTR1488
bSTR1488 = ""
Dim boolean744
settingRepository1.GetAttrInfo "ACOUSTIC_DIPOLE_AMPLITUDE_Nanometric", bSTR1487, bSTR1488, boolean744
'--------------------------------------------------
' Parameter 1 : (String) "ACOUSTIC_DIPOLE_AMPLITUDE_Nanometric"
' Parameter 2 : (String) "Default value"
' Parameter 3 : (String) "Unlocked"
' Parameter 4 : (Boolean) False
'--------------------------------------------------

long745 = settingRepository1.GetAttr("ACOUSTIC_QUADRUPOLE_AMPLITUDE")
'--------------------------------------------------
' Parameter 1 : (String) "ACOUSTIC_QUADRUPOLE_AMPLITUDE"
' Returned value : (Variant) (Long) 1
'--------------------------------------------------

Dim bSTR1489
bSTR1489 = ""
Dim bSTR1490
bSTR1490 = ""
Dim boolean745
settingRepository1.GetAttrInfo "ACOUSTIC_QUADRUPOLE_AMPLITUDE", bSTR1489, bSTR1490, boolean745
'--------------------------------------------------
' Parameter 1 : (String) "ACOUSTIC_QUADRUPOLE_AMPLITUDE"
' Parameter 2 : (String) "Default value"
' Parameter 3 : (String) "Unlocked"
' Parameter 4 : (Boolean) False
'--------------------------------------------------

long746 = settingRepository1.GetAttr("ACOUSTIC_QUADRUPOLE_AMPLITUDE_Large")
'--------------------------------------------------
' Parameter 1 : (String) "ACOUSTIC_QUADRUPOLE_AMPLITUDE_Large"
' Returned value : (Variant) (Long) 1
'--------------------------------------------------

Dim bSTR1491
bSTR1491 = ""
Dim bSTR1492
bSTR1492 = ""
Dim boolean746
settingRepository1.GetAttrInfo "ACOUSTIC_QUADRUPOLE_AMPLITUDE_Large", bSTR1491, bSTR1492, boolean746
'--------------------------------------------------
' Parameter 1 : (String) "ACOUSTIC_QUADRUPOLE_AMPLITUDE_Large"
' Parameter 2 : (String) "Default value"
' Parameter 3 : (String) "Unlocked"
' Parameter 4 : (Boolean) False
'--------------------------------------------------

long747 = settingRepository1.GetAttr("ACOUSTIC_QUADRUPOLE_AMPLITUDE_ExtraLarge")
'--------------------------------------------------
' Parameter 1 : (String) "ACOUSTIC_QUADRUPOLE_AMPLITUDE_ExtraLarge"
' Returned value : (Variant) (Long) 1
'--------------------------------------------------

Dim bSTR1493
bSTR1493 = ""
Dim bSTR1494
bSTR1494 = ""
Dim boolean747
settingRepository1.GetAttrInfo "ACOUSTIC_QUADRUPOLE_AMPLITUDE_ExtraLarge", bSTR1493, bSTR1494, boolean747
'--------------------------------------------------
' Parameter 1 : (String) "ACOUSTIC_QUADRUPOLE_AMPLITUDE_ExtraLarge"
' Parameter 2 : (String) "Default value"
' Parameter 3 : (String) "Unlocked"
' Parameter 4 : (Boolean) False
'--------------------------------------------------

long748 = settingRepository1.GetAttr("ACOUSTIC_QUADRUPOLE_AMPLITUDE_Small")
'--------------------------------------------------
' Parameter 1 : (String) "ACOUSTIC_QUADRUPOLE_AMPLITUDE_Small"
' Returned value : (Variant) (Long) 1
'--------------------------------------------------

Dim bSTR1495
bSTR1495 = ""
Dim bSTR1496
bSTR1496 = ""
Dim boolean748
settingRepository1.GetAttrInfo "ACOUSTIC_QUADRUPOLE_AMPLITUDE_Small", bSTR1495, bSTR1496, boolean748
'--------------------------------------------------
' Parameter 1 : (String) "ACOUSTIC_QUADRUPOLE_AMPLITUDE_Small"
' Parameter 2 : (String) "Default value"
' Parameter 3 : (String) "Unlocked"
' Parameter 4 : (Boolean) False
'--------------------------------------------------

long749 = settingRepository1.GetAttr("ACOUSTIC_QUADRUPOLE_AMPLITUDE_ExtraSmall")
'--------------------------------------------------
' Parameter 1 : (String) "ACOUSTIC_QUADRUPOLE_AMPLITUDE_ExtraSmall"
' Returned value : (Variant) (Long) 1
'--------------------------------------------------

Dim bSTR1497
bSTR1497 = ""
Dim bSTR1498
bSTR1498 = ""
Dim boolean749
settingRepository1.GetAttrInfo "ACOUSTIC_QUADRUPOLE_AMPLITUDE_ExtraSmall", bSTR1497, bSTR1498, boolean749
'--------------------------------------------------
' Parameter 1 : (String) "ACOUSTIC_QUADRUPOLE_AMPLITUDE_ExtraSmall"
' Parameter 2 : (String) "Default value"
' Parameter 3 : (String) "Unlocked"
' Parameter 4 : (Boolean) False
'--------------------------------------------------

long750 = settingRepository1.GetAttr("ACOUSTIC_QUADRUPOLE_AMPLITUDE_Nanometric")
'--------------------------------------------------
' Parameter 1 : (String) "ACOUSTIC_QUADRUPOLE_AMPLITUDE_Nanometric"
' Returned value : (Variant) (Long) 1
'--------------------------------------------------

Dim bSTR1499
bSTR1499 = ""
Dim bSTR1500
bSTR1500 = ""
Dim boolean750
settingRepository1.GetAttrInfo "ACOUSTIC_QUADRUPOLE_AMPLITUDE_Nanometric", bSTR1499, bSTR1500, boolean750
'--------------------------------------------------
' Parameter 1 : (String) "ACOUSTIC_QUADRUPOLE_AMPLITUDE_Nanometric"
' Parameter 2 : (String) "Default value"
' Parameter 3 : (String) "Unlocked"
' Parameter 4 : (Boolean) False
'--------------------------------------------------

long751 = settingRepository1.GetAttr("VOLUME_ACCELERATION")
'--------------------------------------------------
' Parameter 1 : (String) "VOLUME_ACCELERATION"
' Returned value : (Variant) (Long) 1
'--------------------------------------------------

Dim bSTR1501
bSTR1501 = ""
Dim bSTR1502
bSTR1502 = ""
Dim boolean751
settingRepository1.GetAttrInfo "VOLUME_ACCELERATION", bSTR1501, bSTR1502, boolean751
'--------------------------------------------------
' Parameter 1 : (String) "VOLUME_ACCELERATION"
' Parameter 2 : (String) "Default value"
' Parameter 3 : (String) "Unlocked"
' Parameter 4 : (Boolean) False
'--------------------------------------------------

long752 = settingRepository1.GetAttr("VOLUME_ACCELERATION_Large")
'--------------------------------------------------
' Parameter 1 : (String) "VOLUME_ACCELERATION_Large"
' Returned value : (Variant) (Long) 1
'--------------------------------------------------

Dim bSTR1503
bSTR1503 = ""
Dim bSTR1504
bSTR1504 = ""
Dim boolean752
settingRepository1.GetAttrInfo "VOLUME_ACCELERATION_Large", bSTR1503, bSTR1504, boolean752
'--------------------------------------------------
' Parameter 1 : (String) "VOLUME_ACCELERATION_Large"
' Parameter 2 : (String) "Default value"
' Parameter 3 : (String) "Unlocked"
' Parameter 4 : (Boolean) False
'--------------------------------------------------

long753 = settingRepository1.GetAttr("VOLUME_ACCELERATION_ExtraLarge")
'--------------------------------------------------
' Parameter 1 : (String) "VOLUME_ACCELERATION_ExtraLarge"
' Returned value : (Variant) (Long) 1
'--------------------------------------------------

Dim bSTR1505
bSTR1505 = ""
Dim bSTR1506
bSTR1506 = ""
Dim boolean753
settingRepository1.GetAttrInfo "VOLUME_ACCELERATION_ExtraLarge", bSTR1505, bSTR1506, boolean753
'--------------------------------------------------
' Parameter 1 : (String) "VOLUME_ACCELERATION_ExtraLarge"
' Parameter 2 : (String) "Default value"
' Parameter 3 : (String) "Unlocked"
' Parameter 4 : (Boolean) False
'--------------------------------------------------

long754 = settingRepository1.GetAttr("VOLUME_ACCELERATION_Small")
'--------------------------------------------------
' Parameter 1 : (String) "VOLUME_ACCELERATION_Small"
' Returned value : (Variant) (Long) 1
'--------------------------------------------------

Dim bSTR1507
bSTR1507 = ""
Dim bSTR1508
bSTR1508 = ""
Dim boolean754
settingRepository1.GetAttrInfo "VOLUME_ACCELERATION_Small", bSTR1507, bSTR1508, boolean754
'--------------------------------------------------
' Parameter 1 : (String) "VOLUME_ACCELERATION_Small"
' Parameter 2 : (String) "Default value"
' Parameter 3 : (String) "Unlocked"
' Parameter 4 : (Boolean) False
'--------------------------------------------------

long755 = settingRepository1.GetAttr("VOLUME_ACCELERATION_ExtraSmall")
'--------------------------------------------------
' Parameter 1 : (String) "VOLUME_ACCELERATION_ExtraSmall"
' Returned value : (Variant) (Long) 1
'--------------------------------------------------

Dim bSTR1509
bSTR1509 = ""
Dim bSTR1510
bSTR1510 = ""
Dim boolean755
settingRepository1.GetAttrInfo "VOLUME_ACCELERATION_ExtraSmall", bSTR1509, bSTR1510, boolean755
'--------------------------------------------------
' Parameter 1 : (String) "VOLUME_ACCELERATION_ExtraSmall"
' Parameter 2 : (String) "Default value"
' Parameter 3 : (String) "Unlocked"
' Parameter 4 : (Boolean) False
'--------------------------------------------------

long756 = settingRepository1.GetAttr("VOLUME_ACCELERATION_Nanometric")
'--------------------------------------------------
' Parameter 1 : (String) "VOLUME_ACCELERATION_Nanometric"
' Returned value : (Variant) (Long) 1
'--------------------------------------------------

Dim bSTR1511
bSTR1511 = ""
Dim bSTR1512
bSTR1512 = ""
Dim boolean756
settingRepository1.GetAttrInfo "VOLUME_ACCELERATION_Nanometric", bSTR1511, bSTR1512, boolean756
'--------------------------------------------------
' Parameter 1 : (String) "VOLUME_ACCELERATION_Nanometric"
' Parameter 2 : (String) "Default value"
' Parameter 3 : (String) "Unlocked"
' Parameter 4 : (Boolean) False
'--------------------------------------------------

long757 = settingRepository1.GetAttr("INTENSITY")
'--------------------------------------------------
' Parameter 1 : (String) "INTENSITY"
' Returned value : (Variant) (Long) 1
'--------------------------------------------------

Dim bSTR1513
bSTR1513 = ""
Dim bSTR1514
bSTR1514 = ""
Dim boolean757
settingRepository1.GetAttrInfo "INTENSITY", bSTR1513, bSTR1514, boolean757
'--------------------------------------------------
' Parameter 1 : (String) "INTENSITY"
' Parameter 2 : (String) "Default value"
' Parameter 3 : (String) "Unlocked"
' Parameter 4 : (Boolean) False
'--------------------------------------------------

long758 = settingRepository1.GetAttr("INTENSITY_Large")
'--------------------------------------------------
' Parameter 1 : (String) "INTENSITY_Large"
' Returned value : (Variant) (Long) 1
'--------------------------------------------------

Dim bSTR1515
bSTR1515 = ""
Dim bSTR1516
bSTR1516 = ""
Dim boolean758
settingRepository1.GetAttrInfo "INTENSITY_Large", bSTR1515, bSTR1516, boolean758
'--------------------------------------------------
' Parameter 1 : (String) "INTENSITY_Large"
' Parameter 2 : (String) "Default value"
' Parameter 3 : (String) "Unlocked"
' Parameter 4 : (Boolean) False
'--------------------------------------------------

long759 = settingRepository1.GetAttr("INTENSITY_ExtraLarge")
'--------------------------------------------------
' Parameter 1 : (String) "INTENSITY_ExtraLarge"
' Returned value : (Variant) (Long) 1
'--------------------------------------------------

Dim bSTR1517
bSTR1517 = ""
Dim bSTR1518
bSTR1518 = ""
Dim boolean759
settingRepository1.GetAttrInfo "INTENSITY_ExtraLarge", bSTR1517, bSTR1518, boolean759
'--------------------------------------------------
' Parameter 1 : (String) "INTENSITY_ExtraLarge"
' Parameter 2 : (String) "Default value"
' Parameter 3 : (String) "Unlocked"
' Parameter 4 : (Boolean) False
'--------------------------------------------------

long760 = settingRepository1.GetAttr("INTENSITY_Small")
'--------------------------------------------------
' Parameter 1 : (String) "INTENSITY_Small"
' Returned value : (Variant) (Long) 1
'--------------------------------------------------

Dim bSTR1519
bSTR1519 = ""
Dim bSTR1520
bSTR1520 = ""
Dim boolean760
settingRepository1.GetAttrInfo "INTENSITY_Small", bSTR1519, bSTR1520, boolean760
'--------------------------------------------------
' Parameter 1 : (String) "INTENSITY_Small"
' Parameter 2 : (String) "Default value"
' Parameter 3 : (String) "Unlocked"
' Parameter 4 : (Boolean) False
'--------------------------------------------------

long761 = settingRepository1.GetAttr("INTENSITY_ExtraSmall")
'--------------------------------------------------
' Parameter 1 : (String) "INTENSITY_ExtraSmall"
' Returned value : (Variant) (Long) 1
'--------------------------------------------------

Dim bSTR1521
bSTR1521 = ""
Dim bSTR1522
bSTR1522 = ""
Dim boolean761
settingRepository1.GetAttrInfo "INTENSITY_ExtraSmall", bSTR1521, bSTR1522, boolean761
'--------------------------------------------------
' Parameter 1 : (String) "INTENSITY_ExtraSmall"
' Parameter 2 : (String) "Default value"
' Parameter 3 : (String) "Unlocked"
' Parameter 4 : (Boolean) False
'--------------------------------------------------

long762 = settingRepository1.GetAttr("INTENSITY_Nanometric")
'--------------------------------------------------
' Parameter 1 : (String) "INTENSITY_Nanometric"
' Returned value : (Variant) (Long) 1
'--------------------------------------------------

Dim bSTR1523
bSTR1523 = ""
Dim bSTR1524
bSTR1524 = ""
Dim boolean762
settingRepository1.GetAttrInfo "INTENSITY_Nanometric", bSTR1523, bSTR1524, boolean762
'--------------------------------------------------
' Parameter 1 : (String) "INTENSITY_Nanometric"
' Parameter 2 : (String) "Default value"
' Parameter 3 : (String) "Unlocked"
' Parameter 4 : (Boolean) False
'--------------------------------------------------

long763 = settingRepository1.GetAttr("SQUARE_VELOCITY")
'--------------------------------------------------
' Parameter 1 : (String) "SQUARE_VELOCITY"
' Returned value : (Variant) (Long) 1
'--------------------------------------------------

Dim bSTR1525
bSTR1525 = ""
Dim bSTR1526
bSTR1526 = ""
Dim boolean763
settingRepository1.GetAttrInfo "SQUARE_VELOCITY", bSTR1525, bSTR1526, boolean763
'--------------------------------------------------
' Parameter 1 : (String) "SQUARE_VELOCITY"
' Parameter 2 : (String) "Default value"
' Parameter 3 : (String) "Unlocked"
' Parameter 4 : (Boolean) False
'--------------------------------------------------

long764 = settingRepository1.GetAttr("SQUARE_VELOCITY_Large")
'--------------------------------------------------
' Parameter 1 : (String) "SQUARE_VELOCITY_Large"
' Returned value : (Variant) (Long) 1
'--------------------------------------------------

Dim bSTR1527
bSTR1527 = ""
Dim bSTR1528
bSTR1528 = ""
Dim boolean764
settingRepository1.GetAttrInfo "SQUARE_VELOCITY_Large", bSTR1527, bSTR1528, boolean764
'--------------------------------------------------
' Parameter 1 : (String) "SQUARE_VELOCITY_Large"
' Parameter 2 : (String) "Default value"
' Parameter 3 : (String) "Unlocked"
' Parameter 4 : (Boolean) False
'--------------------------------------------------

long765 = settingRepository1.GetAttr("SQUARE_VELOCITY_ExtraLarge")
'--------------------------------------------------
' Parameter 1 : (String) "SQUARE_VELOCITY_ExtraLarge"
' Returned value : (Variant) (Long) 1
'--------------------------------------------------

Dim bSTR1529
bSTR1529 = ""
Dim bSTR1530
bSTR1530 = ""
Dim boolean765
settingRepository1.GetAttrInfo "SQUARE_VELOCITY_ExtraLarge", bSTR1529, bSTR1530, boolean765
'--------------------------------------------------
' Parameter 1 : (String) "SQUARE_VELOCITY_ExtraLarge"
' Parameter 2 : (String) "Default value"
' Parameter 3 : (String) "Unlocked"
' Parameter 4 : (Boolean) False
'--------------------------------------------------

long766 = settingRepository1.GetAttr("SQUARE_VELOCITY_Small")
'--------------------------------------------------
' Parameter 1 : (String) "SQUARE_VELOCITY_Small"
' Returned value : (Variant) (Long) 1
'--------------------------------------------------

Dim bSTR1531
bSTR1531 = ""
Dim bSTR1532
bSTR1532 = ""
Dim boolean766
settingRepository1.GetAttrInfo "SQUARE_VELOCITY_Small", bSTR1531, bSTR1532, boolean766
'--------------------------------------------------
' Parameter 1 : (String) "SQUARE_VELOCITY_Small"
' Parameter 2 : (String) "Default value"
' Parameter 3 : (String) "Unlocked"
' Parameter 4 : (Boolean) False
'--------------------------------------------------

long767 = settingRepository1.GetAttr("SQUARE_VELOCITY_ExtraSmall")
'--------------------------------------------------
' Parameter 1 : (String) "SQUARE_VELOCITY_ExtraSmall"
' Returned value : (Variant) (Long) 1
'--------------------------------------------------

Dim bSTR1533
bSTR1533 = ""
Dim bSTR1534
bSTR1534 = ""
Dim boolean767
settingRepository1.GetAttrInfo "SQUARE_VELOCITY_ExtraSmall", bSTR1533, bSTR1534, boolean767
'--------------------------------------------------
' Parameter 1 : (String) "SQUARE_VELOCITY_ExtraSmall"
' Parameter 2 : (String) "Default value"
' Parameter 3 : (String) "Unlocked"
' Parameter 4 : (Boolean) False
'--------------------------------------------------

long768 = settingRepository1.GetAttr("SQUARE_VELOCITY_Nanometric")
'--------------------------------------------------
' Parameter 1 : (String) "SQUARE_VELOCITY_Nanometric"
' Returned value : (Variant) (Long) 1
'--------------------------------------------------

Dim bSTR1535
bSTR1535 = ""
Dim bSTR1536
bSTR1536 = ""
Dim boolean768
settingRepository1.GetAttrInfo "SQUARE_VELOCITY_Nanometric", bSTR1535, bSTR1536, boolean768
'--------------------------------------------------
' Parameter 1 : (String) "SQUARE_VELOCITY_Nanometric"
' Parameter 2 : (String) "Default value"
' Parameter 3 : (String) "Unlocked"
' Parameter 4 : (Boolean) False
'--------------------------------------------------

long769 = settingRepository1.GetAttr("SQUARE_PRESSURE")
'--------------------------------------------------
' Parameter 1 : (String) "SQUARE_PRESSURE"
' Returned value : (Variant) (Long) 1
'--------------------------------------------------

Dim bSTR1537
bSTR1537 = ""
Dim bSTR1538
bSTR1538 = ""
Dim boolean769
settingRepository1.GetAttrInfo "SQUARE_PRESSURE", bSTR1537, bSTR1538, boolean769
'--------------------------------------------------
' Parameter 1 : (String) "SQUARE_PRESSURE"
' Parameter 2 : (String) "Default value"
' Parameter 3 : (String) "Unlocked"
' Parameter 4 : (Boolean) False
'--------------------------------------------------

long770 = settingRepository1.GetAttr("SQUARE_PRESSURE_Large")
'--------------------------------------------------
' Parameter 1 : (String) "SQUARE_PRESSURE_Large"
' Returned value : (Variant) (Long) 1
'--------------------------------------------------

Dim bSTR1539
bSTR1539 = ""
Dim bSTR1540
bSTR1540 = ""
Dim boolean770
settingRepository1.GetAttrInfo "SQUARE_PRESSURE_Large", bSTR1539, bSTR1540, boolean770
'--------------------------------------------------
' Parameter 1 : (String) "SQUARE_PRESSURE_Large"
' Parameter 2 : (String) "Default value"
' Parameter 3 : (String) "Unlocked"
' Parameter 4 : (Boolean) False
'--------------------------------------------------

long771 = settingRepository1.GetAttr("SQUARE_PRESSURE_ExtraLarge")
'--------------------------------------------------
' Parameter 1 : (String) "SQUARE_PRESSURE_ExtraLarge"
' Returned value : (Variant) (Long) 1
'--------------------------------------------------

Dim bSTR1541
bSTR1541 = ""
Dim bSTR1542
bSTR1542 = ""
Dim boolean771
settingRepository1.GetAttrInfo "SQUARE_PRESSURE_ExtraLarge", bSTR1541, bSTR1542, boolean771
'--------------------------------------------------
' Parameter 1 : (String) "SQUARE_PRESSURE_ExtraLarge"
' Parameter 2 : (String) "Default value"
' Parameter 3 : (String) "Unlocked"
' Parameter 4 : (Boolean) False
'--------------------------------------------------

long772 = settingRepository1.GetAttr("SQUARE_PRESSURE_Small")
'--------------------------------------------------
' Parameter 1 : (String) "SQUARE_PRESSURE_Small"
' Returned value : (Variant) (Long) 1
'--------------------------------------------------

Dim bSTR1543
bSTR1543 = ""
Dim bSTR1544
bSTR1544 = ""
Dim boolean772
settingRepository1.GetAttrInfo "SQUARE_PRESSURE_Small", bSTR1543, bSTR1544, boolean772
'--------------------------------------------------
' Parameter 1 : (String) "SQUARE_PRESSURE_Small"
' Parameter 2 : (String) "Default value"
' Parameter 3 : (String) "Unlocked"
' Parameter 4 : (Boolean) False
'--------------------------------------------------

long773 = settingRepository1.GetAttr("SQUARE_PRESSURE_ExtraSmall")
'--------------------------------------------------
' Parameter 1 : (String) "SQUARE_PRESSURE_ExtraSmall"
' Returned value : (Variant) (Long) 1
'--------------------------------------------------

Dim bSTR1545
bSTR1545 = ""
Dim bSTR1546
bSTR1546 = ""
Dim boolean773
settingRepository1.GetAttrInfo "SQUARE_PRESSURE_ExtraSmall", bSTR1545, bSTR1546, boolean773
'--------------------------------------------------
' Parameter 1 : (String) "SQUARE_PRESSURE_ExtraSmall"
' Parameter 2 : (String) "Default value"
' Parameter 3 : (String) "Unlocked"
' Parameter 4 : (Boolean) False
'--------------------------------------------------

long774 = settingRepository1.GetAttr("SQUARE_PRESSURE_Nanometric")
'--------------------------------------------------
' Parameter 1 : (String) "SQUARE_PRESSURE_Nanometric"
' Returned value : (Variant) (Long) 1
'--------------------------------------------------

Dim bSTR1547
bSTR1547 = ""
Dim bSTR1548
bSTR1548 = ""
Dim boolean774
settingRepository1.GetAttrInfo "SQUARE_PRESSURE_Nanometric", bSTR1547, bSTR1548, boolean774
'--------------------------------------------------
' Parameter 1 : (String) "SQUARE_PRESSURE_Nanometric"
' Parameter 2 : (String) "Default value"
' Parameter 3 : (String) "Unlocked"
' Parameter 4 : (Boolean) False
'--------------------------------------------------

long775 = settingRepository1.GetAttr("FLOW_RESISTIVITY")
'--------------------------------------------------
' Parameter 1 : (String) "FLOW_RESISTIVITY"
' Returned value : (Variant) (Long) 1
'--------------------------------------------------

Dim bSTR1549
bSTR1549 = ""
Dim bSTR1550
bSTR1550 = ""
Dim boolean775
settingRepository1.GetAttrInfo "FLOW_RESISTIVITY", bSTR1549, bSTR1550, boolean775
'--------------------------------------------------
' Parameter 1 : (String) "FLOW_RESISTIVITY"
' Parameter 2 : (String) "Default value"
' Parameter 3 : (String) "Unlocked"
' Parameter 4 : (Boolean) False
'--------------------------------------------------

long776 = settingRepository1.GetAttr("FLOW_RESISTIVITY_Large")
'--------------------------------------------------
' Parameter 1 : (String) "FLOW_RESISTIVITY_Large"
' Returned value : (Variant) (Long) 1
'--------------------------------------------------

Dim bSTR1551
bSTR1551 = ""
Dim bSTR1552
bSTR1552 = ""
Dim boolean776
settingRepository1.GetAttrInfo "FLOW_RESISTIVITY_Large", bSTR1551, bSTR1552, boolean776
'--------------------------------------------------
' Parameter 1 : (String) "FLOW_RESISTIVITY_Large"
' Parameter 2 : (String) "Default value"
' Parameter 3 : (String) "Unlocked"
' Parameter 4 : (Boolean) False
'--------------------------------------------------

long777 = settingRepository1.GetAttr("FLOW_RESISTIVITY_ExtraLarge")
'--------------------------------------------------
' Parameter 1 : (String) "FLOW_RESISTIVITY_ExtraLarge"
' Returned value : (Variant) (Long) 1
'--------------------------------------------------

Dim bSTR1553
bSTR1553 = ""
Dim bSTR1554
bSTR1554 = ""
Dim boolean777
settingRepository1.GetAttrInfo "FLOW_RESISTIVITY_ExtraLarge", bSTR1553, bSTR1554, boolean777
'--------------------------------------------------
' Parameter 1 : (String) "FLOW_RESISTIVITY_ExtraLarge"
' Parameter 2 : (String) "Default value"
' Parameter 3 : (String) "Unlocked"
' Parameter 4 : (Boolean) False
'--------------------------------------------------

long778 = settingRepository1.GetAttr("FLOW_RESISTIVITY_Small")
'--------------------------------------------------
' Parameter 1 : (String) "FLOW_RESISTIVITY_Small"
' Returned value : (Variant) (Long) 1
'--------------------------------------------------

Dim bSTR1555
bSTR1555 = ""
Dim bSTR1556
bSTR1556 = ""
Dim boolean778
settingRepository1.GetAttrInfo "FLOW_RESISTIVITY_Small", bSTR1555, bSTR1556, boolean778
'--------------------------------------------------
' Parameter 1 : (String) "FLOW_RESISTIVITY_Small"
' Parameter 2 : (String) "Default value"
' Parameter 3 : (String) "Unlocked"
' Parameter 4 : (Boolean) False
'--------------------------------------------------

long779 = settingRepository1.GetAttr("FLOW_RESISTIVITY_ExtraSmall")
'--------------------------------------------------
' Parameter 1 : (String) "FLOW_RESISTIVITY_ExtraSmall"
' Returned value : (Variant) (Long) 1
'--------------------------------------------------

Dim bSTR1557
bSTR1557 = ""
Dim bSTR1558
bSTR1558 = ""
Dim boolean779
settingRepository1.GetAttrInfo "FLOW_RESISTIVITY_ExtraSmall", bSTR1557, bSTR1558, boolean779
'--------------------------------------------------
' Parameter 1 : (String) "FLOW_RESISTIVITY_ExtraSmall"
' Parameter 2 : (String) "Default value"
' Parameter 3 : (String) "Unlocked"
' Parameter 4 : (Boolean) False
'--------------------------------------------------

long780 = settingRepository1.GetAttr("FLOW_RESISTIVITY_Nanometric")
'--------------------------------------------------
' Parameter 1 : (String) "FLOW_RESISTIVITY_Nanometric"
' Returned value : (Variant) (Long) 1
'--------------------------------------------------

Dim bSTR1559
bSTR1559 = ""
Dim bSTR1560
bSTR1560 = ""
Dim boolean780
settingRepository1.GetAttrInfo "FLOW_RESISTIVITY_Nanometric", bSTR1559, bSTR1560, boolean780
'--------------------------------------------------
' Parameter 1 : (String) "FLOW_RESISTIVITY_Nanometric"
' Parameter 2 : (String) "Default value"
' Parameter 3 : (String) "Unlocked"
' Parameter 4 : (Boolean) False
'--------------------------------------------------

long781 = settingRepository1.GetAttr("CONVECTIVE_FILM_COEFFICIENT")
'--------------------------------------------------
' Parameter 1 : (String) "CONVECTIVE_FILM_COEFFICIENT"
' Returned value : (Variant) (Long) 1
'--------------------------------------------------

Dim bSTR1561
bSTR1561 = ""
Dim bSTR1562
bSTR1562 = ""
Dim boolean781
settingRepository1.GetAttrInfo "CONVECTIVE_FILM_COEFFICIENT", bSTR1561, bSTR1562, boolean781
'--------------------------------------------------
' Parameter 1 : (String) "CONVECTIVE_FILM_COEFFICIENT"
' Parameter 2 : (String) "Default value"
' Parameter 3 : (String) "Unlocked"
' Parameter 4 : (Boolean) False
'--------------------------------------------------

long782 = settingRepository1.GetAttr("CONVECTIVE_FILM_COEFFICIENT_Large")
'--------------------------------------------------
' Parameter 1 : (String) "CONVECTIVE_FILM_COEFFICIENT_Large"
' Returned value : (Variant) (Long) 1
'--------------------------------------------------

Dim bSTR1563
bSTR1563 = ""
Dim bSTR1564
bSTR1564 = ""
Dim boolean782
settingRepository1.GetAttrInfo "CONVECTIVE_FILM_COEFFICIENT_Large", bSTR1563, bSTR1564, boolean782
'--------------------------------------------------
' Parameter 1 : (String) "CONVECTIVE_FILM_COEFFICIENT_Large"
' Parameter 2 : (String) "Default value"
' Parameter 3 : (String) "Unlocked"
' Parameter 4 : (Boolean) False
'--------------------------------------------------

long783 = settingRepository1.GetAttr("CONVECTIVE_FILM_COEFFICIENT_ExtraLarge")
'--------------------------------------------------
' Parameter 1 : (String) "CONVECTIVE_FILM_COEFFICIENT_ExtraLarge"
' Returned value : (Variant) (Long) 1
'--------------------------------------------------

Dim bSTR1565
bSTR1565 = ""
Dim bSTR1566
bSTR1566 = ""
Dim boolean783
settingRepository1.GetAttrInfo "CONVECTIVE_FILM_COEFFICIENT_ExtraLarge", bSTR1565, bSTR1566, boolean783
'--------------------------------------------------
' Parameter 1 : (String) "CONVECTIVE_FILM_COEFFICIENT_ExtraLarge"
' Parameter 2 : (String) "Default value"
' Parameter 3 : (String) "Unlocked"
' Parameter 4 : (Boolean) False
'--------------------------------------------------

long784 = settingRepository1.GetAttr("CONVECTIVE_FILM_COEFFICIENT_Small")
'--------------------------------------------------
' Parameter 1 : (String) "CONVECTIVE_FILM_COEFFICIENT_Small"
' Returned value : (Variant) (Long) 1
'--------------------------------------------------

Dim bSTR1567
bSTR1567 = ""
Dim bSTR1568
bSTR1568 = ""
Dim boolean784
settingRepository1.GetAttrInfo "CONVECTIVE_FILM_COEFFICIENT_Small", bSTR1567, bSTR1568, boolean784
'--------------------------------------------------
' Parameter 1 : (String) "CONVECTIVE_FILM_COEFFICIENT_Small"
' Parameter 2 : (String) "Default value"
' Parameter 3 : (String) "Unlocked"
' Parameter 4 : (Boolean) False
'--------------------------------------------------

long785 = settingRepository1.GetAttr("CONVECTIVE_FILM_COEFFICIENT_ExtraSmall")
'--------------------------------------------------
' Parameter 1 : (String) "CONVECTIVE_FILM_COEFFICIENT_ExtraSmall"
' Returned value : (Variant) (Long) 1
'--------------------------------------------------

Dim bSTR1569
bSTR1569 = ""
Dim bSTR1570
bSTR1570 = ""
Dim boolean785
settingRepository1.GetAttrInfo "CONVECTIVE_FILM_COEFFICIENT_ExtraSmall", bSTR1569, bSTR1570, boolean785
'--------------------------------------------------
' Parameter 1 : (String) "CONVECTIVE_FILM_COEFFICIENT_ExtraSmall"
' Parameter 2 : (String) "Default value"
' Parameter 3 : (String) "Unlocked"
' Parameter 4 : (Boolean) False
'--------------------------------------------------

long786 = settingRepository1.GetAttr("CONVECTIVE_FILM_COEFFICIENT_Nanometric")
'--------------------------------------------------
' Parameter 1 : (String) "CONVECTIVE_FILM_COEFFICIENT_Nanometric"
' Returned value : (Variant) (Long) 1
'--------------------------------------------------

Dim bSTR1571
bSTR1571 = ""
Dim bSTR1572
bSTR1572 = ""
Dim boolean786
settingRepository1.GetAttrInfo "CONVECTIVE_FILM_COEFFICIENT_Nanometric", bSTR1571, bSTR1572, boolean786
'--------------------------------------------------
' Parameter 1 : (String) "CONVECTIVE_FILM_COEFFICIENT_Nanometric"
' Parameter 2 : (String) "Default value"
' Parameter 3 : (String) "Unlocked"
' Parameter 4 : (Boolean) False
'--------------------------------------------------

long787 = settingRepository1.GetAttr("HEAT_RATE")
'--------------------------------------------------
' Parameter 1 : (String) "HEAT_RATE"
' Returned value : (Variant) (Long) 1
'--------------------------------------------------

Dim bSTR1573
bSTR1573 = ""
Dim bSTR1574
bSTR1574 = ""
Dim boolean787
settingRepository1.GetAttrInfo "HEAT_RATE", bSTR1573, bSTR1574, boolean787
'--------------------------------------------------
' Parameter 1 : (String) "HEAT_RATE"
' Parameter 2 : (String) "Default value"
' Parameter 3 : (String) "Unlocked"
' Parameter 4 : (Boolean) False
'--------------------------------------------------

long788 = settingRepository1.GetAttr("HEAT_RATE_Large")
'--------------------------------------------------
' Parameter 1 : (String) "HEAT_RATE_Large"
' Returned value : (Variant) (Long) 1
'--------------------------------------------------

Dim bSTR1575
bSTR1575 = ""
Dim bSTR1576
bSTR1576 = ""
Dim boolean788
settingRepository1.GetAttrInfo "HEAT_RATE_Large", bSTR1575, bSTR1576, boolean788
'--------------------------------------------------
' Parameter 1 : (String) "HEAT_RATE_Large"
' Parameter 2 : (String) "Default value"
' Parameter 3 : (String) "Unlocked"
' Parameter 4 : (Boolean) False
'--------------------------------------------------

long789 = settingRepository1.GetAttr("HEAT_RATE_ExtraLarge")
'--------------------------------------------------
' Parameter 1 : (String) "HEAT_RATE_ExtraLarge"
' Returned value : (Variant) (Long) 1
'--------------------------------------------------

Dim bSTR1577
bSTR1577 = ""
Dim bSTR1578
bSTR1578 = ""
Dim boolean789
settingRepository1.GetAttrInfo "HEAT_RATE_ExtraLarge", bSTR1577, bSTR1578, boolean789
'--------------------------------------------------
' Parameter 1 : (String) "HEAT_RATE_ExtraLarge"
' Parameter 2 : (String) "Default value"
' Parameter 3 : (String) "Unlocked"
' Parameter 4 : (Boolean) False
'--------------------------------------------------

long790 = settingRepository1.GetAttr("HEAT_RATE_Small")
'--------------------------------------------------
' Parameter 1 : (String) "HEAT_RATE_Small"
' Returned value : (Variant) (Long) 1
'--------------------------------------------------

Dim bSTR1579
bSTR1579 = ""
Dim bSTR1580
bSTR1580 = ""
Dim boolean790
settingRepository1.GetAttrInfo "HEAT_RATE_Small", bSTR1579, bSTR1580, boolean790
'--------------------------------------------------
' Parameter 1 : (String) "HEAT_RATE_Small"
' Parameter 2 : (String) "Default value"
' Parameter 3 : (String) "Unlocked"
' Parameter 4 : (Boolean) False
'--------------------------------------------------

long791 = settingRepository1.GetAttr("HEAT_RATE_ExtraSmall")
'--------------------------------------------------
' Parameter 1 : (String) "HEAT_RATE_ExtraSmall"
' Returned value : (Variant) (Long) 1
'--------------------------------------------------

Dim bSTR1581
bSTR1581 = ""
Dim bSTR1582
bSTR1582 = ""
Dim boolean791
settingRepository1.GetAttrInfo "HEAT_RATE_ExtraSmall", bSTR1581, bSTR1582, boolean791
'--------------------------------------------------
' Parameter 1 : (String) "HEAT_RATE_ExtraSmall"
' Parameter 2 : (String) "Default value"
' Parameter 3 : (String) "Unlocked"
' Parameter 4 : (Boolean) False
'--------------------------------------------------

long792 = settingRepository1.GetAttr("HEAT_RATE_Nanometric")
'--------------------------------------------------
' Parameter 1 : (String) "HEAT_RATE_Nanometric"
' Returned value : (Variant) (Long) 1
'--------------------------------------------------

Dim bSTR1583
bSTR1583 = ""
Dim bSTR1584
bSTR1584 = ""
Dim boolean792
settingRepository1.GetAttrInfo "HEAT_RATE_Nanometric", bSTR1583, bSTR1584, boolean792
'--------------------------------------------------
' Parameter 1 : (String) "HEAT_RATE_Nanometric"
' Parameter 2 : (String) "Default value"
' Parameter 3 : (String) "Unlocked"
' Parameter 4 : (Boolean) False
'--------------------------------------------------

long793 = settingRepository1.GetAttr("HEAT_FLUX")
'--------------------------------------------------
' Parameter 1 : (String) "HEAT_FLUX"
' Returned value : (Variant) (Long) 1
'--------------------------------------------------

Dim bSTR1585
bSTR1585 = ""
Dim bSTR1586
bSTR1586 = ""
Dim boolean793
settingRepository1.GetAttrInfo "HEAT_FLUX", bSTR1585, bSTR1586, boolean793
'--------------------------------------------------
' Parameter 1 : (String) "HEAT_FLUX"
' Parameter 2 : (String) "Default value"
' Parameter 3 : (String) "Unlocked"
' Parameter 4 : (Boolean) False
'--------------------------------------------------

long794 = settingRepository1.GetAttr("HEAT_FLUX_Large")
'--------------------------------------------------
' Parameter 1 : (String) "HEAT_FLUX_Large"
' Returned value : (Variant) (Long) 1
'--------------------------------------------------

Dim bSTR1587
bSTR1587 = ""
Dim bSTR1588
bSTR1588 = ""
Dim boolean794
settingRepository1.GetAttrInfo "HEAT_FLUX_Large", bSTR1587, bSTR1588, boolean794
'--------------------------------------------------
' Parameter 1 : (String) "HEAT_FLUX_Large"
' Parameter 2 : (String) "Default value"
' Parameter 3 : (String) "Unlocked"
' Parameter 4 : (Boolean) False
'--------------------------------------------------

long795 = settingRepository1.GetAttr("HEAT_FLUX_ExtraLarge")
'--------------------------------------------------
' Parameter 1 : (String) "HEAT_FLUX_ExtraLarge"
' Returned value : (Variant) (Long) 1
'--------------------------------------------------

Dim bSTR1589
bSTR1589 = ""
Dim bSTR1590
bSTR1590 = ""
Dim boolean795
settingRepository1.GetAttrInfo "HEAT_FLUX_ExtraLarge", bSTR1589, bSTR1590, boolean795
'--------------------------------------------------
' Parameter 1 : (String) "HEAT_FLUX_ExtraLarge"
' Parameter 2 : (String) "Default value"
' Parameter 3 : (String) "Unlocked"
' Parameter 4 : (Boolean) False
'--------------------------------------------------

long796 = settingRepository1.GetAttr("HEAT_FLUX_Small")
'--------------------------------------------------
' Parameter 1 : (String) "HEAT_FLUX_Small"
' Returned value : (Variant) (Long) 1
'--------------------------------------------------

Dim bSTR1591
bSTR1591 = ""
Dim bSTR1592
bSTR1592 = ""
Dim boolean796
settingRepository1.GetAttrInfo "HEAT_FLUX_Small", bSTR1591, bSTR1592, boolean796
'--------------------------------------------------
' Parameter 1 : (String) "HEAT_FLUX_Small"
' Parameter 2 : (String) "Default value"
' Parameter 3 : (String) "Unlocked"
' Parameter 4 : (Boolean) False
'--------------------------------------------------

long797 = settingRepository1.GetAttr("HEAT_FLUX_ExtraSmall")
'--------------------------------------------------
' Parameter 1 : (String) "HEAT_FLUX_ExtraSmall"
' Returned value : (Variant) (Long) 1
'--------------------------------------------------

Dim bSTR1593
bSTR1593 = ""
Dim bSTR1594
bSTR1594 = ""
Dim boolean797
settingRepository1.GetAttrInfo "HEAT_FLUX_ExtraSmall", bSTR1593, bSTR1594, boolean797
'--------------------------------------------------
' Parameter 1 : (String) "HEAT_FLUX_ExtraSmall"
' Parameter 2 : (String) "Default value"
' Parameter 3 : (String) "Unlocked"
' Parameter 4 : (Boolean) False
'--------------------------------------------------

long798 = settingRepository1.GetAttr("HEAT_FLUX_Nanometric")
'--------------------------------------------------
' Parameter 1 : (String) "HEAT_FLUX_Nanometric"
' Returned value : (Variant) (Long) 1
'--------------------------------------------------

Dim bSTR1595
bSTR1595 = ""
Dim bSTR1596
bSTR1596 = ""
Dim boolean798
settingRepository1.GetAttrInfo "HEAT_FLUX_Nanometric", bSTR1595, bSTR1596, boolean798
'--------------------------------------------------
' Parameter 1 : (String) "HEAT_FLUX_Nanometric"
' Parameter 2 : (String) "Default value"
' Parameter 3 : (String) "Unlocked"
' Parameter 4 : (Boolean) False
'--------------------------------------------------

long799 = settingRepository1.GetAttr("ANGULAR_VELOCITY")
'--------------------------------------------------
' Parameter 1 : (String) "ANGULAR_VELOCITY"
' Returned value : (Variant) (Long) 1
'--------------------------------------------------

Dim bSTR1597
bSTR1597 = ""
Dim bSTR1598
bSTR1598 = ""
Dim boolean799
settingRepository1.GetAttrInfo "ANGULAR_VELOCITY", bSTR1597, bSTR1598, boolean799
'--------------------------------------------------
' Parameter 1 : (String) "ANGULAR_VELOCITY"
' Parameter 2 : (String) "Default value"
' Parameter 3 : (String) "Unlocked"
' Parameter 4 : (Boolean) False
'--------------------------------------------------

long800 = settingRepository1.GetAttr("ANGULAR_VELOCITY_Large")
'--------------------------------------------------
' Parameter 1 : (String) "ANGULAR_VELOCITY_Large"
' Returned value : (Variant) (Long) 1
'--------------------------------------------------

Dim bSTR1599
bSTR1599 = ""
Dim bSTR1600
bSTR1600 = ""
Dim boolean800
settingRepository1.GetAttrInfo "ANGULAR_VELOCITY_Large", bSTR1599, bSTR1600, boolean800
'--------------------------------------------------
' Parameter 1 : (String) "ANGULAR_VELOCITY_Large"
' Parameter 2 : (String) "Default value"
' Parameter 3 : (String) "Unlocked"
' Parameter 4 : (Boolean) False
'--------------------------------------------------

long801 = settingRepository1.GetAttr("ANGULAR_VELOCITY_ExtraLarge")
'--------------------------------------------------
' Parameter 1 : (String) "ANGULAR_VELOCITY_ExtraLarge"
' Returned value : (Variant) (Long) 1
'--------------------------------------------------

Dim bSTR1601
bSTR1601 = ""
Dim bSTR1602
bSTR1602 = ""
Dim boolean801
settingRepository1.GetAttrInfo "ANGULAR_VELOCITY_ExtraLarge", bSTR1601, bSTR1602, boolean801
'--------------------------------------------------
' Parameter 1 : (String) "ANGULAR_VELOCITY_ExtraLarge"
' Parameter 2 : (String) "Default value"
' Parameter 3 : (String) "Unlocked"
' Parameter 4 : (Boolean) False
'--------------------------------------------------

long802 = settingRepository1.GetAttr("ANGULAR_VELOCITY_Small")
'--------------------------------------------------
' Parameter 1 : (String) "ANGULAR_VELOCITY_Small"
' Returned value : (Variant) (Long) 1
'--------------------------------------------------

Dim bSTR1603
bSTR1603 = ""
Dim bSTR1604
bSTR1604 = ""
Dim boolean802
settingRepository1.GetAttrInfo "ANGULAR_VELOCITY_Small", bSTR1603, bSTR1604, boolean802
'--------------------------------------------------
' Parameter 1 : (String) "ANGULAR_VELOCITY_Small"
' Parameter 2 : (String) "Default value"
' Parameter 3 : (String) "Unlocked"
' Parameter 4 : (Boolean) False
'--------------------------------------------------

long803 = settingRepository1.GetAttr("ANGULAR_VELOCITY_ExtraSmall")
'--------------------------------------------------
' Parameter 1 : (String) "ANGULAR_VELOCITY_ExtraSmall"
' Returned value : (Variant) (Long) 1
'--------------------------------------------------

Dim bSTR1605
bSTR1605 = ""
Dim bSTR1606
bSTR1606 = ""
Dim boolean803
settingRepository1.GetAttrInfo "ANGULAR_VELOCITY_ExtraSmall", bSTR1605, bSTR1606, boolean803
'--------------------------------------------------
' Parameter 1 : (String) "ANGULAR_VELOCITY_ExtraSmall"
' Parameter 2 : (String) "Default value"
' Parameter 3 : (String) "Unlocked"
' Parameter 4 : (Boolean) False
'--------------------------------------------------

long804 = settingRepository1.GetAttr("ANGULAR_VELOCITY_Nanometric")
'--------------------------------------------------
' Parameter 1 : (String) "ANGULAR_VELOCITY_Nanometric"
' Returned value : (Variant) (Long) 1
'--------------------------------------------------

Dim bSTR1607
bSTR1607 = ""
Dim bSTR1608
bSTR1608 = ""
Dim boolean804
settingRepository1.GetAttrInfo "ANGULAR_VELOCITY_Nanometric", bSTR1607, bSTR1608, boolean804
'--------------------------------------------------
' Parameter 1 : (String) "ANGULAR_VELOCITY_Nanometric"
' Parameter 2 : (String) "Default value"
' Parameter 3 : (String) "Unlocked"
' Parameter 4 : (Boolean) False
'--------------------------------------------------

long805 = settingRepository1.GetAttr("CUMULATIVE_MOMENT")
'--------------------------------------------------
' Parameter 1 : (String) "CUMULATIVE_MOMENT"
' Returned value : (Variant) (Long) 1
'--------------------------------------------------

Dim bSTR1609
bSTR1609 = ""
Dim bSTR1610
bSTR1610 = ""
Dim boolean805
settingRepository1.GetAttrInfo "CUMULATIVE_MOMENT", bSTR1609, bSTR1610, boolean805
'--------------------------------------------------
' Parameter 1 : (String) "CUMULATIVE_MOMENT"
' Parameter 2 : (String) "Default value"
' Parameter 3 : (String) "Unlocked"
' Parameter 4 : (Boolean) False
'--------------------------------------------------

long806 = settingRepository1.GetAttr("CUMULATIVE_MOMENT_Large")
'--------------------------------------------------
' Parameter 1 : (String) "CUMULATIVE_MOMENT_Large"
' Returned value : (Variant) (Long) 1
'--------------------------------------------------

Dim bSTR1611
bSTR1611 = ""
Dim bSTR1612
bSTR1612 = ""
Dim boolean806
settingRepository1.GetAttrInfo "CUMULATIVE_MOMENT_Large", bSTR1611, bSTR1612, boolean806
'--------------------------------------------------
' Parameter 1 : (String) "CUMULATIVE_MOMENT_Large"
' Parameter 2 : (String) "Default value"
' Parameter 3 : (String) "Unlocked"
' Parameter 4 : (Boolean) False
'--------------------------------------------------

long807 = settingRepository1.GetAttr("CUMULATIVE_MOMENT_ExtraLarge")
'--------------------------------------------------
' Parameter 1 : (String) "CUMULATIVE_MOMENT_ExtraLarge"
' Returned value : (Variant) (Long) 1
'--------------------------------------------------

Dim bSTR1613
bSTR1613 = ""
Dim bSTR1614
bSTR1614 = ""
Dim boolean807
settingRepository1.GetAttrInfo "CUMULATIVE_MOMENT_ExtraLarge", bSTR1613, bSTR1614, boolean807
'--------------------------------------------------
' Parameter 1 : (String) "CUMULATIVE_MOMENT_ExtraLarge"
' Parameter 2 : (String) "Default value"
' Parameter 3 : (String) "Unlocked"
' Parameter 4 : (Boolean) False
'--------------------------------------------------

long808 = settingRepository1.GetAttr("CUMULATIVE_MOMENT_Small")
'--------------------------------------------------
' Parameter 1 : (String) "CUMULATIVE_MOMENT_Small"
' Returned value : (Variant) (Long) 1
'--------------------------------------------------

Dim bSTR1615
bSTR1615 = ""
Dim bSTR1616
bSTR1616 = ""
Dim boolean808
settingRepository1.GetAttrInfo "CUMULATIVE_MOMENT_Small", bSTR1615, bSTR1616, boolean808
'--------------------------------------------------
' Parameter 1 : (String) "CUMULATIVE_MOMENT_Small"
' Parameter 2 : (String) "Default value"
' Parameter 3 : (String) "Unlocked"
' Parameter 4 : (Boolean) False
'--------------------------------------------------

long809 = settingRepository1.GetAttr("CUMULATIVE_MOMENT_ExtraSmall")
'--------------------------------------------------
' Parameter 1 : (String) "CUMULATIVE_MOMENT_ExtraSmall"
' Returned value : (Variant) (Long) 1
'--------------------------------------------------

Dim bSTR1617
bSTR1617 = ""
Dim bSTR1618
bSTR1618 = ""
Dim boolean809
settingRepository1.GetAttrInfo "CUMULATIVE_MOMENT_ExtraSmall", bSTR1617, bSTR1618, boolean809
'--------------------------------------------------
' Parameter 1 : (String) "CUMULATIVE_MOMENT_ExtraSmall"
' Parameter 2 : (String) "Default value"
' Parameter 3 : (String) "Unlocked"
' Parameter 4 : (Boolean) False
'--------------------------------------------------

long810 = settingRepository1.GetAttr("CUMULATIVE_MOMENT_Nanometric")
'--------------------------------------------------
' Parameter 1 : (String) "CUMULATIVE_MOMENT_Nanometric"
' Returned value : (Variant) (Long) 1
'--------------------------------------------------

Dim bSTR1619
bSTR1619 = ""
Dim bSTR1620
bSTR1620 = ""
Dim boolean810
settingRepository1.GetAttrInfo "CUMULATIVE_MOMENT_Nanometric", bSTR1619, bSTR1620, boolean810
'--------------------------------------------------
' Parameter 1 : (String) "CUMULATIVE_MOMENT_Nanometric"
' Parameter 2 : (String) "Default value"
' Parameter 3 : (String) "Unlocked"
' Parameter 4 : (Boolean) False
'--------------------------------------------------

long811 = settingRepository1.GetAttr("CURVATURE")
'--------------------------------------------------
' Parameter 1 : (String) "CURVATURE"
' Returned value : (Variant) (Long) 1
'--------------------------------------------------

Dim bSTR1621
bSTR1621 = ""
Dim bSTR1622
bSTR1622 = ""
Dim boolean811
settingRepository1.GetAttrInfo "CURVATURE", bSTR1621, bSTR1622, boolean811
'--------------------------------------------------
' Parameter 1 : (String) "CURVATURE"
' Parameter 2 : (String) "Default value"
' Parameter 3 : (String) "Unlocked"
' Parameter 4 : (Boolean) False
'--------------------------------------------------

long812 = settingRepository1.GetAttr("CURVATURE_Large")
'--------------------------------------------------
' Parameter 1 : (String) "CURVATURE_Large"
' Returned value : (Variant) (Long) 1
'--------------------------------------------------

Dim bSTR1623
bSTR1623 = ""
Dim bSTR1624
bSTR1624 = ""
Dim boolean812
settingRepository1.GetAttrInfo "CURVATURE_Large", bSTR1623, bSTR1624, boolean812
'--------------------------------------------------
' Parameter 1 : (String) "CURVATURE_Large"
' Parameter 2 : (String) "Default value"
' Parameter 3 : (String) "Unlocked"
' Parameter 4 : (Boolean) False
'--------------------------------------------------

long813 = settingRepository1.GetAttr("CURVATURE_ExtraLarge")
'--------------------------------------------------
' Parameter 1 : (String) "CURVATURE_ExtraLarge"
' Returned value : (Variant) (Long) 1
'--------------------------------------------------

Dim bSTR1625
bSTR1625 = ""
Dim bSTR1626
bSTR1626 = ""
Dim boolean813
settingRepository1.GetAttrInfo "CURVATURE_ExtraLarge", bSTR1625, bSTR1626, boolean813
'--------------------------------------------------
' Parameter 1 : (String) "CURVATURE_ExtraLarge"
' Parameter 2 : (String) "Default value"
' Parameter 3 : (String) "Unlocked"
' Parameter 4 : (Boolean) False
'--------------------------------------------------

long814 = settingRepository1.GetAttr("CURVATURE_Small")
'--------------------------------------------------
' Parameter 1 : (String) "CURVATURE_Small"
' Returned value : (Variant) (Long) 1
'--------------------------------------------------

Dim bSTR1627
bSTR1627 = ""
Dim bSTR1628
bSTR1628 = ""
Dim boolean814
settingRepository1.GetAttrInfo "CURVATURE_Small", bSTR1627, bSTR1628, boolean814
'--------------------------------------------------
' Parameter 1 : (String) "CURVATURE_Small"
' Parameter 2 : (String) "Default value"
' Parameter 3 : (String) "Unlocked"
' Parameter 4 : (Boolean) False
'--------------------------------------------------

long815 = settingRepository1.GetAttr("CURVATURE_ExtraSmall")
'--------------------------------------------------
' Parameter 1 : (String) "CURVATURE_ExtraSmall"
' Returned value : (Variant) (Long) 1
'--------------------------------------------------

Dim bSTR1629
bSTR1629 = ""
Dim bSTR1630
bSTR1630 = ""
Dim boolean815
settingRepository1.GetAttrInfo "CURVATURE_ExtraSmall", bSTR1629, bSTR1630, boolean815
'--------------------------------------------------
' Parameter 1 : (String) "CURVATURE_ExtraSmall"
' Parameter 2 : (String) "Default value"
' Parameter 3 : (String) "Unlocked"
' Parameter 4 : (Boolean) False
'--------------------------------------------------

long816 = settingRepository1.GetAttr("CURVATURE_Nanometric")
'--------------------------------------------------
' Parameter 1 : (String) "CURVATURE_Nanometric"
' Returned value : (Variant) (Long) 1
'--------------------------------------------------

Dim bSTR1631
bSTR1631 = ""
Dim bSTR1632
bSTR1632 = ""
Dim boolean816
settingRepository1.GetAttrInfo "CURVATURE_Nanometric", bSTR1631, bSTR1632, boolean816
'--------------------------------------------------
' Parameter 1 : (String) "CURVATURE_Nanometric"
' Parameter 2 : (String) "Default value"
' Parameter 3 : (String) "Unlocked"
' Parameter 4 : (Boolean) False
'--------------------------------------------------

long817 = settingRepository1.GetAttr("SQUARE_TIME")
'--------------------------------------------------
' Parameter 1 : (String) "SQUARE_TIME"
' Returned value : (Variant) (Long) 1
'--------------------------------------------------

Dim bSTR1633
bSTR1633 = ""
Dim bSTR1634
bSTR1634 = ""
Dim boolean817
settingRepository1.GetAttrInfo "SQUARE_TIME", bSTR1633, bSTR1634, boolean817
'--------------------------------------------------
' Parameter 1 : (String) "SQUARE_TIME"
' Parameter 2 : (String) "Default value"
' Parameter 3 : (String) "Unlocked"
' Parameter 4 : (Boolean) False
'--------------------------------------------------

long818 = settingRepository1.GetAttr("SQUARE_TIME_Large")
'--------------------------------------------------
' Parameter 1 : (String) "SQUARE_TIME_Large"
' Returned value : (Variant) (Long) 1
'--------------------------------------------------

Dim bSTR1635
bSTR1635 = ""
Dim bSTR1636
bSTR1636 = ""
Dim boolean818
settingRepository1.GetAttrInfo "SQUARE_TIME_Large", bSTR1635, bSTR1636, boolean818
'--------------------------------------------------
' Parameter 1 : (String) "SQUARE_TIME_Large"
' Parameter 2 : (String) "Default value"
' Parameter 3 : (String) "Unlocked"
' Parameter 4 : (Boolean) False
'--------------------------------------------------

long819 = settingRepository1.GetAttr("SQUARE_TIME_ExtraLarge")
'--------------------------------------------------
' Parameter 1 : (String) "SQUARE_TIME_ExtraLarge"
' Returned value : (Variant) (Long) 1
'--------------------------------------------------

Dim bSTR1637
bSTR1637 = ""
Dim bSTR1638
bSTR1638 = ""
Dim boolean819
settingRepository1.GetAttrInfo "SQUARE_TIME_ExtraLarge", bSTR1637, bSTR1638, boolean819
'--------------------------------------------------
' Parameter 1 : (String) "SQUARE_TIME_ExtraLarge"
' Parameter 2 : (String) "Default value"
' Parameter 3 : (String) "Unlocked"
' Parameter 4 : (Boolean) False
'--------------------------------------------------

long820 = settingRepository1.GetAttr("SQUARE_TIME_Small")
'--------------------------------------------------
' Parameter 1 : (String) "SQUARE_TIME_Small"
' Returned value : (Variant) (Long) 1
'--------------------------------------------------

Dim bSTR1639
bSTR1639 = ""
Dim bSTR1640
bSTR1640 = ""
Dim boolean820
settingRepository1.GetAttrInfo "SQUARE_TIME_Small", bSTR1639, bSTR1640, boolean820
'--------------------------------------------------
' Parameter 1 : (String) "SQUARE_TIME_Small"
' Parameter 2 : (String) "Default value"
' Parameter 3 : (String) "Unlocked"
' Parameter 4 : (Boolean) False
'--------------------------------------------------

long821 = settingRepository1.GetAttr("SQUARE_TIME_ExtraSmall")
'--------------------------------------------------
' Parameter 1 : (String) "SQUARE_TIME_ExtraSmall"
' Returned value : (Variant) (Long) 1
'--------------------------------------------------

Dim bSTR1641
bSTR1641 = ""
Dim bSTR1642
bSTR1642 = ""
Dim boolean821
settingRepository1.GetAttrInfo "SQUARE_TIME_ExtraSmall", bSTR1641, bSTR1642, boolean821
'--------------------------------------------------
' Parameter 1 : (String) "SQUARE_TIME_ExtraSmall"
' Parameter 2 : (String) "Default value"
' Parameter 3 : (String) "Unlocked"
' Parameter 4 : (Boolean) False
'--------------------------------------------------

long822 = settingRepository1.GetAttr("SQUARE_TIME_Nanometric")
'--------------------------------------------------
' Parameter 1 : (String) "SQUARE_TIME_Nanometric"
' Returned value : (Variant) (Long) 1
'--------------------------------------------------

Dim bSTR1643
bSTR1643 = ""
Dim bSTR1644
bSTR1644 = ""
Dim boolean822
settingRepository1.GetAttrInfo "SQUARE_TIME_Nanometric", bSTR1643, bSTR1644, boolean822
'--------------------------------------------------
' Parameter 1 : (String) "SQUARE_TIME_Nanometric"
' Parameter 2 : (String) "Default value"
' Parameter 3 : (String) "Unlocked"
' Parameter 4 : (Boolean) False
'--------------------------------------------------

long823 = settingRepository1.GetAttr("VOLUME_VELOCITY")
'--------------------------------------------------
' Parameter 1 : (String) "VOLUME_VELOCITY"
' Returned value : (Variant) (Long) 1
'--------------------------------------------------

Dim bSTR1645
bSTR1645 = ""
Dim bSTR1646
bSTR1646 = ""
Dim boolean823
settingRepository1.GetAttrInfo "VOLUME_VELOCITY", bSTR1645, bSTR1646, boolean823
'--------------------------------------------------
' Parameter 1 : (String) "VOLUME_VELOCITY"
' Parameter 2 : (String) "Default value"
' Parameter 3 : (String) "Unlocked"
' Parameter 4 : (Boolean) False
'--------------------------------------------------

long824 = settingRepository1.GetAttr("VOLUME_VELOCITY_Large")
'--------------------------------------------------
' Parameter 1 : (String) "VOLUME_VELOCITY_Large"
' Returned value : (Variant) (Long) 1
'--------------------------------------------------

Dim bSTR1647
bSTR1647 = ""
Dim bSTR1648
bSTR1648 = ""
Dim boolean824
settingRepository1.GetAttrInfo "VOLUME_VELOCITY_Large", bSTR1647, bSTR1648, boolean824
'--------------------------------------------------
' Parameter 1 : (String) "VOLUME_VELOCITY_Large"
' Parameter 2 : (String) "Default value"
' Parameter 3 : (String) "Unlocked"
' Parameter 4 : (Boolean) False
'--------------------------------------------------

long825 = settingRepository1.GetAttr("VOLUME_VELOCITY_ExtraLarge")
'--------------------------------------------------
' Parameter 1 : (String) "VOLUME_VELOCITY_ExtraLarge"
' Returned value : (Variant) (Long) 1
'--------------------------------------------------

Dim bSTR1649
bSTR1649 = ""
Dim bSTR1650
bSTR1650 = ""
Dim boolean825
settingRepository1.GetAttrInfo "VOLUME_VELOCITY_ExtraLarge", bSTR1649, bSTR1650, boolean825
'--------------------------------------------------
' Parameter 1 : (String) "VOLUME_VELOCITY_ExtraLarge"
' Parameter 2 : (String) "Default value"
' Parameter 3 : (String) "Unlocked"
' Parameter 4 : (Boolean) False
'--------------------------------------------------

long826 = settingRepository1.GetAttr("VOLUME_VELOCITY_Small")
'--------------------------------------------------
' Parameter 1 : (String) "VOLUME_VELOCITY_Small"
' Returned value : (Variant) (Long) 1
'--------------------------------------------------

Dim bSTR1651
bSTR1651 = ""
Dim bSTR1652
bSTR1652 = ""
Dim boolean826
settingRepository1.GetAttrInfo "VOLUME_VELOCITY_Small", bSTR1651, bSTR1652, boolean826
'--------------------------------------------------
' Parameter 1 : (String) "VOLUME_VELOCITY_Small"
' Parameter 2 : (String) "Default value"
' Parameter 3 : (String) "Unlocked"
' Parameter 4 : (Boolean) False
'--------------------------------------------------

long827 = settingRepository1.GetAttr("VOLUME_VELOCITY_ExtraSmall")
'--------------------------------------------------
' Parameter 1 : (String) "VOLUME_VELOCITY_ExtraSmall"
' Returned value : (Variant) (Long) 1
'--------------------------------------------------

Dim bSTR1653
bSTR1653 = ""
Dim bSTR1654
bSTR1654 = ""
Dim boolean827
settingRepository1.GetAttrInfo "VOLUME_VELOCITY_ExtraSmall", bSTR1653, bSTR1654, boolean827
'--------------------------------------------------
' Parameter 1 : (String) "VOLUME_VELOCITY_ExtraSmall"
' Parameter 2 : (String) "Default value"
' Parameter 3 : (String) "Unlocked"
' Parameter 4 : (Boolean) False
'--------------------------------------------------

long828 = settingRepository1.GetAttr("VOLUME_VELOCITY_Nanometric")
'--------------------------------------------------
' Parameter 1 : (String) "VOLUME_VELOCITY_Nanometric"
' Returned value : (Variant) (Long) 1
'--------------------------------------------------

Dim bSTR1655
bSTR1655 = ""
Dim bSTR1656
bSTR1656 = ""
Dim boolean828
settingRepository1.GetAttrInfo "VOLUME_VELOCITY_Nanometric", bSTR1655, bSTR1656, boolean828
'--------------------------------------------------
' Parameter 1 : (String) "VOLUME_VELOCITY_Nanometric"
' Parameter 2 : (String) "Default value"
' Parameter 3 : (String) "Unlocked"
' Parameter 4 : (Boolean) False
'--------------------------------------------------

long829 = settingRepository1.GetAttr("PRESSURE_OVER_VOLUME_ACCELERATION")
'--------------------------------------------------
' Parameter 1 : (String) "PRESSURE_OVER_VOLUME_ACCELERATION"
' Returned value : (Variant) (Long) 1
'--------------------------------------------------

Dim bSTR1657
bSTR1657 = ""
Dim bSTR1658
bSTR1658 = ""
Dim boolean829
settingRepository1.GetAttrInfo "PRESSURE_OVER_VOLUME_ACCELERATION", bSTR1657, bSTR1658, boolean829
'--------------------------------------------------
' Parameter 1 : (String) "PRESSURE_OVER_VOLUME_ACCELERATION"
' Parameter 2 : (String) "Default value"
' Parameter 3 : (String) "Unlocked"
' Parameter 4 : (Boolean) False
'--------------------------------------------------

long830 = settingRepository1.GetAttr("PRESSURE_OVER_VOLUME_ACCELERATION_Large")
'--------------------------------------------------
' Parameter 1 : (String) "PRESSURE_OVER_VOLUME_ACCELERATION_Large"
' Returned value : (Variant) (Long) 1
'--------------------------------------------------

Dim bSTR1659
bSTR1659 = ""
Dim bSTR1660
bSTR1660 = ""
Dim boolean830
settingRepository1.GetAttrInfo "PRESSURE_OVER_VOLUME_ACCELERATION_Large", bSTR1659, bSTR1660, boolean830
'--------------------------------------------------
' Parameter 1 : (String) "PRESSURE_OVER_VOLUME_ACCELERATION_Large"
' Parameter 2 : (String) "Default value"
' Parameter 3 : (String) "Unlocked"
' Parameter 4 : (Boolean) False
'--------------------------------------------------

long831 = settingRepository1.GetAttr("PRESSURE_OVER_VOLUME_ACCELERATION_ExtraLarge")
'--------------------------------------------------
' Parameter 1 : (String) "PRESSURE_OVER_VOLUME_ACCELERATION_ExtraLarge"
' Returned value : (Variant) (Long) 1
'--------------------------------------------------

Dim bSTR1661
bSTR1661 = ""
Dim bSTR1662
bSTR1662 = ""
Dim boolean831
settingRepository1.GetAttrInfo "PRESSURE_OVER_VOLUME_ACCELERATION_ExtraLarge", bSTR1661, bSTR1662, boolean831
'--------------------------------------------------
' Parameter 1 : (String) "PRESSURE_OVER_VOLUME_ACCELERATION_ExtraLarge"
' Parameter 2 : (String) "Default value"
' Parameter 3 : (String) "Unlocked"
' Parameter 4 : (Boolean) False
'--------------------------------------------------

long832 = settingRepository1.GetAttr("PRESSURE_OVER_VOLUME_ACCELERATION_Small")
'--------------------------------------------------
' Parameter 1 : (String) "PRESSURE_OVER_VOLUME_ACCELERATION_Small"
' Returned value : (Variant) (Long) 1
'--------------------------------------------------

Dim bSTR1663
bSTR1663 = ""
Dim bSTR1664
bSTR1664 = ""
Dim boolean832
settingRepository1.GetAttrInfo "PRESSURE_OVER_VOLUME_ACCELERATION_Small", bSTR1663, bSTR1664, boolean832
'--------------------------------------------------
' Parameter 1 : (String) "PRESSURE_OVER_VOLUME_ACCELERATION_Small"
' Parameter 2 : (String) "Default value"
' Parameter 3 : (String) "Unlocked"
' Parameter 4 : (Boolean) False
'--------------------------------------------------

long833 = settingRepository1.GetAttr("PRESSURE_OVER_VOLUME_ACCELERATION_ExtraSmall")
'--------------------------------------------------
' Parameter 1 : (String) "PRESSURE_OVER_VOLUME_ACCELERATION_ExtraSmall"
' Returned value : (Variant) (Long) 1
'--------------------------------------------------

Dim bSTR1665
bSTR1665 = ""
Dim bSTR1666
bSTR1666 = ""
Dim boolean833
settingRepository1.GetAttrInfo "PRESSURE_OVER_VOLUME_ACCELERATION_ExtraSmall", bSTR1665, bSTR1666, boolean833
'--------------------------------------------------
' Parameter 1 : (String) "PRESSURE_OVER_VOLUME_ACCELERATION_ExtraSmall"
' Parameter 2 : (String) "Default value"
' Parameter 3 : (String) "Unlocked"
' Parameter 4 : (Boolean) False
'--------------------------------------------------

long834 = settingRepository1.GetAttr("PRESSURE_OVER_VOLUME_ACCELERATION_Nanometric")
'--------------------------------------------------
' Parameter 1 : (String) "PRESSURE_OVER_VOLUME_ACCELERATION_Nanometric"
' Returned value : (Variant) (Long) 1
'--------------------------------------------------

Dim bSTR1667
bSTR1667 = ""
Dim bSTR1668
bSTR1668 = ""
Dim boolean834
settingRepository1.GetAttrInfo "PRESSURE_OVER_VOLUME_ACCELERATION_Nanometric", bSTR1667, bSTR1668, boolean834
'--------------------------------------------------
' Parameter 1 : (String) "PRESSURE_OVER_VOLUME_ACCELERATION_Nanometric"
' Parameter 2 : (String) "Default value"
' Parameter 3 : (String) "Unlocked"
' Parameter 4 : (Boolean) False
'--------------------------------------------------

long835 = settingRepository1.GetAttr("SQUARE_FORCE")
'--------------------------------------------------
' Parameter 1 : (String) "SQUARE_FORCE"
' Returned value : (Variant) (Long) 1
'--------------------------------------------------

Dim bSTR1669
bSTR1669 = ""
Dim bSTR1670
bSTR1670 = ""
Dim boolean835
settingRepository1.GetAttrInfo "SQUARE_FORCE", bSTR1669, bSTR1670, boolean835
'--------------------------------------------------
' Parameter 1 : (String) "SQUARE_FORCE"
' Parameter 2 : (String) "Default value"
' Parameter 3 : (String) "Unlocked"
' Parameter 4 : (Boolean) False
'--------------------------------------------------

long836 = settingRepository1.GetAttr("SQUARE_FORCE_Large")
'--------------------------------------------------
' Parameter 1 : (String) "SQUARE_FORCE_Large"
' Returned value : (Variant) (Long) 1
'--------------------------------------------------

Dim bSTR1671
bSTR1671 = ""
Dim bSTR1672
bSTR1672 = ""
Dim boolean836
settingRepository1.GetAttrInfo "SQUARE_FORCE_Large", bSTR1671, bSTR1672, boolean836
'--------------------------------------------------
' Parameter 1 : (String) "SQUARE_FORCE_Large"
' Parameter 2 : (String) "Default value"
' Parameter 3 : (String) "Unlocked"
' Parameter 4 : (Boolean) False
'--------------------------------------------------

long837 = settingRepository1.GetAttr("SQUARE_FORCE_ExtraLarge")
'--------------------------------------------------
' Parameter 1 : (String) "SQUARE_FORCE_ExtraLarge"
' Returned value : (Variant) (Long) 1
'--------------------------------------------------

Dim bSTR1673
bSTR1673 = ""
Dim bSTR1674
bSTR1674 = ""
Dim boolean837
settingRepository1.GetAttrInfo "SQUARE_FORCE_ExtraLarge", bSTR1673, bSTR1674, boolean837
'--------------------------------------------------
' Parameter 1 : (String) "SQUARE_FORCE_ExtraLarge"
' Parameter 2 : (String) "Default value"
' Parameter 3 : (String) "Unlocked"
' Parameter 4 : (Boolean) False
'--------------------------------------------------

long838 = settingRepository1.GetAttr("SQUARE_FORCE_Small")
'--------------------------------------------------
' Parameter 1 : (String) "SQUARE_FORCE_Small"
' Returned value : (Variant) (Long) 1
'--------------------------------------------------

Dim bSTR1675
bSTR1675 = ""
Dim bSTR1676
bSTR1676 = ""
Dim boolean838
settingRepository1.GetAttrInfo "SQUARE_FORCE_Small", bSTR1675, bSTR1676, boolean838
'--------------------------------------------------
' Parameter 1 : (String) "SQUARE_FORCE_Small"
' Parameter 2 : (String) "Default value"
' Parameter 3 : (String) "Unlocked"
' Parameter 4 : (Boolean) False
'--------------------------------------------------

long839 = settingRepository1.GetAttr("SQUARE_FORCE_ExtraSmall")
'--------------------------------------------------
' Parameter 1 : (String) "SQUARE_FORCE_ExtraSmall"
' Returned value : (Variant) (Long) 1
'--------------------------------------------------

Dim bSTR1677
bSTR1677 = ""
Dim bSTR1678
bSTR1678 = ""
Dim boolean839
settingRepository1.GetAttrInfo "SQUARE_FORCE_ExtraSmall", bSTR1677, bSTR1678, boolean839
'--------------------------------------------------
' Parameter 1 : (String) "SQUARE_FORCE_ExtraSmall"
' Parameter 2 : (String) "Default value"
' Parameter 3 : (String) "Unlocked"
' Parameter 4 : (Boolean) False
'--------------------------------------------------

long840 = settingRepository1.GetAttr("SQUARE_FORCE_Nanometric")
'--------------------------------------------------
' Parameter 1 : (String) "SQUARE_FORCE_Nanometric"
' Returned value : (Variant) (Long) 1
'--------------------------------------------------

Dim bSTR1679
bSTR1679 = ""
Dim bSTR1680
bSTR1680 = ""
Dim boolean840
settingRepository1.GetAttrInfo "SQUARE_FORCE_Nanometric", bSTR1679, bSTR1680, boolean840
'--------------------------------------------------
' Parameter 1 : (String) "SQUARE_FORCE_Nanometric"
' Parameter 2 : (String) "Default value"
' Parameter 3 : (String) "Unlocked"
' Parameter 4 : (Boolean) False
'--------------------------------------------------

long841 = settingRepository1.GetAttr("SQUARE_MOMENT")
'--------------------------------------------------
' Parameter 1 : (String) "SQUARE_MOMENT"
' Returned value : (Variant) (Long) 1
'--------------------------------------------------

Dim bSTR1681
bSTR1681 = ""
Dim bSTR1682
bSTR1682 = ""
Dim boolean841
settingRepository1.GetAttrInfo "SQUARE_MOMENT", bSTR1681, bSTR1682, boolean841
'--------------------------------------------------
' Parameter 1 : (String) "SQUARE_MOMENT"
' Parameter 2 : (String) "Default value"
' Parameter 3 : (String) "Unlocked"
' Parameter 4 : (Boolean) False
'--------------------------------------------------

long842 = settingRepository1.GetAttr("SQUARE_MOMENT_Large")
'--------------------------------------------------
' Parameter 1 : (String) "SQUARE_MOMENT_Large"
' Returned value : (Variant) (Long) 1
'--------------------------------------------------

Dim bSTR1683
bSTR1683 = ""
Dim bSTR1684
bSTR1684 = ""
Dim boolean842
settingRepository1.GetAttrInfo "SQUARE_MOMENT_Large", bSTR1683, bSTR1684, boolean842
'--------------------------------------------------
' Parameter 1 : (String) "SQUARE_MOMENT_Large"
' Parameter 2 : (String) "Default value"
' Parameter 3 : (String) "Unlocked"
' Parameter 4 : (Boolean) False
'--------------------------------------------------

long843 = settingRepository1.GetAttr("SQUARE_MOMENT_ExtraLarge")
'--------------------------------------------------
' Parameter 1 : (String) "SQUARE_MOMENT_ExtraLarge"
' Returned value : (Variant) (Long) 1
'--------------------------------------------------

Dim bSTR1685
bSTR1685 = ""
Dim bSTR1686
bSTR1686 = ""
Dim boolean843
settingRepository1.GetAttrInfo "SQUARE_MOMENT_ExtraLarge", bSTR1685, bSTR1686, boolean843
'--------------------------------------------------
' Parameter 1 : (String) "SQUARE_MOMENT_ExtraLarge"
' Parameter 2 : (String) "Default value"
' Parameter 3 : (String) "Unlocked"
' Parameter 4 : (Boolean) False
'--------------------------------------------------

long844 = settingRepository1.GetAttr("SQUARE_MOMENT_Small")
'--------------------------------------------------
' Parameter 1 : (String) "SQUARE_MOMENT_Small"
' Returned value : (Variant) (Long) 1
'--------------------------------------------------

Dim bSTR1687
bSTR1687 = ""
Dim bSTR1688
bSTR1688 = ""
Dim boolean844
settingRepository1.GetAttrInfo "SQUARE_MOMENT_Small", bSTR1687, bSTR1688, boolean844
'--------------------------------------------------
' Parameter 1 : (String) "SQUARE_MOMENT_Small"
' Parameter 2 : (String) "Default value"
' Parameter 3 : (String) "Unlocked"
' Parameter 4 : (Boolean) False
'--------------------------------------------------

long845 = settingRepository1.GetAttr("SQUARE_MOMENT_ExtraSmall")
'--------------------------------------------------
' Parameter 1 : (String) "SQUARE_MOMENT_ExtraSmall"
' Returned value : (Variant) (Long) 1
'--------------------------------------------------

Dim bSTR1689
bSTR1689 = ""
Dim bSTR1690
bSTR1690 = ""
Dim boolean845
settingRepository1.GetAttrInfo "SQUARE_MOMENT_ExtraSmall", bSTR1689, bSTR1690, boolean845
'--------------------------------------------------
' Parameter 1 : (String) "SQUARE_MOMENT_ExtraSmall"
' Parameter 2 : (String) "Default value"
' Parameter 3 : (String) "Unlocked"
' Parameter 4 : (Boolean) False
'--------------------------------------------------

long846 = settingRepository1.GetAttr("SQUARE_MOMENT_Nanometric")
'--------------------------------------------------
' Parameter 1 : (String) "SQUARE_MOMENT_Nanometric"
' Returned value : (Variant) (Long) 1
'--------------------------------------------------

Dim bSTR1691
bSTR1691 = ""
Dim bSTR1692
bSTR1692 = ""
Dim boolean846
settingRepository1.GetAttrInfo "SQUARE_MOMENT_Nanometric", bSTR1691, bSTR1692, boolean846
'--------------------------------------------------
' Parameter 1 : (String) "SQUARE_MOMENT_Nanometric"
' Parameter 2 : (String) "Default value"
' Parameter 3 : (String) "Unlocked"
' Parameter 4 : (Boolean) False
'--------------------------------------------------

long847 = settingRepository1.GetAttr("SQUARE_DISPLACEMENT")
'--------------------------------------------------
' Parameter 1 : (String) "SQUARE_DISPLACEMENT"
' Returned value : (Variant) (Long) 1
'--------------------------------------------------

Dim bSTR1693
bSTR1693 = ""
Dim bSTR1694
bSTR1694 = ""
Dim boolean847
settingRepository1.GetAttrInfo "SQUARE_DISPLACEMENT", bSTR1693, bSTR1694, boolean847
'--------------------------------------------------
' Parameter 1 : (String) "SQUARE_DISPLACEMENT"
' Parameter 2 : (String) "Default value"
' Parameter 3 : (String) "Unlocked"
' Parameter 4 : (Boolean) False
'--------------------------------------------------

long848 = settingRepository1.GetAttr("SQUARE_DISPLACEMENT_Large")
'--------------------------------------------------
' Parameter 1 : (String) "SQUARE_DISPLACEMENT_Large"
' Returned value : (Variant) (Long) 1
'--------------------------------------------------

Dim bSTR1695
bSTR1695 = ""
Dim bSTR1696
bSTR1696 = ""
Dim boolean848
settingRepository1.GetAttrInfo "SQUARE_DISPLACEMENT_Large", bSTR1695, bSTR1696, boolean848
'--------------------------------------------------
' Parameter 1 : (String) "SQUARE_DISPLACEMENT_Large"
' Parameter 2 : (String) "Default value"
' Parameter 3 : (String) "Unlocked"
' Parameter 4 : (Boolean) False
'--------------------------------------------------

long849 = settingRepository1.GetAttr("SQUARE_DISPLACEMENT_ExtraLarge")
'--------------------------------------------------
' Parameter 1 : (String) "SQUARE_DISPLACEMENT_ExtraLarge"
' Returned value : (Variant) (Long) 1
'--------------------------------------------------

Dim bSTR1697
bSTR1697 = ""
Dim bSTR1698
bSTR1698 = ""
Dim boolean849
settingRepository1.GetAttrInfo "SQUARE_DISPLACEMENT_ExtraLarge", bSTR1697, bSTR1698, boolean849
'--------------------------------------------------
' Parameter 1 : (String) "SQUARE_DISPLACEMENT_ExtraLarge"
' Parameter 2 : (String) "Default value"
' Parameter 3 : (String) "Unlocked"
' Parameter 4 : (Boolean) False
'--------------------------------------------------

long850 = settingRepository1.GetAttr("SQUARE_DISPLACEMENT_Small")
'--------------------------------------------------
' Parameter 1 : (String) "SQUARE_DISPLACEMENT_Small"
' Returned value : (Variant) (Long) 1
'--------------------------------------------------

Dim bSTR1699
bSTR1699 = ""
Dim bSTR1700
bSTR1700 = ""
Dim boolean850
settingRepository1.GetAttrInfo "SQUARE_DISPLACEMENT_Small", bSTR1699, bSTR1700, boolean850
'--------------------------------------------------
' Parameter 1 : (String) "SQUARE_DISPLACEMENT_Small"
' Parameter 2 : (String) "Default value"
' Parameter 3 : (String) "Unlocked"
' Parameter 4 : (Boolean) False
'--------------------------------------------------

long851 = settingRepository1.GetAttr("SQUARE_DISPLACEMENT_ExtraSmall")
'--------------------------------------------------
' Parameter 1 : (String) "SQUARE_DISPLACEMENT_ExtraSmall"
' Returned value : (Variant) (Long) 1
'--------------------------------------------------

Dim bSTR1701
bSTR1701 = ""
Dim bSTR1702
bSTR1702 = ""
Dim boolean851
settingRepository1.GetAttrInfo "SQUARE_DISPLACEMENT_ExtraSmall", bSTR1701, bSTR1702, boolean851
'--------------------------------------------------
' Parameter 1 : (String) "SQUARE_DISPLACEMENT_ExtraSmall"
' Parameter 2 : (String) "Default value"
' Parameter 3 : (String) "Unlocked"
' Parameter 4 : (Boolean) False
'--------------------------------------------------

long852 = settingRepository1.GetAttr("SQUARE_DISPLACEMENT_Nanometric")
'--------------------------------------------------
' Parameter 1 : (String) "SQUARE_DISPLACEMENT_Nanometric"
' Returned value : (Variant) (Long) 1
'--------------------------------------------------

Dim bSTR1703
bSTR1703 = ""
Dim bSTR1704
bSTR1704 = ""
Dim boolean852
settingRepository1.GetAttrInfo "SQUARE_DISPLACEMENT_Nanometric", bSTR1703, bSTR1704, boolean852
'--------------------------------------------------
' Parameter 1 : (String) "SQUARE_DISPLACEMENT_Nanometric"
' Parameter 2 : (String) "Default value"
' Parameter 3 : (String) "Unlocked"
' Parameter 4 : (Boolean) False
'--------------------------------------------------

long853 = settingRepository1.GetAttr("SQUARE_ROTATION")
'--------------------------------------------------
' Parameter 1 : (String) "SQUARE_ROTATION"
' Returned value : (Variant) (Long) 1
'--------------------------------------------------

Dim bSTR1705
bSTR1705 = ""
Dim bSTR1706
bSTR1706 = ""
Dim boolean853
settingRepository1.GetAttrInfo "SQUARE_ROTATION", bSTR1705, bSTR1706, boolean853
'--------------------------------------------------
' Parameter 1 : (String) "SQUARE_ROTATION"
' Parameter 2 : (String) "Default value"
' Parameter 3 : (String) "Unlocked"
' Parameter 4 : (Boolean) False
'--------------------------------------------------

long854 = settingRepository1.GetAttr("SQUARE_ROTATION_Large")
'--------------------------------------------------
' Parameter 1 : (String) "SQUARE_ROTATION_Large"
' Returned value : (Variant) (Long) 1
'--------------------------------------------------

Dim bSTR1707
bSTR1707 = ""
Dim bSTR1708
bSTR1708 = ""
Dim boolean854
settingRepository1.GetAttrInfo "SQUARE_ROTATION_Large", bSTR1707, bSTR1708, boolean854
'--------------------------------------------------
' Parameter 1 : (String) "SQUARE_ROTATION_Large"
' Parameter 2 : (String) "Default value"
' Parameter 3 : (String) "Unlocked"
' Parameter 4 : (Boolean) False
'--------------------------------------------------

long855 = settingRepository1.GetAttr("SQUARE_ROTATION_ExtraLarge")
'--------------------------------------------------
' Parameter 1 : (String) "SQUARE_ROTATION_ExtraLarge"
' Returned value : (Variant) (Long) 1
'--------------------------------------------------

Dim bSTR1709
bSTR1709 = ""
Dim bSTR1710
bSTR1710 = ""
Dim boolean855
settingRepository1.GetAttrInfo "SQUARE_ROTATION_ExtraLarge", bSTR1709, bSTR1710, boolean855
'--------------------------------------------------
' Parameter 1 : (String) "SQUARE_ROTATION_ExtraLarge"
' Parameter 2 : (String) "Default value"
' Parameter 3 : (String) "Unlocked"
' Parameter 4 : (Boolean) False
'--------------------------------------------------

long856 = settingRepository1.GetAttr("SQUARE_ROTATION_Small")
'--------------------------------------------------
' Parameter 1 : (String) "SQUARE_ROTATION_Small"
' Returned value : (Variant) (Long) 1
'--------------------------------------------------

Dim bSTR1711
bSTR1711 = ""
Dim bSTR1712
bSTR1712 = ""
Dim boolean856
settingRepository1.GetAttrInfo "SQUARE_ROTATION_Small", bSTR1711, bSTR1712, boolean856
'--------------------------------------------------
' Parameter 1 : (String) "SQUARE_ROTATION_Small"
' Parameter 2 : (String) "Default value"
' Parameter 3 : (String) "Unlocked"
' Parameter 4 : (Boolean) False
'--------------------------------------------------

long857 = settingRepository1.GetAttr("SQUARE_ROTATION_ExtraSmall")
'--------------------------------------------------
' Parameter 1 : (String) "SQUARE_ROTATION_ExtraSmall"
' Returned value : (Variant) (Long) 1
'--------------------------------------------------

Dim bSTR1713
bSTR1713 = ""
Dim bSTR1714
bSTR1714 = ""
Dim boolean857
settingRepository1.GetAttrInfo "SQUARE_ROTATION_ExtraSmall", bSTR1713, bSTR1714, boolean857
'--------------------------------------------------
' Parameter 1 : (String) "SQUARE_ROTATION_ExtraSmall"
' Parameter 2 : (String) "Default value"
' Parameter 3 : (String) "Unlocked"
' Parameter 4 : (Boolean) False
'--------------------------------------------------

long858 = settingRepository1.GetAttr("SQUARE_ROTATION_Nanometric")
'--------------------------------------------------
' Parameter 1 : (String) "SQUARE_ROTATION_Nanometric"
' Returned value : (Variant) (Long) 1
'--------------------------------------------------

Dim bSTR1715
bSTR1715 = ""
Dim bSTR1716
bSTR1716 = ""
Dim boolean858
settingRepository1.GetAttrInfo "SQUARE_ROTATION_Nanometric", bSTR1715, bSTR1716, boolean858
'--------------------------------------------------
' Parameter 1 : (String) "SQUARE_ROTATION_Nanometric"
' Parameter 2 : (String) "Default value"
' Parameter 3 : (String) "Unlocked"
' Parameter 4 : (Boolean) False
'--------------------------------------------------

long859 = settingRepository1.GetAttr("SQUARE_PULSATION")
'--------------------------------------------------
' Parameter 1 : (String) "SQUARE_PULSATION"
' Returned value : (Variant) (Long) 1
'--------------------------------------------------

Dim bSTR1717
bSTR1717 = ""
Dim bSTR1718
bSTR1718 = ""
Dim boolean859
settingRepository1.GetAttrInfo "SQUARE_PULSATION", bSTR1717, bSTR1718, boolean859
'--------------------------------------------------
' Parameter 1 : (String) "SQUARE_PULSATION"
' Parameter 2 : (String) "Default value"
' Parameter 3 : (String) "Unlocked"
' Parameter 4 : (Boolean) False
'--------------------------------------------------

long860 = settingRepository1.GetAttr("SQUARE_PULSATION_Large")
'--------------------------------------------------
' Parameter 1 : (String) "SQUARE_PULSATION_Large"
' Returned value : (Variant) (Long) 1
'--------------------------------------------------

Dim bSTR1719
bSTR1719 = ""
Dim bSTR1720
bSTR1720 = ""
Dim boolean860
settingRepository1.GetAttrInfo "SQUARE_PULSATION_Large", bSTR1719, bSTR1720, boolean860
'--------------------------------------------------
' Parameter 1 : (String) "SQUARE_PULSATION_Large"
' Parameter 2 : (String) "Default value"
' Parameter 3 : (String) "Unlocked"
' Parameter 4 : (Boolean) False
'--------------------------------------------------

long861 = settingRepository1.GetAttr("SQUARE_PULSATION_ExtraLarge")
'--------------------------------------------------
' Parameter 1 : (String) "SQUARE_PULSATION_ExtraLarge"
' Returned value : (Variant) (Long) 1
'--------------------------------------------------

Dim bSTR1721
bSTR1721 = ""
Dim bSTR1722
bSTR1722 = ""
Dim boolean861
settingRepository1.GetAttrInfo "SQUARE_PULSATION_ExtraLarge", bSTR1721, bSTR1722, boolean861
'--------------------------------------------------
' Parameter 1 : (String) "SQUARE_PULSATION_ExtraLarge"
' Parameter 2 : (String) "Default value"
' Parameter 3 : (String) "Unlocked"
' Parameter 4 : (Boolean) False
'--------------------------------------------------

long862 = settingRepository1.GetAttr("SQUARE_PULSATION_Small")
'--------------------------------------------------
' Parameter 1 : (String) "SQUARE_PULSATION_Small"
' Returned value : (Variant) (Long) 1
'--------------------------------------------------

Dim bSTR1723
bSTR1723 = ""
Dim bSTR1724
bSTR1724 = ""
Dim boolean862
settingRepository1.GetAttrInfo "SQUARE_PULSATION_Small", bSTR1723, bSTR1724, boolean862
'--------------------------------------------------
' Parameter 1 : (String) "SQUARE_PULSATION_Small"
' Parameter 2 : (String) "Default value"
' Parameter 3 : (String) "Unlocked"
' Parameter 4 : (Boolean) False
'--------------------------------------------------

long863 = settingRepository1.GetAttr("SQUARE_PULSATION_ExtraSmall")
'--------------------------------------------------
' Parameter 1 : (String) "SQUARE_PULSATION_ExtraSmall"
' Returned value : (Variant) (Long) 1
'--------------------------------------------------

Dim bSTR1725
bSTR1725 = ""
Dim bSTR1726
bSTR1726 = ""
Dim boolean863
settingRepository1.GetAttrInfo "SQUARE_PULSATION_ExtraSmall", bSTR1725, bSTR1726, boolean863
'--------------------------------------------------
' Parameter 1 : (String) "SQUARE_PULSATION_ExtraSmall"
' Parameter 2 : (String) "Default value"
' Parameter 3 : (String) "Unlocked"
' Parameter 4 : (Boolean) False
'--------------------------------------------------

long864 = settingRepository1.GetAttr("SQUARE_PULSATION_Nanometric")
'--------------------------------------------------
' Parameter 1 : (String) "SQUARE_PULSATION_Nanometric"
' Returned value : (Variant) (Long) 1
'--------------------------------------------------

Dim bSTR1727
bSTR1727 = ""
Dim bSTR1728
bSTR1728 = ""
Dim boolean864
settingRepository1.GetAttrInfo "SQUARE_PULSATION_Nanometric", bSTR1727, bSTR1728, boolean864
'--------------------------------------------------
' Parameter 1 : (String) "SQUARE_PULSATION_Nanometric"
' Parameter 2 : (String) "Default value"
' Parameter 3 : (String) "Unlocked"
' Parameter 4 : (Boolean) False
'--------------------------------------------------

long865 = settingRepository1.GetAttr("SQUARE_ACCELERATION")
'--------------------------------------------------
' Parameter 1 : (String) "SQUARE_ACCELERATION"
' Returned value : (Variant) (Long) 1
'--------------------------------------------------

Dim bSTR1729
bSTR1729 = ""
Dim bSTR1730
bSTR1730 = ""
Dim boolean865
settingRepository1.GetAttrInfo "SQUARE_ACCELERATION", bSTR1729, bSTR1730, boolean865
'--------------------------------------------------
' Parameter 1 : (String) "SQUARE_ACCELERATION"
' Parameter 2 : (String) "Default value"
' Parameter 3 : (String) "Unlocked"
' Parameter 4 : (Boolean) False
'--------------------------------------------------

long866 = settingRepository1.GetAttr("SQUARE_ACCELERATION_Large")
'--------------------------------------------------
' Parameter 1 : (String) "SQUARE_ACCELERATION_Large"
' Returned value : (Variant) (Long) 1
'--------------------------------------------------

Dim bSTR1731
bSTR1731 = ""
Dim bSTR1732
bSTR1732 = ""
Dim boolean866
settingRepository1.GetAttrInfo "SQUARE_ACCELERATION_Large", bSTR1731, bSTR1732, boolean866
'--------------------------------------------------
' Parameter 1 : (String) "SQUARE_ACCELERATION_Large"
' Parameter 2 : (String) "Default value"
' Parameter 3 : (String) "Unlocked"
' Parameter 4 : (Boolean) False
'--------------------------------------------------

long867 = settingRepository1.GetAttr("SQUARE_ACCELERATION_ExtraLarge")
'--------------------------------------------------
' Parameter 1 : (String) "SQUARE_ACCELERATION_ExtraLarge"
' Returned value : (Variant) (Long) 1
'--------------------------------------------------

Dim bSTR1733
bSTR1733 = ""
Dim bSTR1734
bSTR1734 = ""
Dim boolean867
settingRepository1.GetAttrInfo "SQUARE_ACCELERATION_ExtraLarge", bSTR1733, bSTR1734, boolean867
'--------------------------------------------------
' Parameter 1 : (String) "SQUARE_ACCELERATION_ExtraLarge"
' Parameter 2 : (String) "Default value"
' Parameter 3 : (String) "Unlocked"
' Parameter 4 : (Boolean) False
'--------------------------------------------------

long868 = settingRepository1.GetAttr("SQUARE_ACCELERATION_Small")
'--------------------------------------------------
' Parameter 1 : (String) "SQUARE_ACCELERATION_Small"
' Returned value : (Variant) (Long) 1
'--------------------------------------------------

Dim bSTR1735
bSTR1735 = ""
Dim bSTR1736
bSTR1736 = ""
Dim boolean868
settingRepository1.GetAttrInfo "SQUARE_ACCELERATION_Small", bSTR1735, bSTR1736, boolean868
'--------------------------------------------------
' Parameter 1 : (String) "SQUARE_ACCELERATION_Small"
' Parameter 2 : (String) "Default value"
' Parameter 3 : (String) "Unlocked"
' Parameter 4 : (Boolean) False
'--------------------------------------------------

long869 = settingRepository1.GetAttr("SQUARE_ACCELERATION_ExtraSmall")
'--------------------------------------------------
' Parameter 1 : (String) "SQUARE_ACCELERATION_ExtraSmall"
' Returned value : (Variant) (Long) 1
'--------------------------------------------------

Dim bSTR1737
bSTR1737 = ""
Dim bSTR1738
bSTR1738 = ""
Dim boolean869
settingRepository1.GetAttrInfo "SQUARE_ACCELERATION_ExtraSmall", bSTR1737, bSTR1738, boolean869
'--------------------------------------------------
' Parameter 1 : (String) "SQUARE_ACCELERATION_ExtraSmall"
' Parameter 2 : (String) "Default value"
' Parameter 3 : (String) "Unlocked"
' Parameter 4 : (Boolean) False
'--------------------------------------------------

long870 = settingRepository1.GetAttr("SQUARE_ACCELERATION_Nanometric")
'--------------------------------------------------
' Parameter 1 : (String) "SQUARE_ACCELERATION_Nanometric"
' Returned value : (Variant) (Long) 1
'--------------------------------------------------

Dim bSTR1739
bSTR1739 = ""
Dim bSTR1740
bSTR1740 = ""
Dim boolean870
settingRepository1.GetAttrInfo "SQUARE_ACCELERATION_Nanometric", bSTR1739, bSTR1740, boolean870
'--------------------------------------------------
' Parameter 1 : (String) "SQUARE_ACCELERATION_Nanometric"
' Parameter 2 : (String) "Default value"
' Parameter 3 : (String) "Unlocked"
' Parameter 4 : (Boolean) False
'--------------------------------------------------

long871 = settingRepository1.GetAttr("SQUARE_ROTATIONAL_ACCELERATION")
'--------------------------------------------------
' Parameter 1 : (String) "SQUARE_ROTATIONAL_ACCELERATION"
' Returned value : (Variant) (Long) 1
'--------------------------------------------------

Dim bSTR1741
bSTR1741 = ""
Dim bSTR1742
bSTR1742 = ""
Dim boolean871
settingRepository1.GetAttrInfo "SQUARE_ROTATIONAL_ACCELERATION", bSTR1741, bSTR1742, boolean871
'--------------------------------------------------
' Parameter 1 : (String) "SQUARE_ROTATIONAL_ACCELERATION"
' Parameter 2 : (String) "Default value"
' Parameter 3 : (String) "Unlocked"
' Parameter 4 : (Boolean) False
'--------------------------------------------------

long872 = settingRepository1.GetAttr("SQUARE_ROTATIONAL_ACCELERATION_Large")
'--------------------------------------------------
' Parameter 1 : (String) "SQUARE_ROTATIONAL_ACCELERATION_Large"
' Returned value : (Variant) (Long) 1
'--------------------------------------------------

Dim bSTR1743
bSTR1743 = ""
Dim bSTR1744
bSTR1744 = ""
Dim boolean872
settingRepository1.GetAttrInfo "SQUARE_ROTATIONAL_ACCELERATION_Large", bSTR1743, bSTR1744, boolean872
'--------------------------------------------------
' Parameter 1 : (String) "SQUARE_ROTATIONAL_ACCELERATION_Large"
' Parameter 2 : (String) "Default value"
' Parameter 3 : (String) "Unlocked"
' Parameter 4 : (Boolean) False
'--------------------------------------------------

long873 = settingRepository1.GetAttr("SQUARE_ROTATIONAL_ACCELERATION_ExtraLarge")
'--------------------------------------------------
' Parameter 1 : (String) "SQUARE_ROTATIONAL_ACCELERATION_ExtraLarge"
' Returned value : (Variant) (Long) 1
'--------------------------------------------------

Dim bSTR1745
bSTR1745 = ""
Dim bSTR1746
bSTR1746 = ""
Dim boolean873
settingRepository1.GetAttrInfo "SQUARE_ROTATIONAL_ACCELERATION_ExtraLarge", bSTR1745, bSTR1746, boolean873
'--------------------------------------------------
' Parameter 1 : (String) "SQUARE_ROTATIONAL_ACCELERATION_ExtraLarge"
' Parameter 2 : (String) "Default value"
' Parameter 3 : (String) "Unlocked"
' Parameter 4 : (Boolean) False
'--------------------------------------------------

long874 = settingRepository1.GetAttr("SQUARE_ROTATIONAL_ACCELERATION_Small")
'--------------------------------------------------
' Parameter 1 : (String) "SQUARE_ROTATIONAL_ACCELERATION_Small"
' Returned value : (Variant) (Long) 1
'--------------------------------------------------

Dim bSTR1747
bSTR1747 = ""
Dim bSTR1748
bSTR1748 = ""
Dim boolean874
settingRepository1.GetAttrInfo "SQUARE_ROTATIONAL_ACCELERATION_Small", bSTR1747, bSTR1748, boolean874
'--------------------------------------------------
' Parameter 1 : (String) "SQUARE_ROTATIONAL_ACCELERATION_Small"
' Parameter 2 : (String) "Default value"
' Parameter 3 : (String) "Unlocked"
' Parameter 4 : (Boolean) False
'--------------------------------------------------

long875 = settingRepository1.GetAttr("SQUARE_ROTATIONAL_ACCELERATION_ExtraSmall")
'--------------------------------------------------
' Parameter 1 : (String) "SQUARE_ROTATIONAL_ACCELERATION_ExtraSmall"
' Returned value : (Variant) (Long) 1
'--------------------------------------------------

Dim bSTR1749
bSTR1749 = ""
Dim bSTR1750
bSTR1750 = ""
Dim boolean875
settingRepository1.GetAttrInfo "SQUARE_ROTATIONAL_ACCELERATION_ExtraSmall", bSTR1749, bSTR1750, boolean875
'--------------------------------------------------
' Parameter 1 : (String) "SQUARE_ROTATIONAL_ACCELERATION_ExtraSmall"
' Parameter 2 : (String) "Default value"
' Parameter 3 : (String) "Unlocked"
' Parameter 4 : (Boolean) False
'--------------------------------------------------

long876 = settingRepository1.GetAttr("SQUARE_ROTATIONAL_ACCELERATION_Nanometric")
'--------------------------------------------------
' Parameter 1 : (String) "SQUARE_ROTATIONAL_ACCELERATION_Nanometric"
' Returned value : (Variant) (Long) 1
'--------------------------------------------------

Dim bSTR1751
bSTR1751 = ""
Dim bSTR1752
bSTR1752 = ""
Dim boolean876
settingRepository1.GetAttrInfo "SQUARE_ROTATIONAL_ACCELERATION_Nanometric", bSTR1751, bSTR1752, boolean876
'--------------------------------------------------
' Parameter 1 : (String) "SQUARE_ROTATIONAL_ACCELERATION_Nanometric"
' Parameter 2 : (String) "Default value"
' Parameter 3 : (String) "Unlocked"
' Parameter 4 : (Boolean) False
'--------------------------------------------------

long877 = settingRepository1.GetAttr("SQUARE_VOLUME_ACCELERATION")
'--------------------------------------------------
' Parameter 1 : (String) "SQUARE_VOLUME_ACCELERATION"
' Returned value : (Variant) (Long) 1
'--------------------------------------------------

Dim bSTR1753
bSTR1753 = ""
Dim bSTR1754
bSTR1754 = ""
Dim boolean877
settingRepository1.GetAttrInfo "SQUARE_VOLUME_ACCELERATION", bSTR1753, bSTR1754, boolean877
'--------------------------------------------------
' Parameter 1 : (String) "SQUARE_VOLUME_ACCELERATION"
' Parameter 2 : (String) "Default value"
' Parameter 3 : (String) "Unlocked"
' Parameter 4 : (Boolean) False
'--------------------------------------------------

long878 = settingRepository1.GetAttr("SQUARE_VOLUME_ACCELERATION_Large")
'--------------------------------------------------
' Parameter 1 : (String) "SQUARE_VOLUME_ACCELERATION_Large"
' Returned value : (Variant) (Long) 1
'--------------------------------------------------

Dim bSTR1755
bSTR1755 = ""
Dim bSTR1756
bSTR1756 = ""
Dim boolean878
settingRepository1.GetAttrInfo "SQUARE_VOLUME_ACCELERATION_Large", bSTR1755, bSTR1756, boolean878
'--------------------------------------------------
' Parameter 1 : (String) "SQUARE_VOLUME_ACCELERATION_Large"
' Parameter 2 : (String) "Default value"
' Parameter 3 : (String) "Unlocked"
' Parameter 4 : (Boolean) False
'--------------------------------------------------

long879 = settingRepository1.GetAttr("SQUARE_VOLUME_ACCELERATION_ExtraLarge")
'--------------------------------------------------
' Parameter 1 : (String) "SQUARE_VOLUME_ACCELERATION_ExtraLarge"
' Returned value : (Variant) (Long) 1
'--------------------------------------------------

Dim bSTR1757
bSTR1757 = ""
Dim bSTR1758
bSTR1758 = ""
Dim boolean879
settingRepository1.GetAttrInfo "SQUARE_VOLUME_ACCELERATION_ExtraLarge", bSTR1757, bSTR1758, boolean879
'--------------------------------------------------
' Parameter 1 : (String) "SQUARE_VOLUME_ACCELERATION_ExtraLarge"
' Parameter 2 : (String) "Default value"
' Parameter 3 : (String) "Unlocked"
' Parameter 4 : (Boolean) False
'--------------------------------------------------

long880 = settingRepository1.GetAttr("SQUARE_VOLUME_ACCELERATION_Small")
'--------------------------------------------------
' Parameter 1 : (String) "SQUARE_VOLUME_ACCELERATION_Small"
' Returned value : (Variant) (Long) 1
'--------------------------------------------------

Dim bSTR1759
bSTR1759 = ""
Dim bSTR1760
bSTR1760 = ""
Dim boolean880
settingRepository1.GetAttrInfo "SQUARE_VOLUME_ACCELERATION_Small", bSTR1759, bSTR1760, boolean880
'--------------------------------------------------
' Parameter 1 : (String) "SQUARE_VOLUME_ACCELERATION_Small"
' Parameter 2 : (String) "Default value"
' Parameter 3 : (String) "Unlocked"
' Parameter 4 : (Boolean) False
'--------------------------------------------------

long881 = settingRepository1.GetAttr("SQUARE_VOLUME_ACCELERATION_ExtraSmall")
'--------------------------------------------------
' Parameter 1 : (String) "SQUARE_VOLUME_ACCELERATION_ExtraSmall"
' Returned value : (Variant) (Long) 1
'--------------------------------------------------

Dim bSTR1761
bSTR1761 = ""
Dim bSTR1762
bSTR1762 = ""
Dim boolean881
settingRepository1.GetAttrInfo "SQUARE_VOLUME_ACCELERATION_ExtraSmall", bSTR1761, bSTR1762, boolean881
'--------------------------------------------------
' Parameter 1 : (String) "SQUARE_VOLUME_ACCELERATION_ExtraSmall"
' Parameter 2 : (String) "Default value"
' Parameter 3 : (String) "Unlocked"
' Parameter 4 : (Boolean) False
'--------------------------------------------------

long882 = settingRepository1.GetAttr("SQUARE_VOLUME_ACCELERATION_Nanometric")
'--------------------------------------------------
' Parameter 1 : (String) "SQUARE_VOLUME_ACCELERATION_Nanometric"
' Returned value : (Variant) (Long) 1
'--------------------------------------------------

Dim bSTR1763
bSTR1763 = ""
Dim bSTR1764
bSTR1764 = ""
Dim boolean882
settingRepository1.GetAttrInfo "SQUARE_VOLUME_ACCELERATION_Nanometric", bSTR1763, bSTR1764, boolean882
'--------------------------------------------------
' Parameter 1 : (String) "SQUARE_VOLUME_ACCELERATION_Nanometric"
' Parameter 2 : (String) "Default value"
' Parameter 3 : (String) "Unlocked"
' Parameter 4 : (Boolean) False
'--------------------------------------------------

long883 = settingRepository1.GetAttr("SQUARE_VOLUME_VELOCITY")
'--------------------------------------------------
' Parameter 1 : (String) "SQUARE_VOLUME_VELOCITY"
' Returned value : (Variant) (Long) 1
'--------------------------------------------------

Dim bSTR1765
bSTR1765 = ""
Dim bSTR1766
bSTR1766 = ""
Dim boolean883
settingRepository1.GetAttrInfo "SQUARE_VOLUME_VELOCITY", bSTR1765, bSTR1766, boolean883
'--------------------------------------------------
' Parameter 1 : (String) "SQUARE_VOLUME_VELOCITY"
' Parameter 2 : (String) "Default value"
' Parameter 3 : (String) "Unlocked"
' Parameter 4 : (Boolean) False
'--------------------------------------------------

long884 = settingRepository1.GetAttr("SQUARE_VOLUME_VELOCITY_Large")
'--------------------------------------------------
' Parameter 1 : (String) "SQUARE_VOLUME_VELOCITY_Large"
' Returned value : (Variant) (Long) 1
'--------------------------------------------------

Dim bSTR1767
bSTR1767 = ""
Dim bSTR1768
bSTR1768 = ""
Dim boolean884
settingRepository1.GetAttrInfo "SQUARE_VOLUME_VELOCITY_Large", bSTR1767, bSTR1768, boolean884
'--------------------------------------------------
' Parameter 1 : (String) "SQUARE_VOLUME_VELOCITY_Large"
' Parameter 2 : (String) "Default value"
' Parameter 3 : (String) "Unlocked"
' Parameter 4 : (Boolean) False
'--------------------------------------------------

long885 = settingRepository1.GetAttr("SQUARE_VOLUME_VELOCITY_ExtraLarge")
'--------------------------------------------------
' Parameter 1 : (String) "SQUARE_VOLUME_VELOCITY_ExtraLarge"
' Returned value : (Variant) (Long) 1
'--------------------------------------------------

Dim bSTR1769
bSTR1769 = ""
Dim bSTR1770
bSTR1770 = ""
Dim boolean885
settingRepository1.GetAttrInfo "SQUARE_VOLUME_VELOCITY_ExtraLarge", bSTR1769, bSTR1770, boolean885
'--------------------------------------------------
' Parameter 1 : (String) "SQUARE_VOLUME_VELOCITY_ExtraLarge"
' Parameter 2 : (String) "Default value"
' Parameter 3 : (String) "Unlocked"
' Parameter 4 : (Boolean) False
'--------------------------------------------------

long886 = settingRepository1.GetAttr("SQUARE_VOLUME_VELOCITY_Small")
'--------------------------------------------------
' Parameter 1 : (String) "SQUARE_VOLUME_VELOCITY_Small"
' Returned value : (Variant) (Long) 1
'--------------------------------------------------

Dim bSTR1771
bSTR1771 = ""
Dim bSTR1772
bSTR1772 = ""
Dim boolean886
settingRepository1.GetAttrInfo "SQUARE_VOLUME_VELOCITY_Small", bSTR1771, bSTR1772, boolean886
'--------------------------------------------------
' Parameter 1 : (String) "SQUARE_VOLUME_VELOCITY_Small"
' Parameter 2 : (String) "Default value"
' Parameter 3 : (String) "Unlocked"
' Parameter 4 : (Boolean) False
'--------------------------------------------------

long887 = settingRepository1.GetAttr("SQUARE_VOLUME_VELOCITY_ExtraSmall")
'--------------------------------------------------
' Parameter 1 : (String) "SQUARE_VOLUME_VELOCITY_ExtraSmall"
' Returned value : (Variant) (Long) 1
'--------------------------------------------------

Dim bSTR1773
bSTR1773 = ""
Dim bSTR1774
bSTR1774 = ""
Dim boolean887
settingRepository1.GetAttrInfo "SQUARE_VOLUME_VELOCITY_ExtraSmall", bSTR1773, bSTR1774, boolean887
'--------------------------------------------------
' Parameter 1 : (String) "SQUARE_VOLUME_VELOCITY_ExtraSmall"
' Parameter 2 : (String) "Default value"
' Parameter 3 : (String) "Unlocked"
' Parameter 4 : (Boolean) False
'--------------------------------------------------

long888 = settingRepository1.GetAttr("SQUARE_VOLUME_VELOCITY_Nanometric")
'--------------------------------------------------
' Parameter 1 : (String) "SQUARE_VOLUME_VELOCITY_Nanometric"
' Returned value : (Variant) (Long) 1
'--------------------------------------------------

Dim bSTR1775
bSTR1775 = ""
Dim bSTR1776
bSTR1776 = ""
Dim boolean888
settingRepository1.GetAttrInfo "SQUARE_VOLUME_VELOCITY_Nanometric", bSTR1775, bSTR1776, boolean888
'--------------------------------------------------
' Parameter 1 : (String) "SQUARE_VOLUME_VELOCITY_Nanometric"
' Parameter 2 : (String) "Default value"
' Parameter 3 : (String) "Unlocked"
' Parameter 4 : (Boolean) False
'--------------------------------------------------

long889 = settingRepository1.GetAttr("SOLID_ANGLE")
'--------------------------------------------------
' Parameter 1 : (String) "SOLID_ANGLE"
' Returned value : (Variant) (Long) 1
'--------------------------------------------------

Dim bSTR1777
bSTR1777 = ""
Dim bSTR1778
bSTR1778 = ""
Dim boolean889
settingRepository1.GetAttrInfo "SOLID_ANGLE", bSTR1777, bSTR1778, boolean889
'--------------------------------------------------
' Parameter 1 : (String) "SOLID_ANGLE"
' Parameter 2 : (String) "Default value"
' Parameter 3 : (String) "Unlocked"
' Parameter 4 : (Boolean) False
'--------------------------------------------------

long890 = settingRepository1.GetAttr("SOLID_ANGLE_Large")
'--------------------------------------------------
' Parameter 1 : (String) "SOLID_ANGLE_Large"
' Returned value : (Variant) (Long) 1
'--------------------------------------------------

Dim bSTR1779
bSTR1779 = ""
Dim bSTR1780
bSTR1780 = ""
Dim boolean890
settingRepository1.GetAttrInfo "SOLID_ANGLE_Large", bSTR1779, bSTR1780, boolean890
'--------------------------------------------------
' Parameter 1 : (String) "SOLID_ANGLE_Large"
' Parameter 2 : (String) "Default value"
' Parameter 3 : (String) "Unlocked"
' Parameter 4 : (Boolean) False
'--------------------------------------------------

long891 = settingRepository1.GetAttr("SOLID_ANGLE_ExtraLarge")
'--------------------------------------------------
' Parameter 1 : (String) "SOLID_ANGLE_ExtraLarge"
' Returned value : (Variant) (Long) 1
'--------------------------------------------------

Dim bSTR1781
bSTR1781 = ""
Dim bSTR1782
bSTR1782 = ""
Dim boolean891
settingRepository1.GetAttrInfo "SOLID_ANGLE_ExtraLarge", bSTR1781, bSTR1782, boolean891
'--------------------------------------------------
' Parameter 1 : (String) "SOLID_ANGLE_ExtraLarge"
' Parameter 2 : (String) "Default value"
' Parameter 3 : (String) "Unlocked"
' Parameter 4 : (Boolean) False
'--------------------------------------------------

long892 = settingRepository1.GetAttr("SOLID_ANGLE_Small")
'--------------------------------------------------
' Parameter 1 : (String) "SOLID_ANGLE_Small"
' Returned value : (Variant) (Long) 1
'--------------------------------------------------

Dim bSTR1783
bSTR1783 = ""
Dim bSTR1784
bSTR1784 = ""
Dim boolean892
settingRepository1.GetAttrInfo "SOLID_ANGLE_Small", bSTR1783, bSTR1784, boolean892
'--------------------------------------------------
' Parameter 1 : (String) "SOLID_ANGLE_Small"
' Parameter 2 : (String) "Default value"
' Parameter 3 : (String) "Unlocked"
' Parameter 4 : (Boolean) False
'--------------------------------------------------

long893 = settingRepository1.GetAttr("SOLID_ANGLE_ExtraSmall")
'--------------------------------------------------
' Parameter 1 : (String) "SOLID_ANGLE_ExtraSmall"
' Returned value : (Variant) (Long) 1
'--------------------------------------------------

Dim bSTR1785
bSTR1785 = ""
Dim bSTR1786
bSTR1786 = ""
Dim boolean893
settingRepository1.GetAttrInfo "SOLID_ANGLE_ExtraSmall", bSTR1785, bSTR1786, boolean893
'--------------------------------------------------
' Parameter 1 : (String) "SOLID_ANGLE_ExtraSmall"
' Parameter 2 : (String) "Default value"
' Parameter 3 : (String) "Unlocked"
' Parameter 4 : (Boolean) False
'--------------------------------------------------

long894 = settingRepository1.GetAttr("SOLID_ANGLE_Nanometric")
'--------------------------------------------------
' Parameter 1 : (String) "SOLID_ANGLE_Nanometric"
' Returned value : (Variant) (Long) 1
'--------------------------------------------------

Dim bSTR1787
bSTR1787 = ""
Dim bSTR1788
bSTR1788 = ""
Dim boolean894
settingRepository1.GetAttrInfo "SOLID_ANGLE_Nanometric", bSTR1787, bSTR1788, boolean894
'--------------------------------------------------
' Parameter 1 : (String) "SOLID_ANGLE_Nanometric"
' Parameter 2 : (String) "Default value"
' Parameter 3 : (String) "Unlocked"
' Parameter 4 : (Boolean) False
'--------------------------------------------------

long895 = settingRepository1.GetAttr("VOLUME_ACCELERATION_OVER_FORCE")
'--------------------------------------------------
' Parameter 1 : (String) "VOLUME_ACCELERATION_OVER_FORCE"
' Returned value : (Variant) (Long) 1
'--------------------------------------------------

Dim bSTR1789
bSTR1789 = ""
Dim bSTR1790
bSTR1790 = ""
Dim boolean895
settingRepository1.GetAttrInfo "VOLUME_ACCELERATION_OVER_FORCE", bSTR1789, bSTR1790, boolean895
'--------------------------------------------------
' Parameter 1 : (String) "VOLUME_ACCELERATION_OVER_FORCE"
' Parameter 2 : (String) "Default value"
' Parameter 3 : (String) "Unlocked"
' Parameter 4 : (Boolean) False
'--------------------------------------------------

long896 = settingRepository1.GetAttr("VOLUME_ACCELERATION_OVER_FORCE_Large")
'--------------------------------------------------
' Parameter 1 : (String) "VOLUME_ACCELERATION_OVER_FORCE_Large"
' Returned value : (Variant) (Long) 1
'--------------------------------------------------

Dim bSTR1791
bSTR1791 = ""
Dim bSTR1792
bSTR1792 = ""
Dim boolean896
settingRepository1.GetAttrInfo "VOLUME_ACCELERATION_OVER_FORCE_Large", bSTR1791, bSTR1792, boolean896
'--------------------------------------------------
' Parameter 1 : (String) "VOLUME_ACCELERATION_OVER_FORCE_Large"
' Parameter 2 : (String) "Default value"
' Parameter 3 : (String) "Unlocked"
' Parameter 4 : (Boolean) False
'--------------------------------------------------

long897 = settingRepository1.GetAttr("VOLUME_ACCELERATION_OVER_FORCE_ExtraLarge")
'--------------------------------------------------
' Parameter 1 : (String) "VOLUME_ACCELERATION_OVER_FORCE_ExtraLarge"
' Returned value : (Variant) (Long) 1
'--------------------------------------------------

Dim bSTR1793
bSTR1793 = ""
Dim bSTR1794
bSTR1794 = ""
Dim boolean897
settingRepository1.GetAttrInfo "VOLUME_ACCELERATION_OVER_FORCE_ExtraLarge", bSTR1793, bSTR1794, boolean897
'--------------------------------------------------
' Parameter 1 : (String) "VOLUME_ACCELERATION_OVER_FORCE_ExtraLarge"
' Parameter 2 : (String) "Default value"
' Parameter 3 : (String) "Unlocked"
' Parameter 4 : (Boolean) False
'--------------------------------------------------

long898 = settingRepository1.GetAttr("VOLUME_ACCELERATION_OVER_FORCE_Small")
'--------------------------------------------------
' Parameter 1 : (String) "VOLUME_ACCELERATION_OVER_FORCE_Small"
' Returned value : (Variant) (Long) 1
'--------------------------------------------------

Dim bSTR1795
bSTR1795 = ""
Dim bSTR1796
bSTR1796 = ""
Dim boolean898
settingRepository1.GetAttrInfo "VOLUME_ACCELERATION_OVER_FORCE_Small", bSTR1795, bSTR1796, boolean898
'--------------------------------------------------
' Parameter 1 : (String) "VOLUME_ACCELERATION_OVER_FORCE_Small"
' Parameter 2 : (String) "Default value"
' Parameter 3 : (String) "Unlocked"
' Parameter 4 : (Boolean) False
'--------------------------------------------------

long899 = settingRepository1.GetAttr("VOLUME_ACCELERATION_OVER_FORCE_ExtraSmall")
'--------------------------------------------------
' Parameter 1 : (String) "VOLUME_ACCELERATION_OVER_FORCE_ExtraSmall"
' Returned value : (Variant) (Long) 1
'--------------------------------------------------

Dim bSTR1797
bSTR1797 = ""
Dim bSTR1798
bSTR1798 = ""
Dim boolean899
settingRepository1.GetAttrInfo "VOLUME_ACCELERATION_OVER_FORCE_ExtraSmall", bSTR1797, bSTR1798, boolean899
'--------------------------------------------------
' Parameter 1 : (String) "VOLUME_ACCELERATION_OVER_FORCE_ExtraSmall"
' Parameter 2 : (String) "Default value"
' Parameter 3 : (String) "Unlocked"
' Parameter 4 : (Boolean) False
'--------------------------------------------------

long900 = settingRepository1.GetAttr("VOLUME_ACCELERATION_OVER_FORCE_Nanometric")
'--------------------------------------------------
' Parameter 1 : (String) "VOLUME_ACCELERATION_OVER_FORCE_Nanometric"
' Returned value : (Variant) (Long) 1
'--------------------------------------------------

Dim bSTR1799
bSTR1799 = ""
Dim bSTR1800
bSTR1800 = ""
Dim boolean900
settingRepository1.GetAttrInfo "VOLUME_ACCELERATION_OVER_FORCE_Nanometric", bSTR1799, bSTR1800, boolean900
'--------------------------------------------------
' Parameter 1 : (String) "VOLUME_ACCELERATION_OVER_FORCE_Nanometric"
' Parameter 2 : (String) "Default value"
' Parameter 3 : (String) "Unlocked"
' Parameter 4 : (Boolean) False
'--------------------------------------------------

long901 = settingRepository1.GetAttr("VOLUME_ACCELERATION_OVER_MOMENT")
'--------------------------------------------------
' Parameter 1 : (String) "VOLUME_ACCELERATION_OVER_MOMENT"
' Returned value : (Variant) (Long) 1
'--------------------------------------------------

Dim bSTR1801
bSTR1801 = ""
Dim bSTR1802
bSTR1802 = ""
Dim boolean901
settingRepository1.GetAttrInfo "VOLUME_ACCELERATION_OVER_MOMENT", bSTR1801, bSTR1802, boolean901
'--------------------------------------------------
' Parameter 1 : (String) "VOLUME_ACCELERATION_OVER_MOMENT"
' Parameter 2 : (String) "Default value"
' Parameter 3 : (String) "Unlocked"
' Parameter 4 : (Boolean) False
'--------------------------------------------------

long902 = settingRepository1.GetAttr("VOLUME_ACCELERATION_OVER_MOMENT_Large")
'--------------------------------------------------
' Parameter 1 : (String) "VOLUME_ACCELERATION_OVER_MOMENT_Large"
' Returned value : (Variant) (Long) 1
'--------------------------------------------------

Dim bSTR1803
bSTR1803 = ""
Dim bSTR1804
bSTR1804 = ""
Dim boolean902
settingRepository1.GetAttrInfo "VOLUME_ACCELERATION_OVER_MOMENT_Large", bSTR1803, bSTR1804, boolean902
'--------------------------------------------------
' Parameter 1 : (String) "VOLUME_ACCELERATION_OVER_MOMENT_Large"
' Parameter 2 : (String) "Default value"
' Parameter 3 : (String) "Unlocked"
' Parameter 4 : (Boolean) False
'--------------------------------------------------

long903 = settingRepository1.GetAttr("VOLUME_ACCELERATION_OVER_MOMENT_ExtraLarge")
'--------------------------------------------------
' Parameter 1 : (String) "VOLUME_ACCELERATION_OVER_MOMENT_ExtraLarge"
' Returned value : (Variant) (Long) 1
'--------------------------------------------------

Dim bSTR1805
bSTR1805 = ""
Dim bSTR1806
bSTR1806 = ""
Dim boolean903
settingRepository1.GetAttrInfo "VOLUME_ACCELERATION_OVER_MOMENT_ExtraLarge", bSTR1805, bSTR1806, boolean903
'--------------------------------------------------
' Parameter 1 : (String) "VOLUME_ACCELERATION_OVER_MOMENT_ExtraLarge"
' Parameter 2 : (String) "Default value"
' Parameter 3 : (String) "Unlocked"
' Parameter 4 : (Boolean) False
'--------------------------------------------------

long904 = settingRepository1.GetAttr("VOLUME_ACCELERATION_OVER_MOMENT_Small")
'--------------------------------------------------
' Parameter 1 : (String) "VOLUME_ACCELERATION_OVER_MOMENT_Small"
' Returned value : (Variant) (Long) 1
'--------------------------------------------------

Dim bSTR1807
bSTR1807 = ""
Dim bSTR1808
bSTR1808 = ""
Dim boolean904
settingRepository1.GetAttrInfo "VOLUME_ACCELERATION_OVER_MOMENT_Small", bSTR1807, bSTR1808, boolean904
'--------------------------------------------------
' Parameter 1 : (String) "VOLUME_ACCELERATION_OVER_MOMENT_Small"
' Parameter 2 : (String) "Default value"
' Parameter 3 : (String) "Unlocked"
' Parameter 4 : (Boolean) False
'--------------------------------------------------

long905 = settingRepository1.GetAttr("VOLUME_ACCELERATION_OVER_MOMENT_ExtraSmall")
'--------------------------------------------------
' Parameter 1 : (String) "VOLUME_ACCELERATION_OVER_MOMENT_ExtraSmall"
' Returned value : (Variant) (Long) 1
'--------------------------------------------------

Dim bSTR1809
bSTR1809 = ""
Dim bSTR1810
bSTR1810 = ""
Dim boolean905
settingRepository1.GetAttrInfo "VOLUME_ACCELERATION_OVER_MOMENT_ExtraSmall", bSTR1809, bSTR1810, boolean905
'--------------------------------------------------
' Parameter 1 : (String) "VOLUME_ACCELERATION_OVER_MOMENT_ExtraSmall"
' Parameter 2 : (String) "Default value"
' Parameter 3 : (String) "Unlocked"
' Parameter 4 : (Boolean) False
'--------------------------------------------------

long906 = settingRepository1.GetAttr("VOLUME_ACCELERATION_OVER_MOMENT_Nanometric")
'--------------------------------------------------
' Parameter 1 : (String) "VOLUME_ACCELERATION_OVER_MOMENT_Nanometric"
' Returned value : (Variant) (Long) 1
'--------------------------------------------------

Dim bSTR1811
bSTR1811 = ""
Dim bSTR1812
bSTR1812 = ""
Dim boolean906
settingRepository1.GetAttrInfo "VOLUME_ACCELERATION_OVER_MOMENT_Nanometric", bSTR1811, bSTR1812, boolean906
'--------------------------------------------------
' Parameter 1 : (String) "VOLUME_ACCELERATION_OVER_MOMENT_Nanometric"
' Parameter 2 : (String) "Default value"
' Parameter 3 : (String) "Unlocked"
' Parameter 4 : (Boolean) False
'--------------------------------------------------

long907 = settingRepository1.GetAttr("VOLUME_VELOCITY_OVER_FORCE")
'--------------------------------------------------
' Parameter 1 : (String) "VOLUME_VELOCITY_OVER_FORCE"
' Returned value : (Variant) (Long) 1
'--------------------------------------------------

Dim bSTR1813
bSTR1813 = ""
Dim bSTR1814
bSTR1814 = ""
Dim boolean907
settingRepository1.GetAttrInfo "VOLUME_VELOCITY_OVER_FORCE", bSTR1813, bSTR1814, boolean907
'--------------------------------------------------
' Parameter 1 : (String) "VOLUME_VELOCITY_OVER_FORCE"
' Parameter 2 : (String) "Default value"
' Parameter 3 : (String) "Unlocked"
' Parameter 4 : (Boolean) False
'--------------------------------------------------

long908 = settingRepository1.GetAttr("VOLUME_VELOCITY_OVER_FORCE_Large")
'--------------------------------------------------
' Parameter 1 : (String) "VOLUME_VELOCITY_OVER_FORCE_Large"
' Returned value : (Variant) (Long) 1
'--------------------------------------------------

Dim bSTR1815
bSTR1815 = ""
Dim bSTR1816
bSTR1816 = ""
Dim boolean908
settingRepository1.GetAttrInfo "VOLUME_VELOCITY_OVER_FORCE_Large", bSTR1815, bSTR1816, boolean908
'--------------------------------------------------
' Parameter 1 : (String) "VOLUME_VELOCITY_OVER_FORCE_Large"
' Parameter 2 : (String) "Default value"
' Parameter 3 : (String) "Unlocked"
' Parameter 4 : (Boolean) False
'--------------------------------------------------

long909 = settingRepository1.GetAttr("VOLUME_VELOCITY_OVER_FORCE_ExtraLarge")
'--------------------------------------------------
' Parameter 1 : (String) "VOLUME_VELOCITY_OVER_FORCE_ExtraLarge"
' Returned value : (Variant) (Long) 1
'--------------------------------------------------

Dim bSTR1817
bSTR1817 = ""
Dim bSTR1818
bSTR1818 = ""
Dim boolean909
settingRepository1.GetAttrInfo "VOLUME_VELOCITY_OVER_FORCE_ExtraLarge", bSTR1817, bSTR1818, boolean909
'--------------------------------------------------
' Parameter 1 : (String) "VOLUME_VELOCITY_OVER_FORCE_ExtraLarge"
' Parameter 2 : (String) "Default value"
' Parameter 3 : (String) "Unlocked"
' Parameter 4 : (Boolean) False
'--------------------------------------------------

long910 = settingRepository1.GetAttr("VOLUME_VELOCITY_OVER_FORCE_Small")
'--------------------------------------------------
' Parameter 1 : (String) "VOLUME_VELOCITY_OVER_FORCE_Small"
' Returned value : (Variant) (Long) 1
'--------------------------------------------------

Dim bSTR1819
bSTR1819 = ""
Dim bSTR1820
bSTR1820 = ""
Dim boolean910
settingRepository1.GetAttrInfo "VOLUME_VELOCITY_OVER_FORCE_Small", bSTR1819, bSTR1820, boolean910
'--------------------------------------------------
' Parameter 1 : (String) "VOLUME_VELOCITY_OVER_FORCE_Small"
' Parameter 2 : (String) "Default value"
' Parameter 3 : (String) "Unlocked"
' Parameter 4 : (Boolean) False
'--------------------------------------------------

long911 = settingRepository1.GetAttr("VOLUME_VELOCITY_OVER_FORCE_ExtraSmall")
'--------------------------------------------------
' Parameter 1 : (String) "VOLUME_VELOCITY_OVER_FORCE_ExtraSmall"
' Returned value : (Variant) (Long) 1
'--------------------------------------------------

Dim bSTR1821
bSTR1821 = ""
Dim bSTR1822
bSTR1822 = ""
Dim boolean911
settingRepository1.GetAttrInfo "VOLUME_VELOCITY_OVER_FORCE_ExtraSmall", bSTR1821, bSTR1822, boolean911
'--------------------------------------------------
' Parameter 1 : (String) "VOLUME_VELOCITY_OVER_FORCE_ExtraSmall"
' Parameter 2 : (String) "Default value"
' Parameter 3 : (String) "Unlocked"
' Parameter 4 : (Boolean) False
'--------------------------------------------------

long912 = settingRepository1.GetAttr("VOLUME_VELOCITY_OVER_FORCE_Nanometric")
'--------------------------------------------------
' Parameter 1 : (String) "VOLUME_VELOCITY_OVER_FORCE_Nanometric"
' Returned value : (Variant) (Long) 1
'--------------------------------------------------

Dim bSTR1823
bSTR1823 = ""
Dim bSTR1824
bSTR1824 = ""
Dim boolean912
settingRepository1.GetAttrInfo "VOLUME_VELOCITY_OVER_FORCE_Nanometric", bSTR1823, bSTR1824, boolean912
'--------------------------------------------------
' Parameter 1 : (String) "VOLUME_VELOCITY_OVER_FORCE_Nanometric"
' Parameter 2 : (String) "Default value"
' Parameter 3 : (String) "Unlocked"
' Parameter 4 : (Boolean) False
'--------------------------------------------------

long913 = settingRepository1.GetAttr("VOLUME_VELOCITY_OVER_MOMENT")
'--------------------------------------------------
' Parameter 1 : (String) "VOLUME_VELOCITY_OVER_MOMENT"
' Returned value : (Variant) (Long) 1
'--------------------------------------------------

Dim bSTR1825
bSTR1825 = ""
Dim bSTR1826
bSTR1826 = ""
Dim boolean913
settingRepository1.GetAttrInfo "VOLUME_VELOCITY_OVER_MOMENT", bSTR1825, bSTR1826, boolean913
'--------------------------------------------------
' Parameter 1 : (String) "VOLUME_VELOCITY_OVER_MOMENT"
' Parameter 2 : (String) "Default value"
' Parameter 3 : (String) "Unlocked"
' Parameter 4 : (Boolean) False
'--------------------------------------------------

long914 = settingRepository1.GetAttr("VOLUME_VELOCITY_OVER_MOMENT_Large")
'--------------------------------------------------
' Parameter 1 : (String) "VOLUME_VELOCITY_OVER_MOMENT_Large"
' Returned value : (Variant) (Long) 1
'--------------------------------------------------

Dim bSTR1827
bSTR1827 = ""
Dim bSTR1828
bSTR1828 = ""
Dim boolean914
settingRepository1.GetAttrInfo "VOLUME_VELOCITY_OVER_MOMENT_Large", bSTR1827, bSTR1828, boolean914
'--------------------------------------------------
' Parameter 1 : (String) "VOLUME_VELOCITY_OVER_MOMENT_Large"
' Parameter 2 : (String) "Default value"
' Parameter 3 : (String) "Unlocked"
' Parameter 4 : (Boolean) False
'--------------------------------------------------

long915 = settingRepository1.GetAttr("VOLUME_VELOCITY_OVER_MOMENT_ExtraLarge")
'--------------------------------------------------
' Parameter 1 : (String) "VOLUME_VELOCITY_OVER_MOMENT_ExtraLarge"
' Returned value : (Variant) (Long) 1
'--------------------------------------------------

Dim bSTR1829
bSTR1829 = ""
Dim bSTR1830
bSTR1830 = ""
Dim boolean915
settingRepository1.GetAttrInfo "VOLUME_VELOCITY_OVER_MOMENT_ExtraLarge", bSTR1829, bSTR1830, boolean915
'--------------------------------------------------
' Parameter 1 : (String) "VOLUME_VELOCITY_OVER_MOMENT_ExtraLarge"
' Parameter 2 : (String) "Default value"
' Parameter 3 : (String) "Unlocked"
' Parameter 4 : (Boolean) False
'--------------------------------------------------

long916 = settingRepository1.GetAttr("VOLUME_VELOCITY_OVER_MOMENT_Small")
'--------------------------------------------------
' Parameter 1 : (String) "VOLUME_VELOCITY_OVER_MOMENT_Small"
' Returned value : (Variant) (Long) 1
'--------------------------------------------------

Dim bSTR1831
bSTR1831 = ""
Dim bSTR1832
bSTR1832 = ""
Dim boolean916
settingRepository1.GetAttrInfo "VOLUME_VELOCITY_OVER_MOMENT_Small", bSTR1831, bSTR1832, boolean916
'--------------------------------------------------
' Parameter 1 : (String) "VOLUME_VELOCITY_OVER_MOMENT_Small"
' Parameter 2 : (String) "Default value"
' Parameter 3 : (String) "Unlocked"
' Parameter 4 : (Boolean) False
'--------------------------------------------------

long917 = settingRepository1.GetAttr("VOLUME_VELOCITY_OVER_MOMENT_ExtraSmall")
'--------------------------------------------------
' Parameter 1 : (String) "VOLUME_VELOCITY_OVER_MOMENT_ExtraSmall"
' Returned value : (Variant) (Long) 1
'--------------------------------------------------

Dim bSTR1833
bSTR1833 = ""
Dim bSTR1834
bSTR1834 = ""
Dim boolean917
settingRepository1.GetAttrInfo "VOLUME_VELOCITY_OVER_MOMENT_ExtraSmall", bSTR1833, bSTR1834, boolean917
'--------------------------------------------------
' Parameter 1 : (String) "VOLUME_VELOCITY_OVER_MOMENT_ExtraSmall"
' Parameter 2 : (String) "Default value"
' Parameter 3 : (String) "Unlocked"
' Parameter 4 : (Boolean) False
'--------------------------------------------------

long918 = settingRepository1.GetAttr("VOLUME_VELOCITY_OVER_MOMENT_Nanometric")
'--------------------------------------------------
' Parameter 1 : (String) "VOLUME_VELOCITY_OVER_MOMENT_Nanometric"
' Returned value : (Variant) (Long) 1
'--------------------------------------------------

Dim bSTR1835
bSTR1835 = ""
Dim bSTR1836
bSTR1836 = ""
Dim boolean918
settingRepository1.GetAttrInfo "VOLUME_VELOCITY_OVER_MOMENT_Nanometric", bSTR1835, bSTR1836, boolean918
'--------------------------------------------------
' Parameter 1 : (String) "VOLUME_VELOCITY_OVER_MOMENT_Nanometric"
' Parameter 2 : (String) "Default value"
' Parameter 3 : (String) "Unlocked"
' Parameter 4 : (Boolean) False
'--------------------------------------------------

long919 = settingRepository1.GetAttr("VOLUME_ACCELERATION_OVER_ACCELERATION")
'--------------------------------------------------
' Parameter 1 : (String) "VOLUME_ACCELERATION_OVER_ACCELERATION"
' Returned value : (Variant) (Long) 1
'--------------------------------------------------

Dim bSTR1837
bSTR1837 = ""
Dim bSTR1838
bSTR1838 = ""
Dim boolean919
settingRepository1.GetAttrInfo "VOLUME_ACCELERATION_OVER_ACCELERATION", bSTR1837, bSTR1838, boolean919
'--------------------------------------------------
' Parameter 1 : (String) "VOLUME_ACCELERATION_OVER_ACCELERATION"
' Parameter 2 : (String) "Default value"
' Parameter 3 : (String) "Unlocked"
' Parameter 4 : (Boolean) False
'--------------------------------------------------

long920 = settingRepository1.GetAttr("VOLUME_ACCELERATION_OVER_ACCELERATION_Large")
'--------------------------------------------------
' Parameter 1 : (String) "VOLUME_ACCELERATION_OVER_ACCELERATION_Large"
' Returned value : (Variant) (Long) 1
'--------------------------------------------------

Dim bSTR1839
bSTR1839 = ""
Dim bSTR1840
bSTR1840 = ""
Dim boolean920
settingRepository1.GetAttrInfo "VOLUME_ACCELERATION_OVER_ACCELERATION_Large", bSTR1839, bSTR1840, boolean920
'--------------------------------------------------
' Parameter 1 : (String) "VOLUME_ACCELERATION_OVER_ACCELERATION_Large"
' Parameter 2 : (String) "Default value"
' Parameter 3 : (String) "Unlocked"
' Parameter 4 : (Boolean) False
'--------------------------------------------------

long921 = settingRepository1.GetAttr("VOLUME_ACCELERATION_OVER_ACCELERATION_ExtraLarge")
'--------------------------------------------------
' Parameter 1 : (String) "VOLUME_ACCELERATION_OVER_ACCELERATION_ExtraLarge"
' Returned value : (Variant) (Long) 1
'--------------------------------------------------

Dim bSTR1841
bSTR1841 = ""
Dim bSTR1842
bSTR1842 = ""
Dim boolean921
settingRepository1.GetAttrInfo "VOLUME_ACCELERATION_OVER_ACCELERATION_ExtraLarge", bSTR1841, bSTR1842, boolean921
'--------------------------------------------------
' Parameter 1 : (String) "VOLUME_ACCELERATION_OVER_ACCELERATION_ExtraLarge"
' Parameter 2 : (String) "Default value"
' Parameter 3 : (String) "Unlocked"
' Parameter 4 : (Boolean) False
'--------------------------------------------------

long922 = settingRepository1.GetAttr("VOLUME_ACCELERATION_OVER_ACCELERATION_Small")
'--------------------------------------------------
' Parameter 1 : (String) "VOLUME_ACCELERATION_OVER_ACCELERATION_Small"
' Returned value : (Variant) (Long) 1
'--------------------------------------------------

Dim bSTR1843
bSTR1843 = ""
Dim bSTR1844
bSTR1844 = ""
Dim boolean922
settingRepository1.GetAttrInfo "VOLUME_ACCELERATION_OVER_ACCELERATION_Small", bSTR1843, bSTR1844, boolean922
'--------------------------------------------------
' Parameter 1 : (String) "VOLUME_ACCELERATION_OVER_ACCELERATION_Small"
' Parameter 2 : (String) "Default value"
' Parameter 3 : (String) "Unlocked"
' Parameter 4 : (Boolean) False
'--------------------------------------------------

long923 = settingRepository1.GetAttr("VOLUME_ACCELERATION_OVER_ACCELERATION_ExtraSmall")
'--------------------------------------------------
' Parameter 1 : (String) "VOLUME_ACCELERATION_OVER_ACCELERATION_ExtraSmall"
' Returned value : (Variant) (Long) 1
'--------------------------------------------------

Dim bSTR1845
bSTR1845 = ""
Dim bSTR1846
bSTR1846 = ""
Dim boolean923
settingRepository1.GetAttrInfo "VOLUME_ACCELERATION_OVER_ACCELERATION_ExtraSmall", bSTR1845, bSTR1846, boolean923
'--------------------------------------------------
' Parameter 1 : (String) "VOLUME_ACCELERATION_OVER_ACCELERATION_ExtraSmall"
' Parameter 2 : (String) "Default value"
' Parameter 3 : (String) "Unlocked"
' Parameter 4 : (Boolean) False
'--------------------------------------------------

long924 = settingRepository1.GetAttr("VOLUME_ACCELERATION_OVER_ACCELERATION_Nanometric")
'--------------------------------------------------
' Parameter 1 : (String) "VOLUME_ACCELERATION_OVER_ACCELERATION_Nanometric"
' Returned value : (Variant) (Long) 1
'--------------------------------------------------

Dim bSTR1847
bSTR1847 = ""
Dim bSTR1848
bSTR1848 = ""
Dim boolean924
settingRepository1.GetAttrInfo "VOLUME_ACCELERATION_OVER_ACCELERATION_Nanometric", bSTR1847, bSTR1848, boolean924
'--------------------------------------------------
' Parameter 1 : (String) "VOLUME_ACCELERATION_OVER_ACCELERATION_Nanometric"
' Parameter 2 : (String) "Default value"
' Parameter 3 : (String) "Unlocked"
' Parameter 4 : (Boolean) False
'--------------------------------------------------

long925 = settingRepository1.GetAttr("VOLUME_VELOCITY_OVER_ACCELERATION")
'--------------------------------------------------
' Parameter 1 : (String) "VOLUME_VELOCITY_OVER_ACCELERATION"
' Returned value : (Variant) (Long) 1
'--------------------------------------------------

Dim bSTR1849
bSTR1849 = ""
Dim bSTR1850
bSTR1850 = ""
Dim boolean925
settingRepository1.GetAttrInfo "VOLUME_VELOCITY_OVER_ACCELERATION", bSTR1849, bSTR1850, boolean925
'--------------------------------------------------
' Parameter 1 : (String) "VOLUME_VELOCITY_OVER_ACCELERATION"
' Parameter 2 : (String) "Default value"
' Parameter 3 : (String) "Unlocked"
' Parameter 4 : (Boolean) False
'--------------------------------------------------

long926 = settingRepository1.GetAttr("VOLUME_VELOCITY_OVER_ACCELERATION_Large")
'--------------------------------------------------
' Parameter 1 : (String) "VOLUME_VELOCITY_OVER_ACCELERATION_Large"
' Returned value : (Variant) (Long) 1
'--------------------------------------------------

Dim bSTR1851
bSTR1851 = ""
Dim bSTR1852
bSTR1852 = ""
Dim boolean926
settingRepository1.GetAttrInfo "VOLUME_VELOCITY_OVER_ACCELERATION_Large", bSTR1851, bSTR1852, boolean926
'--------------------------------------------------
' Parameter 1 : (String) "VOLUME_VELOCITY_OVER_ACCELERATION_Large"
' Parameter 2 : (String) "Default value"
' Parameter 3 : (String) "Unlocked"
' Parameter 4 : (Boolean) False
'--------------------------------------------------

long927 = settingRepository1.GetAttr("VOLUME_VELOCITY_OVER_ACCELERATION_ExtraLarge")
'--------------------------------------------------
' Parameter 1 : (String) "VOLUME_VELOCITY_OVER_ACCELERATION_ExtraLarge"
' Returned value : (Variant) (Long) 1
'--------------------------------------------------

Dim bSTR1853
bSTR1853 = ""
Dim bSTR1854
bSTR1854 = ""
Dim boolean927
settingRepository1.GetAttrInfo "VOLUME_VELOCITY_OVER_ACCELERATION_ExtraLarge", bSTR1853, bSTR1854, boolean927
'--------------------------------------------------
' Parameter 1 : (String) "VOLUME_VELOCITY_OVER_ACCELERATION_ExtraLarge"
' Parameter 2 : (String) "Default value"
' Parameter 3 : (String) "Unlocked"
' Parameter 4 : (Boolean) False
'--------------------------------------------------

long928 = settingRepository1.GetAttr("VOLUME_VELOCITY_OVER_ACCELERATION_Small")
'--------------------------------------------------
' Parameter 1 : (String) "VOLUME_VELOCITY_OVER_ACCELERATION_Small"
' Returned value : (Variant) (Long) 1
'--------------------------------------------------

Dim bSTR1855
bSTR1855 = ""
Dim bSTR1856
bSTR1856 = ""
Dim boolean928
settingRepository1.GetAttrInfo "VOLUME_VELOCITY_OVER_ACCELERATION_Small", bSTR1855, bSTR1856, boolean928
'--------------------------------------------------
' Parameter 1 : (String) "VOLUME_VELOCITY_OVER_ACCELERATION_Small"
' Parameter 2 : (String) "Default value"
' Parameter 3 : (String) "Unlocked"
' Parameter 4 : (Boolean) False
'--------------------------------------------------

long929 = settingRepository1.GetAttr("VOLUME_VELOCITY_OVER_ACCELERATION_ExtraSmall")
'--------------------------------------------------
' Parameter 1 : (String) "VOLUME_VELOCITY_OVER_ACCELERATION_ExtraSmall"
' Returned value : (Variant) (Long) 1
'--------------------------------------------------

Dim bSTR1857
bSTR1857 = ""
Dim bSTR1858
bSTR1858 = ""
Dim boolean929
settingRepository1.GetAttrInfo "VOLUME_VELOCITY_OVER_ACCELERATION_ExtraSmall", bSTR1857, bSTR1858, boolean929
'--------------------------------------------------
' Parameter 1 : (String) "VOLUME_VELOCITY_OVER_ACCELERATION_ExtraSmall"
' Parameter 2 : (String) "Default value"
' Parameter 3 : (String) "Unlocked"
' Parameter 4 : (Boolean) False
'--------------------------------------------------

long930 = settingRepository1.GetAttr("VOLUME_VELOCITY_OVER_ACCELERATION_Nanometric")
'--------------------------------------------------
' Parameter 1 : (String) "VOLUME_VELOCITY_OVER_ACCELERATION_Nanometric"
' Returned value : (Variant) (Long) 1
'--------------------------------------------------

Dim bSTR1859
bSTR1859 = ""
Dim bSTR1860
bSTR1860 = ""
Dim boolean930
settingRepository1.GetAttrInfo "VOLUME_VELOCITY_OVER_ACCELERATION_Nanometric", bSTR1859, bSTR1860, boolean930
'--------------------------------------------------
' Parameter 1 : (String) "VOLUME_VELOCITY_OVER_ACCELERATION_Nanometric"
' Parameter 2 : (String) "Default value"
' Parameter 3 : (String) "Unlocked"
' Parameter 4 : (Boolean) False
'--------------------------------------------------

long931 = settingRepository1.GetAttr("VOLUME_ACCELERATION_OVER_ROTATIONAL_ACCELERATION")
'--------------------------------------------------
' Parameter 1 : (String) "VOLUME_ACCELERATION_OVER_ROTATIONAL_ACCELERATION"
' Returned value : (Variant) (Long) 1
'--------------------------------------------------

Dim bSTR1861
bSTR1861 = ""
Dim bSTR1862
bSTR1862 = ""
Dim boolean931
settingRepository1.GetAttrInfo "VOLUME_ACCELERATION_OVER_ROTATIONAL_ACCELERATION", bSTR1861, bSTR1862, boolean931
'--------------------------------------------------
' Parameter 1 : (String) "VOLUME_ACCELERATION_OVER_ROTATIONAL_ACCELERATION"
' Parameter 2 : (String) "Default value"
' Parameter 3 : (String) "Unlocked"
' Parameter 4 : (Boolean) False
'--------------------------------------------------

long932 = settingRepository1.GetAttr("VOLUME_ACCELERATION_OVER_ROTATIONAL_ACCELERATION_Large")
'--------------------------------------------------
' Parameter 1 : (String) "VOLUME_ACCELERATION_OVER_ROTATIONAL_ACCELERATION_Large"
' Returned value : (Variant) (Long) 1
'--------------------------------------------------

Dim bSTR1863
bSTR1863 = ""
Dim bSTR1864
bSTR1864 = ""
Dim boolean932
settingRepository1.GetAttrInfo "VOLUME_ACCELERATION_OVER_ROTATIONAL_ACCELERATION_Large", bSTR1863, bSTR1864, boolean932
'--------------------------------------------------
' Parameter 1 : (String) "VOLUME_ACCELERATION_OVER_ROTATIONAL_ACCELERATION_Large"
' Parameter 2 : (String) "Default value"
' Parameter 3 : (String) "Unlocked"
' Parameter 4 : (Boolean) False
'--------------------------------------------------

long933 = settingRepository1.GetAttr("VOLUME_ACCELERATION_OVER_ROTATIONAL_ACCELERATION_ExtraLarge")
'--------------------------------------------------
' Parameter 1 : (String) "VOLUME_ACCELERATION_OVER_ROTATIONAL_ACCELERATION_ExtraLarge"
' Returned value : (Variant) (Long) 1
'--------------------------------------------------

Dim bSTR1865
bSTR1865 = ""
Dim bSTR1866
bSTR1866 = ""
Dim boolean933
settingRepository1.GetAttrInfo "VOLUME_ACCELERATION_OVER_ROTATIONAL_ACCELERATION_ExtraLarge", bSTR1865, bSTR1866, boolean933
'--------------------------------------------------
' Parameter 1 : (String) "VOLUME_ACCELERATION_OVER_ROTATIONAL_ACCELERATION_ExtraLarge"
' Parameter 2 : (String) "Default value"
' Parameter 3 : (String) "Unlocked"
' Parameter 4 : (Boolean) False
'--------------------------------------------------

long934 = settingRepository1.GetAttr("VOLUME_ACCELERATION_OVER_ROTATIONAL_ACCELERATION_Small")
'--------------------------------------------------
' Parameter 1 : (String) "VOLUME_ACCELERATION_OVER_ROTATIONAL_ACCELERATION_Small"
' Returned value : (Variant) (Long) 1
'--------------------------------------------------

Dim bSTR1867
bSTR1867 = ""
Dim bSTR1868
bSTR1868 = ""
Dim boolean934
settingRepository1.GetAttrInfo "VOLUME_ACCELERATION_OVER_ROTATIONAL_ACCELERATION_Small", bSTR1867, bSTR1868, boolean934
'--------------------------------------------------
' Parameter 1 : (String) "VOLUME_ACCELERATION_OVER_ROTATIONAL_ACCELERATION_Small"
' Parameter 2 : (String) "Default value"
' Parameter 3 : (String) "Unlocked"
' Parameter 4 : (Boolean) False
'--------------------------------------------------

long935 = settingRepository1.GetAttr("VOLUME_ACCELERATION_OVER_ROTATIONAL_ACCELERATION_ExtraSmall")
'--------------------------------------------------
' Parameter 1 : (String) "VOLUME_ACCELERATION_OVER_ROTATIONAL_ACCELERATION_ExtraSmall"
' Returned value : (Variant) (Long) 1
'--------------------------------------------------

Dim bSTR1869
bSTR1869 = ""
Dim bSTR1870
bSTR1870 = ""
Dim boolean935
settingRepository1.GetAttrInfo "VOLUME_ACCELERATION_OVER_ROTATIONAL_ACCELERATION_ExtraSmall", bSTR1869, bSTR1870, boolean935
'--------------------------------------------------
' Parameter 1 : (String) "VOLUME_ACCELERATION_OVER_ROTATIONAL_ACCELERATION_ExtraSmall"
' Parameter 2 : (String) "Default value"
' Parameter 3 : (String) "Unlocked"
' Parameter 4 : (Boolean) False
'--------------------------------------------------

long936 = settingRepository1.GetAttr("VOLUME_ACCELERATION_OVER_ROTATIONAL_ACCELERATION_Nanometric")
'--------------------------------------------------
' Parameter 1 : (String) "VOLUME_ACCELERATION_OVER_ROTATIONAL_ACCELERATION_Nanometric"
' Returned value : (Variant) (Long) 1
'--------------------------------------------------

Dim bSTR1871
bSTR1871 = ""
Dim bSTR1872
bSTR1872 = ""
Dim boolean936
settingRepository1.GetAttrInfo "VOLUME_ACCELERATION_OVER_ROTATIONAL_ACCELERATION_Nanometric", bSTR1871, bSTR1872, boolean936
'--------------------------------------------------
' Parameter 1 : (String) "VOLUME_ACCELERATION_OVER_ROTATIONAL_ACCELERATION_Nanometric"
' Parameter 2 : (String) "Default value"
' Parameter 3 : (String) "Unlocked"
' Parameter 4 : (Boolean) False
'--------------------------------------------------

long937 = settingRepository1.GetAttr("VOLUME_VELOCITY_OVER_ROTATIONAL_ACCELERATION")
'--------------------------------------------------
' Parameter 1 : (String) "VOLUME_VELOCITY_OVER_ROTATIONAL_ACCELERATION"
' Returned value : (Variant) (Long) 1
'--------------------------------------------------

Dim bSTR1873
bSTR1873 = ""
Dim bSTR1874
bSTR1874 = ""
Dim boolean937
settingRepository1.GetAttrInfo "VOLUME_VELOCITY_OVER_ROTATIONAL_ACCELERATION", bSTR1873, bSTR1874, boolean937
'--------------------------------------------------
' Parameter 1 : (String) "VOLUME_VELOCITY_OVER_ROTATIONAL_ACCELERATION"
' Parameter 2 : (String) "Default value"
' Parameter 3 : (String) "Unlocked"
' Parameter 4 : (Boolean) False
'--------------------------------------------------

long938 = settingRepository1.GetAttr("VOLUME_VELOCITY_OVER_ROTATIONAL_ACCELERATION_Large")
'--------------------------------------------------
' Parameter 1 : (String) "VOLUME_VELOCITY_OVER_ROTATIONAL_ACCELERATION_Large"
' Returned value : (Variant) (Long) 1
'--------------------------------------------------

Dim bSTR1875
bSTR1875 = ""
Dim bSTR1876
bSTR1876 = ""
Dim boolean938
settingRepository1.GetAttrInfo "VOLUME_VELOCITY_OVER_ROTATIONAL_ACCELERATION_Large", bSTR1875, bSTR1876, boolean938
'--------------------------------------------------
' Parameter 1 : (String) "VOLUME_VELOCITY_OVER_ROTATIONAL_ACCELERATION_Large"
' Parameter 2 : (String) "Default value"
' Parameter 3 : (String) "Unlocked"
' Parameter 4 : (Boolean) False
'--------------------------------------------------

long939 = settingRepository1.GetAttr("VOLUME_VELOCITY_OVER_ROTATIONAL_ACCELERATION_ExtraLarge")
'--------------------------------------------------
' Parameter 1 : (String) "VOLUME_VELOCITY_OVER_ROTATIONAL_ACCELERATION_ExtraLarge"
' Returned value : (Variant) (Long) 1
'--------------------------------------------------

Dim bSTR1877
bSTR1877 = ""
Dim bSTR1878
bSTR1878 = ""
Dim boolean939
settingRepository1.GetAttrInfo "VOLUME_VELOCITY_OVER_ROTATIONAL_ACCELERATION_ExtraLarge", bSTR1877, bSTR1878, boolean939
'--------------------------------------------------
' Parameter 1 : (String) "VOLUME_VELOCITY_OVER_ROTATIONAL_ACCELERATION_ExtraLarge"
' Parameter 2 : (String) "Default value"
' Parameter 3 : (String) "Unlocked"
' Parameter 4 : (Boolean) False
'--------------------------------------------------

long940 = settingRepository1.GetAttr("VOLUME_VELOCITY_OVER_ROTATIONAL_ACCELERATION_Small")
'--------------------------------------------------
' Parameter 1 : (String) "VOLUME_VELOCITY_OVER_ROTATIONAL_ACCELERATION_Small"
' Returned value : (Variant) (Long) 1
'--------------------------------------------------

Dim bSTR1879
bSTR1879 = ""
Dim bSTR1880
bSTR1880 = ""
Dim boolean940
settingRepository1.GetAttrInfo "VOLUME_VELOCITY_OVER_ROTATIONAL_ACCELERATION_Small", bSTR1879, bSTR1880, boolean940
'--------------------------------------------------
' Parameter 1 : (String) "VOLUME_VELOCITY_OVER_ROTATIONAL_ACCELERATION_Small"
' Parameter 2 : (String) "Default value"
' Parameter 3 : (String) "Unlocked"
' Parameter 4 : (Boolean) False
'--------------------------------------------------

long941 = settingRepository1.GetAttr("VOLUME_VELOCITY_OVER_ROTATIONAL_ACCELERATION_ExtraSmall")
'--------------------------------------------------
' Parameter 1 : (String) "VOLUME_VELOCITY_OVER_ROTATIONAL_ACCELERATION_ExtraSmall"
' Returned value : (Variant) (Long) 1
'--------------------------------------------------

Dim bSTR1881
bSTR1881 = ""
Dim bSTR1882
bSTR1882 = ""
Dim boolean941
settingRepository1.GetAttrInfo "VOLUME_VELOCITY_OVER_ROTATIONAL_ACCELERATION_ExtraSmall", bSTR1881, bSTR1882, boolean941
'--------------------------------------------------
' Parameter 1 : (String) "VOLUME_VELOCITY_OVER_ROTATIONAL_ACCELERATION_ExtraSmall"
' Parameter 2 : (String) "Default value"
' Parameter 3 : (String) "Unlocked"
' Parameter 4 : (Boolean) False
'--------------------------------------------------

long942 = settingRepository1.GetAttr("VOLUME_VELOCITY_OVER_ROTATIONAL_ACCELERATION_Nanometric")
'--------------------------------------------------
' Parameter 1 : (String) "VOLUME_VELOCITY_OVER_ROTATIONAL_ACCELERATION_Nanometric"
' Returned value : (Variant) (Long) 1
'--------------------------------------------------

Dim bSTR1883
bSTR1883 = ""
Dim bSTR1884
bSTR1884 = ""
Dim boolean942
settingRepository1.GetAttrInfo "VOLUME_VELOCITY_OVER_ROTATIONAL_ACCELERATION_Nanometric", bSTR1883, bSTR1884, boolean942
'--------------------------------------------------
' Parameter 1 : (String) "VOLUME_VELOCITY_OVER_ROTATIONAL_ACCELERATION_Nanometric"
' Parameter 2 : (String) "Default value"
' Parameter 3 : (String) "Unlocked"
' Parameter 4 : (Boolean) False
'--------------------------------------------------

long943 = settingRepository1.GetAttr("VELOCITY_POTENTIAL")
'--------------------------------------------------
' Parameter 1 : (String) "VELOCITY_POTENTIAL"
' Returned value : (Variant) (Long) 1
'--------------------------------------------------

Dim bSTR1885
bSTR1885 = ""
Dim bSTR1886
bSTR1886 = ""
Dim boolean943
settingRepository1.GetAttrInfo "VELOCITY_POTENTIAL", bSTR1885, bSTR1886, boolean943
'--------------------------------------------------
' Parameter 1 : (String) "VELOCITY_POTENTIAL"
' Parameter 2 : (String) "Default value"
' Parameter 3 : (String) "Unlocked"
' Parameter 4 : (Boolean) False
'--------------------------------------------------

long944 = settingRepository1.GetAttr("VELOCITY_POTENTIAL_Large")
'--------------------------------------------------
' Parameter 1 : (String) "VELOCITY_POTENTIAL_Large"
' Returned value : (Variant) (Long) 1
'--------------------------------------------------

Dim bSTR1887
bSTR1887 = ""
Dim bSTR1888
bSTR1888 = ""
Dim boolean944
settingRepository1.GetAttrInfo "VELOCITY_POTENTIAL_Large", bSTR1887, bSTR1888, boolean944
'--------------------------------------------------
' Parameter 1 : (String) "VELOCITY_POTENTIAL_Large"
' Parameter 2 : (String) "Default value"
' Parameter 3 : (String) "Unlocked"
' Parameter 4 : (Boolean) False
'--------------------------------------------------

long945 = settingRepository1.GetAttr("VELOCITY_POTENTIAL_ExtraLarge")
'--------------------------------------------------
' Parameter 1 : (String) "VELOCITY_POTENTIAL_ExtraLarge"
' Returned value : (Variant) (Long) 1
'--------------------------------------------------

Dim bSTR1889
bSTR1889 = ""
Dim bSTR1890
bSTR1890 = ""
Dim boolean945
settingRepository1.GetAttrInfo "VELOCITY_POTENTIAL_ExtraLarge", bSTR1889, bSTR1890, boolean945
'--------------------------------------------------
' Parameter 1 : (String) "VELOCITY_POTENTIAL_ExtraLarge"
' Parameter 2 : (String) "Default value"
' Parameter 3 : (String) "Unlocked"
' Parameter 4 : (Boolean) False
'--------------------------------------------------

long946 = settingRepository1.GetAttr("VELOCITY_POTENTIAL_Small")
'--------------------------------------------------
' Parameter 1 : (String) "VELOCITY_POTENTIAL_Small"
' Returned value : (Variant) (Long) 1
'--------------------------------------------------

Dim bSTR1891
bSTR1891 = ""
Dim bSTR1892
bSTR1892 = ""
Dim boolean946
settingRepository1.GetAttrInfo "VELOCITY_POTENTIAL_Small", bSTR1891, bSTR1892, boolean946
'--------------------------------------------------
' Parameter 1 : (String) "VELOCITY_POTENTIAL_Small"
' Parameter 2 : (String) "Default value"
' Parameter 3 : (String) "Unlocked"
' Parameter 4 : (Boolean) False
'--------------------------------------------------

long947 = settingRepository1.GetAttr("VELOCITY_POTENTIAL_ExtraSmall")
'--------------------------------------------------
' Parameter 1 : (String) "VELOCITY_POTENTIAL_ExtraSmall"
' Returned value : (Variant) (Long) 1
'--------------------------------------------------

Dim bSTR1893
bSTR1893 = ""
Dim bSTR1894
bSTR1894 = ""
Dim boolean947
settingRepository1.GetAttrInfo "VELOCITY_POTENTIAL_ExtraSmall", bSTR1893, bSTR1894, boolean947
'--------------------------------------------------
' Parameter 1 : (String) "VELOCITY_POTENTIAL_ExtraSmall"
' Parameter 2 : (String) "Default value"
' Parameter 3 : (String) "Unlocked"
' Parameter 4 : (Boolean) False
'--------------------------------------------------

long948 = settingRepository1.GetAttr("VELOCITY_POTENTIAL_Nanometric")
'--------------------------------------------------
' Parameter 1 : (String) "VELOCITY_POTENTIAL_Nanometric"
' Returned value : (Variant) (Long) 1
'--------------------------------------------------

Dim bSTR1895
bSTR1895 = ""
Dim bSTR1896
bSTR1896 = ""
Dim boolean948
settingRepository1.GetAttrInfo "VELOCITY_POTENTIAL_Nanometric", bSTR1895, bSTR1896, boolean948
'--------------------------------------------------
' Parameter 1 : (String) "VELOCITY_POTENTIAL_Nanometric"
' Parameter 2 : (String) "Default value"
' Parameter 3 : (String) "Unlocked"
' Parameter 4 : (Boolean) False
'--------------------------------------------------

long949 = settingRepository1.GetAttr("PRESSURE_OVER_TIME")
'--------------------------------------------------
' Parameter 1 : (String) "PRESSURE_OVER_TIME"
' Returned value : (Variant) (Long) 1
'--------------------------------------------------

Dim bSTR1897
bSTR1897 = ""
Dim bSTR1898
bSTR1898 = ""
Dim boolean949
settingRepository1.GetAttrInfo "PRESSURE_OVER_TIME", bSTR1897, bSTR1898, boolean949
'--------------------------------------------------
' Parameter 1 : (String) "PRESSURE_OVER_TIME"
' Parameter 2 : (String) "Default value"
' Parameter 3 : (String) "Unlocked"
' Parameter 4 : (Boolean) False
'--------------------------------------------------

long950 = settingRepository1.GetAttr("PRESSURE_OVER_TIME_Large")
'--------------------------------------------------
' Parameter 1 : (String) "PRESSURE_OVER_TIME_Large"
' Returned value : (Variant) (Long) 1
'--------------------------------------------------

Dim bSTR1899
bSTR1899 = ""
Dim bSTR1900
bSTR1900 = ""
Dim boolean950
settingRepository1.GetAttrInfo "PRESSURE_OVER_TIME_Large", bSTR1899, bSTR1900, boolean950
'--------------------------------------------------
' Parameter 1 : (String) "PRESSURE_OVER_TIME_Large"
' Parameter 2 : (String) "Default value"
' Parameter 3 : (String) "Unlocked"
' Parameter 4 : (Boolean) False
'--------------------------------------------------

long951 = settingRepository1.GetAttr("PRESSURE_OVER_TIME_ExtraLarge")
'--------------------------------------------------
' Parameter 1 : (String) "PRESSURE_OVER_TIME_ExtraLarge"
' Returned value : (Variant) (Long) 1
'--------------------------------------------------

Dim bSTR1901
bSTR1901 = ""
Dim bSTR1902
bSTR1902 = ""
Dim boolean951
settingRepository1.GetAttrInfo "PRESSURE_OVER_TIME_ExtraLarge", bSTR1901, bSTR1902, boolean951
'--------------------------------------------------
' Parameter 1 : (String) "PRESSURE_OVER_TIME_ExtraLarge"
' Parameter 2 : (String) "Default value"
' Parameter 3 : (String) "Unlocked"
' Parameter 4 : (Boolean) False
'--------------------------------------------------

long952 = settingRepository1.GetAttr("PRESSURE_OVER_TIME_Small")
'--------------------------------------------------
' Parameter 1 : (String) "PRESSURE_OVER_TIME_Small"
' Returned value : (Variant) (Long) 1
'--------------------------------------------------

Dim bSTR1903
bSTR1903 = ""
Dim bSTR1904
bSTR1904 = ""
Dim boolean952
settingRepository1.GetAttrInfo "PRESSURE_OVER_TIME_Small", bSTR1903, bSTR1904, boolean952
'--------------------------------------------------
' Parameter 1 : (String) "PRESSURE_OVER_TIME_Small"
' Parameter 2 : (String) "Default value"
' Parameter 3 : (String) "Unlocked"
' Parameter 4 : (Boolean) False
'--------------------------------------------------

long953 = settingRepository1.GetAttr("PRESSURE_OVER_TIME_ExtraSmall")
'--------------------------------------------------
' Parameter 1 : (String) "PRESSURE_OVER_TIME_ExtraSmall"
' Returned value : (Variant) (Long) 1
'--------------------------------------------------

Dim bSTR1905
bSTR1905 = ""
Dim bSTR1906
bSTR1906 = ""
Dim boolean953
settingRepository1.GetAttrInfo "PRESSURE_OVER_TIME_ExtraSmall", bSTR1905, bSTR1906, boolean953
'--------------------------------------------------
' Parameter 1 : (String) "PRESSURE_OVER_TIME_ExtraSmall"
' Parameter 2 : (String) "Default value"
' Parameter 3 : (String) "Unlocked"
' Parameter 4 : (Boolean) False
'--------------------------------------------------

long954 = settingRepository1.GetAttr("PRESSURE_OVER_TIME_Nanometric")
'--------------------------------------------------
' Parameter 1 : (String) "PRESSURE_OVER_TIME_Nanometric"
' Returned value : (Variant) (Long) 1
'--------------------------------------------------

Dim bSTR1907
bSTR1907 = ""
Dim bSTR1908
bSTR1908 = ""
Dim boolean954
settingRepository1.GetAttrInfo "PRESSURE_OVER_TIME_Nanometric", bSTR1907, bSTR1908, boolean954
'--------------------------------------------------
' Parameter 1 : (String) "PRESSURE_OVER_TIME_Nanometric"
' Parameter 2 : (String) "Default value"
' Parameter 3 : (String) "Unlocked"
' Parameter 4 : (Boolean) False
'--------------------------------------------------

long955 = settingRepository1.GetAttr("VOLUME_ACCELERATION_OVER_DISPLACEMENT")
'--------------------------------------------------
' Parameter 1 : (String) "VOLUME_ACCELERATION_OVER_DISPLACEMENT"
' Returned value : (Variant) (Long) 1
'--------------------------------------------------

Dim bSTR1909
bSTR1909 = ""
Dim bSTR1910
bSTR1910 = ""
Dim boolean955
settingRepository1.GetAttrInfo "VOLUME_ACCELERATION_OVER_DISPLACEMENT", bSTR1909, bSTR1910, boolean955
'--------------------------------------------------
' Parameter 1 : (String) "VOLUME_ACCELERATION_OVER_DISPLACEMENT"
' Parameter 2 : (String) "Default value"
' Parameter 3 : (String) "Unlocked"
' Parameter 4 : (Boolean) False
'--------------------------------------------------

long956 = settingRepository1.GetAttr("VOLUME_ACCELERATION_OVER_DISPLACEMENT_Large")
'--------------------------------------------------
' Parameter 1 : (String) "VOLUME_ACCELERATION_OVER_DISPLACEMENT_Large"
' Returned value : (Variant) (Long) 1
'--------------------------------------------------

Dim bSTR1911
bSTR1911 = ""
Dim bSTR1912
bSTR1912 = ""
Dim boolean956
settingRepository1.GetAttrInfo "VOLUME_ACCELERATION_OVER_DISPLACEMENT_Large", bSTR1911, bSTR1912, boolean956
'--------------------------------------------------
' Parameter 1 : (String) "VOLUME_ACCELERATION_OVER_DISPLACEMENT_Large"
' Parameter 2 : (String) "Default value"
' Parameter 3 : (String) "Unlocked"
' Parameter 4 : (Boolean) False
'--------------------------------------------------

long957 = settingRepository1.GetAttr("VOLUME_ACCELERATION_OVER_DISPLACEMENT_ExtraLarge")
'--------------------------------------------------
' Parameter 1 : (String) "VOLUME_ACCELERATION_OVER_DISPLACEMENT_ExtraLarge"
' Returned value : (Variant) (Long) 1
'--------------------------------------------------

Dim bSTR1913
bSTR1913 = ""
Dim bSTR1914
bSTR1914 = ""
Dim boolean957
settingRepository1.GetAttrInfo "VOLUME_ACCELERATION_OVER_DISPLACEMENT_ExtraLarge", bSTR1913, bSTR1914, boolean957
'--------------------------------------------------
' Parameter 1 : (String) "VOLUME_ACCELERATION_OVER_DISPLACEMENT_ExtraLarge"
' Parameter 2 : (String) "Default value"
' Parameter 3 : (String) "Unlocked"
' Parameter 4 : (Boolean) False
'--------------------------------------------------

long958 = settingRepository1.GetAttr("VOLUME_ACCELERATION_OVER_DISPLACEMENT_Small")
'--------------------------------------------------
' Parameter 1 : (String) "VOLUME_ACCELERATION_OVER_DISPLACEMENT_Small"
' Returned value : (Variant) (Long) 1
'--------------------------------------------------

Dim bSTR1915
bSTR1915 = ""
Dim bSTR1916
bSTR1916 = ""
Dim boolean958
settingRepository1.GetAttrInfo "VOLUME_ACCELERATION_OVER_DISPLACEMENT_Small", bSTR1915, bSTR1916, boolean958
'--------------------------------------------------
' Parameter 1 : (String) "VOLUME_ACCELERATION_OVER_DISPLACEMENT_Small"
' Parameter 2 : (String) "Default value"
' Parameter 3 : (String) "Unlocked"
' Parameter 4 : (Boolean) False
'--------------------------------------------------

long959 = settingRepository1.GetAttr("VOLUME_ACCELERATION_OVER_DISPLACEMENT_ExtraSmall")
'--------------------------------------------------
' Parameter 1 : (String) "VOLUME_ACCELERATION_OVER_DISPLACEMENT_ExtraSmall"
' Returned value : (Variant) (Long) 1
'--------------------------------------------------

Dim bSTR1917
bSTR1917 = ""
Dim bSTR1918
bSTR1918 = ""
Dim boolean959
settingRepository1.GetAttrInfo "VOLUME_ACCELERATION_OVER_DISPLACEMENT_ExtraSmall", bSTR1917, bSTR1918, boolean959
'--------------------------------------------------
' Parameter 1 : (String) "VOLUME_ACCELERATION_OVER_DISPLACEMENT_ExtraSmall"
' Parameter 2 : (String) "Default value"
' Parameter 3 : (String) "Unlocked"
' Parameter 4 : (Boolean) False
'--------------------------------------------------

long960 = settingRepository1.GetAttr("VOLUME_ACCELERATION_OVER_DISPLACEMENT_Nanometric")
'--------------------------------------------------
' Parameter 1 : (String) "VOLUME_ACCELERATION_OVER_DISPLACEMENT_Nanometric"
' Returned value : (Variant) (Long) 1
'--------------------------------------------------

Dim bSTR1919
bSTR1919 = ""
Dim bSTR1920
bSTR1920 = ""
Dim boolean960
settingRepository1.GetAttrInfo "VOLUME_ACCELERATION_OVER_DISPLACEMENT_Nanometric", bSTR1919, bSTR1920, boolean960
'--------------------------------------------------
' Parameter 1 : (String) "VOLUME_ACCELERATION_OVER_DISPLACEMENT_Nanometric"
' Parameter 2 : (String) "Default value"
' Parameter 3 : (String) "Unlocked"
' Parameter 4 : (Boolean) False
'--------------------------------------------------

long961 = settingRepository1.GetAttr("VOLUME_VELOCITY_OVER_DISPLACEMENT")
'--------------------------------------------------
' Parameter 1 : (String) "VOLUME_VELOCITY_OVER_DISPLACEMENT"
' Returned value : (Variant) (Long) 1
'--------------------------------------------------

Dim bSTR1921
bSTR1921 = ""
Dim bSTR1922
bSTR1922 = ""
Dim boolean961
settingRepository1.GetAttrInfo "VOLUME_VELOCITY_OVER_DISPLACEMENT", bSTR1921, bSTR1922, boolean961
'--------------------------------------------------
' Parameter 1 : (String) "VOLUME_VELOCITY_OVER_DISPLACEMENT"
' Parameter 2 : (String) "Default value"
' Parameter 3 : (String) "Unlocked"
' Parameter 4 : (Boolean) False
'--------------------------------------------------

long962 = settingRepository1.GetAttr("VOLUME_VELOCITY_OVER_DISPLACEMENT_Large")
'--------------------------------------------------
' Parameter 1 : (String) "VOLUME_VELOCITY_OVER_DISPLACEMENT_Large"
' Returned value : (Variant) (Long) 1
'--------------------------------------------------

Dim bSTR1923
bSTR1923 = ""
Dim bSTR1924
bSTR1924 = ""
Dim boolean962
settingRepository1.GetAttrInfo "VOLUME_VELOCITY_OVER_DISPLACEMENT_Large", bSTR1923, bSTR1924, boolean962
'--------------------------------------------------
' Parameter 1 : (String) "VOLUME_VELOCITY_OVER_DISPLACEMENT_Large"
' Parameter 2 : (String) "Default value"
' Parameter 3 : (String) "Unlocked"
' Parameter 4 : (Boolean) False
'--------------------------------------------------

long963 = settingRepository1.GetAttr("VOLUME_VELOCITY_OVER_DISPLACEMENT_ExtraLarge")
'--------------------------------------------------
' Parameter 1 : (String) "VOLUME_VELOCITY_OVER_DISPLACEMENT_ExtraLarge"
' Returned value : (Variant) (Long) 1
'--------------------------------------------------

Dim bSTR1925
bSTR1925 = ""
Dim bSTR1926
bSTR1926 = ""
Dim boolean963
settingRepository1.GetAttrInfo "VOLUME_VELOCITY_OVER_DISPLACEMENT_ExtraLarge", bSTR1925, bSTR1926, boolean963
'--------------------------------------------------
' Parameter 1 : (String) "VOLUME_VELOCITY_OVER_DISPLACEMENT_ExtraLarge"
' Parameter 2 : (String) "Default value"
' Parameter 3 : (String) "Unlocked"
' Parameter 4 : (Boolean) False
'--------------------------------------------------

long964 = settingRepository1.GetAttr("VOLUME_VELOCITY_OVER_DISPLACEMENT_Small")
'--------------------------------------------------
' Parameter 1 : (String) "VOLUME_VELOCITY_OVER_DISPLACEMENT_Small"
' Returned value : (Variant) (Long) 1
'--------------------------------------------------

Dim bSTR1927
bSTR1927 = ""
Dim bSTR1928
bSTR1928 = ""
Dim boolean964
settingRepository1.GetAttrInfo "VOLUME_VELOCITY_OVER_DISPLACEMENT_Small", bSTR1927, bSTR1928, boolean964
'--------------------------------------------------
' Parameter 1 : (String) "VOLUME_VELOCITY_OVER_DISPLACEMENT_Small"
' Parameter 2 : (String) "Default value"
' Parameter 3 : (String) "Unlocked"
' Parameter 4 : (Boolean) False
'--------------------------------------------------

long965 = settingRepository1.GetAttr("VOLUME_VELOCITY_OVER_DISPLACEMENT_ExtraSmall")
'--------------------------------------------------
' Parameter 1 : (String) "VOLUME_VELOCITY_OVER_DISPLACEMENT_ExtraSmall"
' Returned value : (Variant) (Long) 1
'--------------------------------------------------

Dim bSTR1929
bSTR1929 = ""
Dim bSTR1930
bSTR1930 = ""
Dim boolean965
settingRepository1.GetAttrInfo "VOLUME_VELOCITY_OVER_DISPLACEMENT_ExtraSmall", bSTR1929, bSTR1930, boolean965
'--------------------------------------------------
' Parameter 1 : (String) "VOLUME_VELOCITY_OVER_DISPLACEMENT_ExtraSmall"
' Parameter 2 : (String) "Default value"
' Parameter 3 : (String) "Unlocked"
' Parameter 4 : (Boolean) False
'--------------------------------------------------

long966 = settingRepository1.GetAttr("VOLUME_VELOCITY_OVER_DISPLACEMENT_Nanometric")
'--------------------------------------------------
' Parameter 1 : (String) "VOLUME_VELOCITY_OVER_DISPLACEMENT_Nanometric"
' Returned value : (Variant) (Long) 1
'--------------------------------------------------

Dim bSTR1931
bSTR1931 = ""
Dim bSTR1932
bSTR1932 = ""
Dim boolean966
settingRepository1.GetAttrInfo "VOLUME_VELOCITY_OVER_DISPLACEMENT_Nanometric", bSTR1931, bSTR1932, boolean966
'--------------------------------------------------
' Parameter 1 : (String) "VOLUME_VELOCITY_OVER_DISPLACEMENT_Nanometric"
' Parameter 2 : (String) "Default value"
' Parameter 3 : (String) "Unlocked"
' Parameter 4 : (Boolean) False
'--------------------------------------------------

long967 = settingRepository1.GetAttr("VOLUME_ACCELERATION_OVER_ROTATION")
'--------------------------------------------------
' Parameter 1 : (String) "VOLUME_ACCELERATION_OVER_ROTATION"
' Returned value : (Variant) (Long) 1
'--------------------------------------------------

Dim bSTR1933
bSTR1933 = ""
Dim bSTR1934
bSTR1934 = ""
Dim boolean967
settingRepository1.GetAttrInfo "VOLUME_ACCELERATION_OVER_ROTATION", bSTR1933, bSTR1934, boolean967
'--------------------------------------------------
' Parameter 1 : (String) "VOLUME_ACCELERATION_OVER_ROTATION"
' Parameter 2 : (String) "Default value"
' Parameter 3 : (String) "Unlocked"
' Parameter 4 : (Boolean) False
'--------------------------------------------------

long968 = settingRepository1.GetAttr("VOLUME_ACCELERATION_OVER_ROTATION_Large")
'--------------------------------------------------
' Parameter 1 : (String) "VOLUME_ACCELERATION_OVER_ROTATION_Large"
' Returned value : (Variant) (Long) 1
'--------------------------------------------------

Dim bSTR1935
bSTR1935 = ""
Dim bSTR1936
bSTR1936 = ""
Dim boolean968
settingRepository1.GetAttrInfo "VOLUME_ACCELERATION_OVER_ROTATION_Large", bSTR1935, bSTR1936, boolean968
'--------------------------------------------------
' Parameter 1 : (String) "VOLUME_ACCELERATION_OVER_ROTATION_Large"
' Parameter 2 : (String) "Default value"
' Parameter 3 : (String) "Unlocked"
' Parameter 4 : (Boolean) False
'--------------------------------------------------

long969 = settingRepository1.GetAttr("VOLUME_ACCELERATION_OVER_ROTATION_ExtraLarge")
'--------------------------------------------------
' Parameter 1 : (String) "VOLUME_ACCELERATION_OVER_ROTATION_ExtraLarge"
' Returned value : (Variant) (Long) 1
'--------------------------------------------------

Dim bSTR1937
bSTR1937 = ""
Dim bSTR1938
bSTR1938 = ""
Dim boolean969
settingRepository1.GetAttrInfo "VOLUME_ACCELERATION_OVER_ROTATION_ExtraLarge", bSTR1937, bSTR1938, boolean969
'--------------------------------------------------
' Parameter 1 : (String) "VOLUME_ACCELERATION_OVER_ROTATION_ExtraLarge"
' Parameter 2 : (String) "Default value"
' Parameter 3 : (String) "Unlocked"
' Parameter 4 : (Boolean) False
'--------------------------------------------------

long970 = settingRepository1.GetAttr("VOLUME_ACCELERATION_OVER_ROTATION_Small")
'--------------------------------------------------
' Parameter 1 : (String) "VOLUME_ACCELERATION_OVER_ROTATION_Small"
' Returned value : (Variant) (Long) 1
'--------------------------------------------------

Dim bSTR1939
bSTR1939 = ""
Dim bSTR1940
bSTR1940 = ""
Dim boolean970
settingRepository1.GetAttrInfo "VOLUME_ACCELERATION_OVER_ROTATION_Small", bSTR1939, bSTR1940, boolean970
'--------------------------------------------------
' Parameter 1 : (String) "VOLUME_ACCELERATION_OVER_ROTATION_Small"
' Parameter 2 : (String) "Default value"
' Parameter 3 : (String) "Unlocked"
' Parameter 4 : (Boolean) False
'--------------------------------------------------

long971 = settingRepository1.GetAttr("VOLUME_ACCELERATION_OVER_ROTATION_ExtraSmall")
'--------------------------------------------------
' Parameter 1 : (String) "VOLUME_ACCELERATION_OVER_ROTATION_ExtraSmall"
' Returned value : (Variant) (Long) 1
'--------------------------------------------------

Dim bSTR1941
bSTR1941 = ""
Dim bSTR1942
bSTR1942 = ""
Dim boolean971
settingRepository1.GetAttrInfo "VOLUME_ACCELERATION_OVER_ROTATION_ExtraSmall", bSTR1941, bSTR1942, boolean971
'--------------------------------------------------
' Parameter 1 : (String) "VOLUME_ACCELERATION_OVER_ROTATION_ExtraSmall"
' Parameter 2 : (String) "Default value"
' Parameter 3 : (String) "Unlocked"
' Parameter 4 : (Boolean) False
'--------------------------------------------------

long972 = settingRepository1.GetAttr("VOLUME_ACCELERATION_OVER_ROTATION_Nanometric")
'--------------------------------------------------
' Parameter 1 : (String) "VOLUME_ACCELERATION_OVER_ROTATION_Nanometric"
' Returned value : (Variant) (Long) 1
'--------------------------------------------------

Dim bSTR1943
bSTR1943 = ""
Dim bSTR1944
bSTR1944 = ""
Dim boolean972
settingRepository1.GetAttrInfo "VOLUME_ACCELERATION_OVER_ROTATION_Nanometric", bSTR1943, bSTR1944, boolean972
'--------------------------------------------------
' Parameter 1 : (String) "VOLUME_ACCELERATION_OVER_ROTATION_Nanometric"
' Parameter 2 : (String) "Default value"
' Parameter 3 : (String) "Unlocked"
' Parameter 4 : (Boolean) False
'--------------------------------------------------

long973 = settingRepository1.GetAttr("VOLUME_VELOCITY_OVER_ROTATION")
'--------------------------------------------------
' Parameter 1 : (String) "VOLUME_VELOCITY_OVER_ROTATION"
' Returned value : (Variant) (Long) 1
'--------------------------------------------------

Dim bSTR1945
bSTR1945 = ""
Dim bSTR1946
bSTR1946 = ""
Dim boolean973
settingRepository1.GetAttrInfo "VOLUME_VELOCITY_OVER_ROTATION", bSTR1945, bSTR1946, boolean973
'--------------------------------------------------
' Parameter 1 : (String) "VOLUME_VELOCITY_OVER_ROTATION"
' Parameter 2 : (String) "Default value"
' Parameter 3 : (String) "Unlocked"
' Parameter 4 : (Boolean) False
'--------------------------------------------------

long974 = settingRepository1.GetAttr("VOLUME_VELOCITY_OVER_ROTATION_Large")
'--------------------------------------------------
' Parameter 1 : (String) "VOLUME_VELOCITY_OVER_ROTATION_Large"
' Returned value : (Variant) (Long) 1
'--------------------------------------------------

Dim bSTR1947
bSTR1947 = ""
Dim bSTR1948
bSTR1948 = ""
Dim boolean974
settingRepository1.GetAttrInfo "VOLUME_VELOCITY_OVER_ROTATION_Large", bSTR1947, bSTR1948, boolean974
'--------------------------------------------------
' Parameter 1 : (String) "VOLUME_VELOCITY_OVER_ROTATION_Large"
' Parameter 2 : (String) "Default value"
' Parameter 3 : (String) "Unlocked"
' Parameter 4 : (Boolean) False
'--------------------------------------------------

long975 = settingRepository1.GetAttr("VOLUME_VELOCITY_OVER_ROTATION_ExtraLarge")
'--------------------------------------------------
' Parameter 1 : (String) "VOLUME_VELOCITY_OVER_ROTATION_ExtraLarge"
' Returned value : (Variant) (Long) 1
'--------------------------------------------------

Dim bSTR1949
bSTR1949 = ""
Dim bSTR1950
bSTR1950 = ""
Dim boolean975
settingRepository1.GetAttrInfo "VOLUME_VELOCITY_OVER_ROTATION_ExtraLarge", bSTR1949, bSTR1950, boolean975
'--------------------------------------------------
' Parameter 1 : (String) "VOLUME_VELOCITY_OVER_ROTATION_ExtraLarge"
' Parameter 2 : (String) "Default value"
' Parameter 3 : (String) "Unlocked"
' Parameter 4 : (Boolean) False
'--------------------------------------------------

long976 = settingRepository1.GetAttr("VOLUME_VELOCITY_OVER_ROTATION_Small")
'--------------------------------------------------
' Parameter 1 : (String) "VOLUME_VELOCITY_OVER_ROTATION_Small"
' Returned value : (Variant) (Long) 1
'--------------------------------------------------

Dim bSTR1951
bSTR1951 = ""
Dim bSTR1952
bSTR1952 = ""
Dim boolean976
settingRepository1.GetAttrInfo "VOLUME_VELOCITY_OVER_ROTATION_Small", bSTR1951, bSTR1952, boolean976
'--------------------------------------------------
' Parameter 1 : (String) "VOLUME_VELOCITY_OVER_ROTATION_Small"
' Parameter 2 : (String) "Default value"
' Parameter 3 : (String) "Unlocked"
' Parameter 4 : (Boolean) False
'--------------------------------------------------

long977 = settingRepository1.GetAttr("VOLUME_VELOCITY_OVER_ROTATION_ExtraSmall")
'--------------------------------------------------
' Parameter 1 : (String) "VOLUME_VELOCITY_OVER_ROTATION_ExtraSmall"
' Returned value : (Variant) (Long) 1
'--------------------------------------------------

Dim bSTR1953
bSTR1953 = ""
Dim bSTR1954
bSTR1954 = ""
Dim boolean977
settingRepository1.GetAttrInfo "VOLUME_VELOCITY_OVER_ROTATION_ExtraSmall", bSTR1953, bSTR1954, boolean977
'--------------------------------------------------
' Parameter 1 : (String) "VOLUME_VELOCITY_OVER_ROTATION_ExtraSmall"
' Parameter 2 : (String) "Default value"
' Parameter 3 : (String) "Unlocked"
' Parameter 4 : (Boolean) False
'--------------------------------------------------

long978 = settingRepository1.GetAttr("VOLUME_VELOCITY_OVER_ROTATION_Nanometric")
'--------------------------------------------------
' Parameter 1 : (String) "VOLUME_VELOCITY_OVER_ROTATION_Nanometric"
' Returned value : (Variant) (Long) 1
'--------------------------------------------------

Dim bSTR1955
bSTR1955 = ""
Dim bSTR1956
bSTR1956 = ""
Dim boolean978
settingRepository1.GetAttrInfo "VOLUME_VELOCITY_OVER_ROTATION_Nanometric", bSTR1955, bSTR1956, boolean978
'--------------------------------------------------
' Parameter 1 : (String) "VOLUME_VELOCITY_OVER_ROTATION_Nanometric"
' Parameter 2 : (String) "Default value"
' Parameter 3 : (String) "Unlocked"
' Parameter 4 : (Boolean) False
'--------------------------------------------------

long979 = settingRepository1.GetAttr("VOLUME_ACCELERATION_OVER_VELOCITY")
'--------------------------------------------------
' Parameter 1 : (String) "VOLUME_ACCELERATION_OVER_VELOCITY"
' Returned value : (Variant) (Long) 1
'--------------------------------------------------

Dim bSTR1957
bSTR1957 = ""
Dim bSTR1958
bSTR1958 = ""
Dim boolean979
settingRepository1.GetAttrInfo "VOLUME_ACCELERATION_OVER_VELOCITY", bSTR1957, bSTR1958, boolean979
'--------------------------------------------------
' Parameter 1 : (String) "VOLUME_ACCELERATION_OVER_VELOCITY"
' Parameter 2 : (String) "Default value"
' Parameter 3 : (String) "Unlocked"
' Parameter 4 : (Boolean) False
'--------------------------------------------------

long980 = settingRepository1.GetAttr("VOLUME_ACCELERATION_OVER_VELOCITY_Large")
'--------------------------------------------------
' Parameter 1 : (String) "VOLUME_ACCELERATION_OVER_VELOCITY_Large"
' Returned value : (Variant) (Long) 1
'--------------------------------------------------

Dim bSTR1959
bSTR1959 = ""
Dim bSTR1960
bSTR1960 = ""
Dim boolean980
settingRepository1.GetAttrInfo "VOLUME_ACCELERATION_OVER_VELOCITY_Large", bSTR1959, bSTR1960, boolean980
'--------------------------------------------------
' Parameter 1 : (String) "VOLUME_ACCELERATION_OVER_VELOCITY_Large"
' Parameter 2 : (String) "Default value"
' Parameter 3 : (String) "Unlocked"
' Parameter 4 : (Boolean) False
'--------------------------------------------------

long981 = settingRepository1.GetAttr("VOLUME_ACCELERATION_OVER_VELOCITY_ExtraLarge")
'--------------------------------------------------
' Parameter 1 : (String) "VOLUME_ACCELERATION_OVER_VELOCITY_ExtraLarge"
' Returned value : (Variant) (Long) 1
'--------------------------------------------------

Dim bSTR1961
bSTR1961 = ""
Dim bSTR1962
bSTR1962 = ""
Dim boolean981
settingRepository1.GetAttrInfo "VOLUME_ACCELERATION_OVER_VELOCITY_ExtraLarge", bSTR1961, bSTR1962, boolean981
'--------------------------------------------------
' Parameter 1 : (String) "VOLUME_ACCELERATION_OVER_VELOCITY_ExtraLarge"
' Parameter 2 : (String) "Default value"
' Parameter 3 : (String) "Unlocked"
' Parameter 4 : (Boolean) False
'--------------------------------------------------

long982 = settingRepository1.GetAttr("VOLUME_ACCELERATION_OVER_VELOCITY_Small")
'--------------------------------------------------
' Parameter 1 : (String) "VOLUME_ACCELERATION_OVER_VELOCITY_Small"
' Returned value : (Variant) (Long) 1
'--------------------------------------------------

Dim bSTR1963
bSTR1963 = ""
Dim bSTR1964
bSTR1964 = ""
Dim boolean982
settingRepository1.GetAttrInfo "VOLUME_ACCELERATION_OVER_VELOCITY_Small", bSTR1963, bSTR1964, boolean982
'--------------------------------------------------
' Parameter 1 : (String) "VOLUME_ACCELERATION_OVER_VELOCITY_Small"
' Parameter 2 : (String) "Default value"
' Parameter 3 : (String) "Unlocked"
' Parameter 4 : (Boolean) False
'--------------------------------------------------

long983 = settingRepository1.GetAttr("VOLUME_ACCELERATION_OVER_VELOCITY_ExtraSmall")
'--------------------------------------------------
' Parameter 1 : (String) "VOLUME_ACCELERATION_OVER_VELOCITY_ExtraSmall"
' Returned value : (Variant) (Long) 1
'--------------------------------------------------

Dim bSTR1965
bSTR1965 = ""
Dim bSTR1966
bSTR1966 = ""
Dim boolean983
settingRepository1.GetAttrInfo "VOLUME_ACCELERATION_OVER_VELOCITY_ExtraSmall", bSTR1965, bSTR1966, boolean983
'--------------------------------------------------
' Parameter 1 : (String) "VOLUME_ACCELERATION_OVER_VELOCITY_ExtraSmall"
' Parameter 2 : (String) "Default value"
' Parameter 3 : (String) "Unlocked"
' Parameter 4 : (Boolean) False
'--------------------------------------------------

long984 = settingRepository1.GetAttr("VOLUME_ACCELERATION_OVER_VELOCITY_Nanometric")
'--------------------------------------------------
' Parameter 1 : (String) "VOLUME_ACCELERATION_OVER_VELOCITY_Nanometric"
' Returned value : (Variant) (Long) 1
'--------------------------------------------------

Dim bSTR1967
bSTR1967 = ""
Dim bSTR1968
bSTR1968 = ""
Dim boolean984
settingRepository1.GetAttrInfo "VOLUME_ACCELERATION_OVER_VELOCITY_Nanometric", bSTR1967, bSTR1968, boolean984
'--------------------------------------------------
' Parameter 1 : (String) "VOLUME_ACCELERATION_OVER_VELOCITY_Nanometric"
' Parameter 2 : (String) "Default value"
' Parameter 3 : (String) "Unlocked"
' Parameter 4 : (Boolean) False
'--------------------------------------------------

long985 = settingRepository1.GetAttr("VOLUME_VELOCITY_OVER_VELOCITY")
'--------------------------------------------------
' Parameter 1 : (String) "VOLUME_VELOCITY_OVER_VELOCITY"
' Returned value : (Variant) (Long) 1
'--------------------------------------------------

Dim bSTR1969
bSTR1969 = ""
Dim bSTR1970
bSTR1970 = ""
Dim boolean985
settingRepository1.GetAttrInfo "VOLUME_VELOCITY_OVER_VELOCITY", bSTR1969, bSTR1970, boolean985
'--------------------------------------------------
' Parameter 1 : (String) "VOLUME_VELOCITY_OVER_VELOCITY"
' Parameter 2 : (String) "Default value"
' Parameter 3 : (String) "Unlocked"
' Parameter 4 : (Boolean) False
'--------------------------------------------------

long986 = settingRepository1.GetAttr("VOLUME_VELOCITY_OVER_VELOCITY_Large")
'--------------------------------------------------
' Parameter 1 : (String) "VOLUME_VELOCITY_OVER_VELOCITY_Large"
' Returned value : (Variant) (Long) 1
'--------------------------------------------------

Dim bSTR1971
bSTR1971 = ""
Dim bSTR1972
bSTR1972 = ""
Dim boolean986
settingRepository1.GetAttrInfo "VOLUME_VELOCITY_OVER_VELOCITY_Large", bSTR1971, bSTR1972, boolean986
'--------------------------------------------------
' Parameter 1 : (String) "VOLUME_VELOCITY_OVER_VELOCITY_Large"
' Parameter 2 : (String) "Default value"
' Parameter 3 : (String) "Unlocked"
' Parameter 4 : (Boolean) False
'--------------------------------------------------

long987 = settingRepository1.GetAttr("VOLUME_VELOCITY_OVER_VELOCITY_ExtraLarge")
'--------------------------------------------------
' Parameter 1 : (String) "VOLUME_VELOCITY_OVER_VELOCITY_ExtraLarge"
' Returned value : (Variant) (Long) 1
'--------------------------------------------------

Dim bSTR1973
bSTR1973 = ""
Dim bSTR1974
bSTR1974 = ""
Dim boolean987
settingRepository1.GetAttrInfo "VOLUME_VELOCITY_OVER_VELOCITY_ExtraLarge", bSTR1973, bSTR1974, boolean987
'--------------------------------------------------
' Parameter 1 : (String) "VOLUME_VELOCITY_OVER_VELOCITY_ExtraLarge"
' Parameter 2 : (String) "Default value"
' Parameter 3 : (String) "Unlocked"
' Parameter 4 : (Boolean) False
'--------------------------------------------------

long988 = settingRepository1.GetAttr("VOLUME_VELOCITY_OVER_VELOCITY_Small")
'--------------------------------------------------
' Parameter 1 : (String) "VOLUME_VELOCITY_OVER_VELOCITY_Small"
' Returned value : (Variant) (Long) 1
'--------------------------------------------------

Dim bSTR1975
bSTR1975 = ""
Dim bSTR1976
bSTR1976 = ""
Dim boolean988
settingRepository1.GetAttrInfo "VOLUME_VELOCITY_OVER_VELOCITY_Small", bSTR1975, bSTR1976, boolean988
'--------------------------------------------------
' Parameter 1 : (String) "VOLUME_VELOCITY_OVER_VELOCITY_Small"
' Parameter 2 : (String) "Default value"
' Parameter 3 : (String) "Unlocked"
' Parameter 4 : (Boolean) False
'--------------------------------------------------

long989 = settingRepository1.GetAttr("VOLUME_VELOCITY_OVER_VELOCITY_ExtraSmall")
'--------------------------------------------------
' Parameter 1 : (String) "VOLUME_VELOCITY_OVER_VELOCITY_ExtraSmall"
' Returned value : (Variant) (Long) 1
'--------------------------------------------------

Dim bSTR1977
bSTR1977 = ""
Dim bSTR1978
bSTR1978 = ""
Dim boolean989
settingRepository1.GetAttrInfo "VOLUME_VELOCITY_OVER_VELOCITY_ExtraSmall", bSTR1977, bSTR1978, boolean989
'--------------------------------------------------
' Parameter 1 : (String) "VOLUME_VELOCITY_OVER_VELOCITY_ExtraSmall"
' Parameter 2 : (String) "Default value"
' Parameter 3 : (String) "Unlocked"
' Parameter 4 : (Boolean) False
'--------------------------------------------------

long990 = settingRepository1.GetAttr("VOLUME_VELOCITY_OVER_VELOCITY_Nanometric")
'--------------------------------------------------
' Parameter 1 : (String) "VOLUME_VELOCITY_OVER_VELOCITY_Nanometric"
' Returned value : (Variant) (Long) 1
'--------------------------------------------------

Dim bSTR1979
bSTR1979 = ""
Dim bSTR1980
bSTR1980 = ""
Dim boolean990
settingRepository1.GetAttrInfo "VOLUME_VELOCITY_OVER_VELOCITY_Nanometric", bSTR1979, bSTR1980, boolean990
'--------------------------------------------------
' Parameter 1 : (String) "VOLUME_VELOCITY_OVER_VELOCITY_Nanometric"
' Parameter 2 : (String) "Default value"
' Parameter 3 : (String) "Unlocked"
' Parameter 4 : (Boolean) False
'--------------------------------------------------

long991 = settingRepository1.GetAttr("VOLUME_ACCELERATION_OVER_PULSATION")
'--------------------------------------------------
' Parameter 1 : (String) "VOLUME_ACCELERATION_OVER_PULSATION"
' Returned value : (Variant) (Long) 1
'--------------------------------------------------

Dim bSTR1981
bSTR1981 = ""
Dim bSTR1982
bSTR1982 = ""
Dim boolean991
settingRepository1.GetAttrInfo "VOLUME_ACCELERATION_OVER_PULSATION", bSTR1981, bSTR1982, boolean991
'--------------------------------------------------
' Parameter 1 : (String) "VOLUME_ACCELERATION_OVER_PULSATION"
' Parameter 2 : (String) "Default value"
' Parameter 3 : (String) "Unlocked"
' Parameter 4 : (Boolean) False
'--------------------------------------------------

long992 = settingRepository1.GetAttr("VOLUME_ACCELERATION_OVER_PULSATION_Large")
'--------------------------------------------------
' Parameter 1 : (String) "VOLUME_ACCELERATION_OVER_PULSATION_Large"
' Returned value : (Variant) (Long) 1
'--------------------------------------------------

Dim bSTR1983
bSTR1983 = ""
Dim bSTR1984
bSTR1984 = ""
Dim boolean992
settingRepository1.GetAttrInfo "VOLUME_ACCELERATION_OVER_PULSATION_Large", bSTR1983, bSTR1984, boolean992
'--------------------------------------------------
' Parameter 1 : (String) "VOLUME_ACCELERATION_OVER_PULSATION_Large"
' Parameter 2 : (String) "Default value"
' Parameter 3 : (String) "Unlocked"
' Parameter 4 : (Boolean) False
'--------------------------------------------------

long993 = settingRepository1.GetAttr("VOLUME_ACCELERATION_OVER_PULSATION_ExtraLarge")
'--------------------------------------------------
' Parameter 1 : (String) "VOLUME_ACCELERATION_OVER_PULSATION_ExtraLarge"
' Returned value : (Variant) (Long) 1
'--------------------------------------------------

Dim bSTR1985
bSTR1985 = ""
Dim bSTR1986
bSTR1986 = ""
Dim boolean993
settingRepository1.GetAttrInfo "VOLUME_ACCELERATION_OVER_PULSATION_ExtraLarge", bSTR1985, bSTR1986, boolean993
'--------------------------------------------------
' Parameter 1 : (String) "VOLUME_ACCELERATION_OVER_PULSATION_ExtraLarge"
' Parameter 2 : (String) "Default value"
' Parameter 3 : (String) "Unlocked"
' Parameter 4 : (Boolean) False
'--------------------------------------------------

long994 = settingRepository1.GetAttr("VOLUME_ACCELERATION_OVER_PULSATION_Small")
'--------------------------------------------------
' Parameter 1 : (String) "VOLUME_ACCELERATION_OVER_PULSATION_Small"
' Returned value : (Variant) (Long) 1
'--------------------------------------------------

Dim bSTR1987
bSTR1987 = ""
Dim bSTR1988
bSTR1988 = ""
Dim boolean994
settingRepository1.GetAttrInfo "VOLUME_ACCELERATION_OVER_PULSATION_Small", bSTR1987, bSTR1988, boolean994
'--------------------------------------------------
' Parameter 1 : (String) "VOLUME_ACCELERATION_OVER_PULSATION_Small"
' Parameter 2 : (String) "Default value"
' Parameter 3 : (String) "Unlocked"
' Parameter 4 : (Boolean) False
'--------------------------------------------------

long995 = settingRepository1.GetAttr("VOLUME_ACCELERATION_OVER_PULSATION_ExtraSmall")
'--------------------------------------------------
' Parameter 1 : (String) "VOLUME_ACCELERATION_OVER_PULSATION_ExtraSmall"
' Returned value : (Variant) (Long) 1
'--------------------------------------------------

Dim bSTR1989
bSTR1989 = ""
Dim bSTR1990
bSTR1990 = ""
Dim boolean995
settingRepository1.GetAttrInfo "VOLUME_ACCELERATION_OVER_PULSATION_ExtraSmall", bSTR1989, bSTR1990, boolean995
'--------------------------------------------------
' Parameter 1 : (String) "VOLUME_ACCELERATION_OVER_PULSATION_ExtraSmall"
' Parameter 2 : (String) "Default value"
' Parameter 3 : (String) "Unlocked"
' Parameter 4 : (Boolean) False
'--------------------------------------------------

long996 = settingRepository1.GetAttr("VOLUME_ACCELERATION_OVER_PULSATION_Nanometric")
'--------------------------------------------------
' Parameter 1 : (String) "VOLUME_ACCELERATION_OVER_PULSATION_Nanometric"
' Returned value : (Variant) (Long) 1
'--------------------------------------------------

Dim bSTR1991
bSTR1991 = ""
Dim bSTR1992
bSTR1992 = ""
Dim boolean996
settingRepository1.GetAttrInfo "VOLUME_ACCELERATION_OVER_PULSATION_Nanometric", bSTR1991, bSTR1992, boolean996
'--------------------------------------------------
' Parameter 1 : (String) "VOLUME_ACCELERATION_OVER_PULSATION_Nanometric"
' Parameter 2 : (String) "Default value"
' Parameter 3 : (String) "Unlocked"
' Parameter 4 : (Boolean) False
'--------------------------------------------------

long997 = settingRepository1.GetAttr("VOLUME_VELOCITY_OVER_PULSATION")
'--------------------------------------------------
' Parameter 1 : (String) "VOLUME_VELOCITY_OVER_PULSATION"
' Returned value : (Variant) (Long) 1
'--------------------------------------------------

Dim bSTR1993
bSTR1993 = ""
Dim bSTR1994
bSTR1994 = ""
Dim boolean997
settingRepository1.GetAttrInfo "VOLUME_VELOCITY_OVER_PULSATION", bSTR1993, bSTR1994, boolean997
'--------------------------------------------------
' Parameter 1 : (String) "VOLUME_VELOCITY_OVER_PULSATION"
' Parameter 2 : (String) "Default value"
' Parameter 3 : (String) "Unlocked"
' Parameter 4 : (Boolean) False
'--------------------------------------------------

long998 = settingRepository1.GetAttr("VOLUME_VELOCITY_OVER_PULSATION_Large")
'--------------------------------------------------
' Parameter 1 : (String) "VOLUME_VELOCITY_OVER_PULSATION_Large"
' Returned value : (Variant) (Long) 1
'--------------------------------------------------

Dim bSTR1995
bSTR1995 = ""
Dim bSTR1996
bSTR1996 = ""
Dim boolean998
settingRepository1.GetAttrInfo "VOLUME_VELOCITY_OVER_PULSATION_Large", bSTR1995, bSTR1996, boolean998
'--------------------------------------------------
' Parameter 1 : (String) "VOLUME_VELOCITY_OVER_PULSATION_Large"
' Parameter 2 : (String) "Default value"
' Parameter 3 : (String) "Unlocked"
' Parameter 4 : (Boolean) False
'--------------------------------------------------

long999 = settingRepository1.GetAttr("VOLUME_VELOCITY_OVER_PULSATION_ExtraLarge")
'--------------------------------------------------
' Parameter 1 : (String) "VOLUME_VELOCITY_OVER_PULSATION_ExtraLarge"
' Returned value : (Variant) (Long) 1
'--------------------------------------------------

Dim bSTR1997
bSTR1997 = ""
Dim bSTR1998
bSTR1998 = ""
Dim boolean999
settingRepository1.GetAttrInfo "VOLUME_VELOCITY_OVER_PULSATION_ExtraLarge", bSTR1997, bSTR1998, boolean999
'--------------------------------------------------
' Parameter 1 : (String) "VOLUME_VELOCITY_OVER_PULSATION_ExtraLarge"
' Parameter 2 : (String) "Default value"
' Parameter 3 : (String) "Unlocked"
' Parameter 4 : (Boolean) False
'--------------------------------------------------

long1000 = settingRepository1.GetAttr("VOLUME_VELOCITY_OVER_PULSATION_Small")
'--------------------------------------------------
' Parameter 1 : (String) "VOLUME_VELOCITY_OVER_PULSATION_Small"
' Returned value : (Variant) (Long) 1
'--------------------------------------------------

Dim bSTR1999
bSTR1999 = ""
Dim bSTR2000
bSTR2000 = ""
Dim boolean1000
settingRepository1.GetAttrInfo "VOLUME_VELOCITY_OVER_PULSATION_Small", bSTR1999, bSTR2000, boolean1000
'--------------------------------------------------
' Parameter 1 : (String) "VOLUME_VELOCITY_OVER_PULSATION_Small"
' Parameter 2 : (String) "Default value"
' Parameter 3 : (String) "Unlocked"
' Parameter 4 : (Boolean) False
'--------------------------------------------------

long1001 = settingRepository1.GetAttr("VOLUME_VELOCITY_OVER_PULSATION_ExtraSmall")
'--------------------------------------------------
' Parameter 1 : (String) "VOLUME_VELOCITY_OVER_PULSATION_ExtraSmall"
' Returned value : (Variant) (Long) 1
'--------------------------------------------------

Dim bSTR2001
bSTR2001 = ""
Dim bSTR2002
bSTR2002 = ""
Dim boolean1001
settingRepository1.GetAttrInfo "VOLUME_VELOCITY_OVER_PULSATION_ExtraSmall", bSTR2001, bSTR2002, boolean1001
'--------------------------------------------------
' Parameter 1 : (String) "VOLUME_VELOCITY_OVER_PULSATION_ExtraSmall"
' Parameter 2 : (String) "Default value"
' Parameter 3 : (String) "Unlocked"
' Parameter 4 : (Boolean) False
'--------------------------------------------------

long1002 = settingRepository1.GetAttr("VOLUME_VELOCITY_OVER_PULSATION_Nanometric")
'--------------------------------------------------
' Parameter 1 : (String) "VOLUME_VELOCITY_OVER_PULSATION_Nanometric"
' Returned value : (Variant) (Long) 1
'--------------------------------------------------

Dim bSTR2003
bSTR2003 = ""
Dim bSTR2004
bSTR2004 = ""
Dim boolean1002
settingRepository1.GetAttrInfo "VOLUME_VELOCITY_OVER_PULSATION_Nanometric", bSTR2003, bSTR2004, boolean1002
'--------------------------------------------------
' Parameter 1 : (String) "VOLUME_VELOCITY_OVER_PULSATION_Nanometric"
' Parameter 2 : (String) "Default value"
' Parameter 3 : (String) "Unlocked"
' Parameter 4 : (Boolean) False
'--------------------------------------------------

long1003 = settingRepository1.GetAttr("POWER_SPECTRAL_DENSITY_PRESSURE")
'--------------------------------------------------
' Parameter 1 : (String) "POWER_SPECTRAL_DENSITY_PRESSURE"
' Returned value : (Variant) (Long) 1
'--------------------------------------------------

Dim bSTR2005
bSTR2005 = ""
Dim bSTR2006
bSTR2006 = ""
Dim boolean1003
settingRepository1.GetAttrInfo "POWER_SPECTRAL_DENSITY_PRESSURE", bSTR2005, bSTR2006, boolean1003
'--------------------------------------------------
' Parameter 1 : (String) "POWER_SPECTRAL_DENSITY_PRESSURE"
' Parameter 2 : (String) "Default value"
' Parameter 3 : (String) "Unlocked"
' Parameter 4 : (Boolean) False
'--------------------------------------------------

long1004 = settingRepository1.GetAttr("POWER_SPECTRAL_DENSITY_PRESSURE_Large")
'--------------------------------------------------
' Parameter 1 : (String) "POWER_SPECTRAL_DENSITY_PRESSURE_Large"
' Returned value : (Variant) (Long) 1
'--------------------------------------------------

Dim bSTR2007
bSTR2007 = ""
Dim bSTR2008
bSTR2008 = ""
Dim boolean1004
settingRepository1.GetAttrInfo "POWER_SPECTRAL_DENSITY_PRESSURE_Large", bSTR2007, bSTR2008, boolean1004
'--------------------------------------------------
' Parameter 1 : (String) "POWER_SPECTRAL_DENSITY_PRESSURE_Large"
' Parameter 2 : (String) "Default value"
' Parameter 3 : (String) "Unlocked"
' Parameter 4 : (Boolean) False
'--------------------------------------------------

long1005 = settingRepository1.GetAttr("POWER_SPECTRAL_DENSITY_PRESSURE_ExtraLarge")
'--------------------------------------------------
' Parameter 1 : (String) "POWER_SPECTRAL_DENSITY_PRESSURE_ExtraLarge"
' Returned value : (Variant) (Long) 1
'--------------------------------------------------

Dim bSTR2009
bSTR2009 = ""
Dim bSTR2010
bSTR2010 = ""
Dim boolean1005
settingRepository1.GetAttrInfo "POWER_SPECTRAL_DENSITY_PRESSURE_ExtraLarge", bSTR2009, bSTR2010, boolean1005
'--------------------------------------------------
' Parameter 1 : (String) "POWER_SPECTRAL_DENSITY_PRESSURE_ExtraLarge"
' Parameter 2 : (String) "Default value"
' Parameter 3 : (String) "Unlocked"
' Parameter 4 : (Boolean) False
'--------------------------------------------------

long1006 = settingRepository1.GetAttr("POWER_SPECTRAL_DENSITY_PRESSURE_Small")
'--------------------------------------------------
' Parameter 1 : (String) "POWER_SPECTRAL_DENSITY_PRESSURE_Small"
' Returned value : (Variant) (Long) 1
'--------------------------------------------------

Dim bSTR2011
bSTR2011 = ""
Dim bSTR2012
bSTR2012 = ""
Dim boolean1006
settingRepository1.GetAttrInfo "POWER_SPECTRAL_DENSITY_PRESSURE_Small", bSTR2011, bSTR2012, boolean1006
'--------------------------------------------------
' Parameter 1 : (String) "POWER_SPECTRAL_DENSITY_PRESSURE_Small"
' Parameter 2 : (String) "Default value"
' Parameter 3 : (String) "Unlocked"
' Parameter 4 : (Boolean) False
'--------------------------------------------------

long1007 = settingRepository1.GetAttr("POWER_SPECTRAL_DENSITY_PRESSURE_ExtraSmall")
'--------------------------------------------------
' Parameter 1 : (String) "POWER_SPECTRAL_DENSITY_PRESSURE_ExtraSmall"
' Returned value : (Variant) (Long) 1
'--------------------------------------------------

Dim bSTR2013
bSTR2013 = ""
Dim bSTR2014
bSTR2014 = ""
Dim boolean1007
settingRepository1.GetAttrInfo "POWER_SPECTRAL_DENSITY_PRESSURE_ExtraSmall", bSTR2013, bSTR2014, boolean1007
'--------------------------------------------------
' Parameter 1 : (String) "POWER_SPECTRAL_DENSITY_PRESSURE_ExtraSmall"
' Parameter 2 : (String) "Default value"
' Parameter 3 : (String) "Unlocked"
' Parameter 4 : (Boolean) False
'--------------------------------------------------

long1008 = settingRepository1.GetAttr("POWER_SPECTRAL_DENSITY_PRESSURE_Nanometric")
'--------------------------------------------------
' Parameter 1 : (String) "POWER_SPECTRAL_DENSITY_PRESSURE_Nanometric"
' Returned value : (Variant) (Long) 1
'--------------------------------------------------

Dim bSTR2015
bSTR2015 = ""
Dim bSTR2016
bSTR2016 = ""
Dim boolean1008
settingRepository1.GetAttrInfo "POWER_SPECTRAL_DENSITY_PRESSURE_Nanometric", bSTR2015, bSTR2016, boolean1008
'--------------------------------------------------
' Parameter 1 : (String) "POWER_SPECTRAL_DENSITY_PRESSURE_Nanometric"
' Parameter 2 : (String) "Default value"
' Parameter 3 : (String) "Unlocked"
' Parameter 4 : (Boolean) False
'--------------------------------------------------

long1009 = settingRepository1.GetAttr("POWER_SPECTRAL_DENSITY_DISPLACEMENT")
'--------------------------------------------------
' Parameter 1 : (String) "POWER_SPECTRAL_DENSITY_DISPLACEMENT"
' Returned value : (Variant) (Long) 1
'--------------------------------------------------

Dim bSTR2017
bSTR2017 = ""
Dim bSTR2018
bSTR2018 = ""
Dim boolean1009
settingRepository1.GetAttrInfo "POWER_SPECTRAL_DENSITY_DISPLACEMENT", bSTR2017, bSTR2018, boolean1009
'--------------------------------------------------
' Parameter 1 : (String) "POWER_SPECTRAL_DENSITY_DISPLACEMENT"
' Parameter 2 : (String) "Default value"
' Parameter 3 : (String) "Unlocked"
' Parameter 4 : (Boolean) False
'--------------------------------------------------

long1010 = settingRepository1.GetAttr("POWER_SPECTRAL_DENSITY_DISPLACEMENT_Large")
'--------------------------------------------------
' Parameter 1 : (String) "POWER_SPECTRAL_DENSITY_DISPLACEMENT_Large"
' Returned value : (Variant) (Long) 1
'--------------------------------------------------

Dim bSTR2019
bSTR2019 = ""
Dim bSTR2020
bSTR2020 = ""
Dim boolean1010
settingRepository1.GetAttrInfo "POWER_SPECTRAL_DENSITY_DISPLACEMENT_Large", bSTR2019, bSTR2020, boolean1010
'--------------------------------------------------
' Parameter 1 : (String) "POWER_SPECTRAL_DENSITY_DISPLACEMENT_Large"
' Parameter 2 : (String) "Default value"
' Parameter 3 : (String) "Unlocked"
' Parameter 4 : (Boolean) False
'--------------------------------------------------

long1011 = settingRepository1.GetAttr("POWER_SPECTRAL_DENSITY_DISPLACEMENT_ExtraLarge")
'--------------------------------------------------
' Parameter 1 : (String) "POWER_SPECTRAL_DENSITY_DISPLACEMENT_ExtraLarge"
' Returned value : (Variant) (Long) 1
'--------------------------------------------------

Dim bSTR2021
bSTR2021 = ""
Dim bSTR2022
bSTR2022 = ""
Dim boolean1011
settingRepository1.GetAttrInfo "POWER_SPECTRAL_DENSITY_DISPLACEMENT_ExtraLarge", bSTR2021, bSTR2022, boolean1011
'--------------------------------------------------
' Parameter 1 : (String) "POWER_SPECTRAL_DENSITY_DISPLACEMENT_ExtraLarge"
' Parameter 2 : (String) "Default value"
' Parameter 3 : (String) "Unlocked"
' Parameter 4 : (Boolean) False
'--------------------------------------------------

long1012 = settingRepository1.GetAttr("POWER_SPECTRAL_DENSITY_DISPLACEMENT_Small")
'--------------------------------------------------
' Parameter 1 : (String) "POWER_SPECTRAL_DENSITY_DISPLACEMENT_Small"
' Returned value : (Variant) (Long) 1
'--------------------------------------------------

Dim bSTR2023
bSTR2023 = ""
Dim bSTR2024
bSTR2024 = ""
Dim boolean1012
settingRepository1.GetAttrInfo "POWER_SPECTRAL_DENSITY_DISPLACEMENT_Small", bSTR2023, bSTR2024, boolean1012
'--------------------------------------------------
' Parameter 1 : (String) "POWER_SPECTRAL_DENSITY_DISPLACEMENT_Small"
' Parameter 2 : (String) "Default value"
' Parameter 3 : (String) "Unlocked"
' Parameter 4 : (Boolean) False
'--------------------------------------------------

long1013 = settingRepository1.GetAttr("POWER_SPECTRAL_DENSITY_DISPLACEMENT_ExtraSmall")
'--------------------------------------------------
' Parameter 1 : (String) "POWER_SPECTRAL_DENSITY_DISPLACEMENT_ExtraSmall"
' Returned value : (Variant) (Long) 1
'--------------------------------------------------

Dim bSTR2025
bSTR2025 = ""
Dim bSTR2026
bSTR2026 = ""
Dim boolean1013
settingRepository1.GetAttrInfo "POWER_SPECTRAL_DENSITY_DISPLACEMENT_ExtraSmall", bSTR2025, bSTR2026, boolean1013
'--------------------------------------------------
' Parameter 1 : (String) "POWER_SPECTRAL_DENSITY_DISPLACEMENT_ExtraSmall"
' Parameter 2 : (String) "Default value"
' Parameter 3 : (String) "Unlocked"
' Parameter 4 : (Boolean) False
'--------------------------------------------------

long1014 = settingRepository1.GetAttr("POWER_SPECTRAL_DENSITY_DISPLACEMENT_Nanometric")
'--------------------------------------------------
' Parameter 1 : (String) "POWER_SPECTRAL_DENSITY_DISPLACEMENT_Nanometric"
' Returned value : (Variant) (Long) 1
'--------------------------------------------------

Dim bSTR2027
bSTR2027 = ""
Dim bSTR2028
bSTR2028 = ""
Dim boolean1014
settingRepository1.GetAttrInfo "POWER_SPECTRAL_DENSITY_DISPLACEMENT_Nanometric", bSTR2027, bSTR2028, boolean1014
'--------------------------------------------------
' Parameter 1 : (String) "POWER_SPECTRAL_DENSITY_DISPLACEMENT_Nanometric"
' Parameter 2 : (String) "Default value"
' Parameter 3 : (String) "Unlocked"
' Parameter 4 : (Boolean) False
'--------------------------------------------------

long1015 = settingRepository1.GetAttr("POWER_SPECTRAL_DENSITY_VELOCITY")
'--------------------------------------------------
' Parameter 1 : (String) "POWER_SPECTRAL_DENSITY_VELOCITY"
' Returned value : (Variant) (Long) 1
'--------------------------------------------------

Dim bSTR2029
bSTR2029 = ""
Dim bSTR2030
bSTR2030 = ""
Dim boolean1015
settingRepository1.GetAttrInfo "POWER_SPECTRAL_DENSITY_VELOCITY", bSTR2029, bSTR2030, boolean1015
'--------------------------------------------------
' Parameter 1 : (String) "POWER_SPECTRAL_DENSITY_VELOCITY"
' Parameter 2 : (String) "Default value"
' Parameter 3 : (String) "Unlocked"
' Parameter 4 : (Boolean) False
'--------------------------------------------------

long1016 = settingRepository1.GetAttr("POWER_SPECTRAL_DENSITY_VELOCITY_Large")
'--------------------------------------------------
' Parameter 1 : (String) "POWER_SPECTRAL_DENSITY_VELOCITY_Large"
' Returned value : (Variant) (Long) 1
'--------------------------------------------------

Dim bSTR2031
bSTR2031 = ""
Dim bSTR2032
bSTR2032 = ""
Dim boolean1016
settingRepository1.GetAttrInfo "POWER_SPECTRAL_DENSITY_VELOCITY_Large", bSTR2031, bSTR2032, boolean1016
'--------------------------------------------------
' Parameter 1 : (String) "POWER_SPECTRAL_DENSITY_VELOCITY_Large"
' Parameter 2 : (String) "Default value"
' Parameter 3 : (String) "Unlocked"
' Parameter 4 : (Boolean) False
'--------------------------------------------------

long1017 = settingRepository1.GetAttr("POWER_SPECTRAL_DENSITY_VELOCITY_ExtraLarge")
'--------------------------------------------------
' Parameter 1 : (String) "POWER_SPECTRAL_DENSITY_VELOCITY_ExtraLarge"
' Returned value : (Variant) (Long) 1
'--------------------------------------------------

Dim bSTR2033
bSTR2033 = ""
Dim bSTR2034
bSTR2034 = ""
Dim boolean1017
settingRepository1.GetAttrInfo "POWER_SPECTRAL_DENSITY_VELOCITY_ExtraLarge", bSTR2033, bSTR2034, boolean1017
'--------------------------------------------------
' Parameter 1 : (String) "POWER_SPECTRAL_DENSITY_VELOCITY_ExtraLarge"
' Parameter 2 : (String) "Default value"
' Parameter 3 : (String) "Unlocked"
' Parameter 4 : (Boolean) False
'--------------------------------------------------

long1018 = settingRepository1.GetAttr("POWER_SPECTRAL_DENSITY_VELOCITY_Small")
'--------------------------------------------------
' Parameter 1 : (String) "POWER_SPECTRAL_DENSITY_VELOCITY_Small"
' Returned value : (Variant) (Long) 1
'--------------------------------------------------

Dim bSTR2035
bSTR2035 = ""
Dim bSTR2036
bSTR2036 = ""
Dim boolean1018
settingRepository1.GetAttrInfo "POWER_SPECTRAL_DENSITY_VELOCITY_Small", bSTR2035, bSTR2036, boolean1018
'--------------------------------------------------
' Parameter 1 : (String) "POWER_SPECTRAL_DENSITY_VELOCITY_Small"
' Parameter 2 : (String) "Default value"
' Parameter 3 : (String) "Unlocked"
' Parameter 4 : (Boolean) False
'--------------------------------------------------

long1019 = settingRepository1.GetAttr("POWER_SPECTRAL_DENSITY_VELOCITY_ExtraSmall")
'--------------------------------------------------
' Parameter 1 : (String) "POWER_SPECTRAL_DENSITY_VELOCITY_ExtraSmall"
' Returned value : (Variant) (Long) 1
'--------------------------------------------------

Dim bSTR2037
bSTR2037 = ""
Dim bSTR2038
bSTR2038 = ""
Dim boolean1019
settingRepository1.GetAttrInfo "POWER_SPECTRAL_DENSITY_VELOCITY_ExtraSmall", bSTR2037, bSTR2038, boolean1019
'--------------------------------------------------
' Parameter 1 : (String) "POWER_SPECTRAL_DENSITY_VELOCITY_ExtraSmall"
' Parameter 2 : (String) "Default value"
' Parameter 3 : (String) "Unlocked"
' Parameter 4 : (Boolean) False
'--------------------------------------------------

long1020 = settingRepository1.GetAttr("POWER_SPECTRAL_DENSITY_VELOCITY_Nanometric")
'--------------------------------------------------
' Parameter 1 : (String) "POWER_SPECTRAL_DENSITY_VELOCITY_Nanometric"
' Returned value : (Variant) (Long) 1
'--------------------------------------------------

Dim bSTR2039
bSTR2039 = ""
Dim bSTR2040
bSTR2040 = ""
Dim boolean1020
settingRepository1.GetAttrInfo "POWER_SPECTRAL_DENSITY_VELOCITY_Nanometric", bSTR2039, bSTR2040, boolean1020
'--------------------------------------------------
' Parameter 1 : (String) "POWER_SPECTRAL_DENSITY_VELOCITY_Nanometric"
' Parameter 2 : (String) "Default value"
' Parameter 3 : (String) "Unlocked"
' Parameter 4 : (Boolean) False
'--------------------------------------------------

long1021 = settingRepository1.GetAttr("POWER_SPECTRAL_DENSITY_ACCELERATION")
'--------------------------------------------------
' Parameter 1 : (String) "POWER_SPECTRAL_DENSITY_ACCELERATION"
' Returned value : (Variant) (Long) 1
'--------------------------------------------------

Dim bSTR2041
bSTR2041 = ""
Dim bSTR2042
bSTR2042 = ""
Dim boolean1021
settingRepository1.GetAttrInfo "POWER_SPECTRAL_DENSITY_ACCELERATION", bSTR2041, bSTR2042, boolean1021
'--------------------------------------------------
' Parameter 1 : (String) "POWER_SPECTRAL_DENSITY_ACCELERATION"
' Parameter 2 : (String) "Default value"
' Parameter 3 : (String) "Unlocked"
' Parameter 4 : (Boolean) False
'--------------------------------------------------

long1022 = settingRepository1.GetAttr("POWER_SPECTRAL_DENSITY_ACCELERATION_Large")
'--------------------------------------------------
' Parameter 1 : (String) "POWER_SPECTRAL_DENSITY_ACCELERATION_Large"
' Returned value : (Variant) (Long) 1
'--------------------------------------------------

Dim bSTR2043
bSTR2043 = ""
Dim bSTR2044
bSTR2044 = ""
Dim boolean1022
settingRepository1.GetAttrInfo "POWER_SPECTRAL_DENSITY_ACCELERATION_Large", bSTR2043, bSTR2044, boolean1022
'--------------------------------------------------
' Parameter 1 : (String) "POWER_SPECTRAL_DENSITY_ACCELERATION_Large"
' Parameter 2 : (String) "Default value"
' Parameter 3 : (String) "Unlocked"
' Parameter 4 : (Boolean) False
'--------------------------------------------------

long1023 = settingRepository1.GetAttr("POWER_SPECTRAL_DENSITY_ACCELERATION_ExtraLarge")
'--------------------------------------------------
' Parameter 1 : (String) "POWER_SPECTRAL_DENSITY_ACCELERATION_ExtraLarge"
' Returned value : (Variant) (Long) 1
'--------------------------------------------------

Dim bSTR2045
bSTR2045 = ""
Dim bSTR2046
bSTR2046 = ""
Dim boolean1023
settingRepository1.GetAttrInfo "POWER_SPECTRAL_DENSITY_ACCELERATION_ExtraLarge", bSTR2045, bSTR2046, boolean1023
'--------------------------------------------------
' Parameter 1 : (String) "POWER_SPECTRAL_DENSITY_ACCELERATION_ExtraLarge"
' Parameter 2 : (String) "Default value"
' Parameter 3 : (String) "Unlocked"
' Parameter 4 : (Boolean) False
'--------------------------------------------------

long1024 = settingRepository1.GetAttr("POWER_SPECTRAL_DENSITY_ACCELERATION_Small")
'--------------------------------------------------
' Parameter 1 : (String) "POWER_SPECTRAL_DENSITY_ACCELERATION_Small"
' Returned value : (Variant) (Long) 1
'--------------------------------------------------

Dim bSTR2047
bSTR2047 = ""
Dim bSTR2048
bSTR2048 = ""
Dim boolean1024
settingRepository1.GetAttrInfo "POWER_SPECTRAL_DENSITY_ACCELERATION_Small", bSTR2047, bSTR2048, boolean1024
'--------------------------------------------------
' Parameter 1 : (String) "POWER_SPECTRAL_DENSITY_ACCELERATION_Small"
' Parameter 2 : (String) "Default value"
' Parameter 3 : (String) "Unlocked"
' Parameter 4 : (Boolean) False
'--------------------------------------------------

long1025 = settingRepository1.GetAttr("POWER_SPECTRAL_DENSITY_ACCELERATION_ExtraSmall")
'--------------------------------------------------
' Parameter 1 : (String) "POWER_SPECTRAL_DENSITY_ACCELERATION_ExtraSmall"
' Returned value : (Variant) (Long) 1
'--------------------------------------------------

Dim bSTR2049
bSTR2049 = ""
Dim bSTR2050
bSTR2050 = ""
Dim boolean1025
settingRepository1.GetAttrInfo "POWER_SPECTRAL_DENSITY_ACCELERATION_ExtraSmall", bSTR2049, bSTR2050, boolean1025
'--------------------------------------------------
' Parameter 1 : (String) "POWER_SPECTRAL_DENSITY_ACCELERATION_ExtraSmall"
' Parameter 2 : (String) "Default value"
' Parameter 3 : (String) "Unlocked"
' Parameter 4 : (Boolean) False
'--------------------------------------------------

long1026 = settingRepository1.GetAttr("POWER_SPECTRAL_DENSITY_ACCELERATION_Nanometric")
'--------------------------------------------------
' Parameter 1 : (String) "POWER_SPECTRAL_DENSITY_ACCELERATION_Nanometric"
' Returned value : (Variant) (Long) 1
'--------------------------------------------------

Dim bSTR2051
bSTR2051 = ""
Dim bSTR2052
bSTR2052 = ""
Dim boolean1026
settingRepository1.GetAttrInfo "POWER_SPECTRAL_DENSITY_ACCELERATION_Nanometric", bSTR2051, bSTR2052, boolean1026
'--------------------------------------------------
' Parameter 1 : (String) "POWER_SPECTRAL_DENSITY_ACCELERATION_Nanometric"
' Parameter 2 : (String) "Default value"
' Parameter 3 : (String) "Unlocked"
' Parameter 4 : (Boolean) False
'--------------------------------------------------

long1027 = settingRepository1.GetAttr("POWER_SPECTRAL_DENSITY")
'--------------------------------------------------
' Parameter 1 : (String) "POWER_SPECTRAL_DENSITY"
' Returned value : (Variant) (Long) 1
'--------------------------------------------------

Dim bSTR2053
bSTR2053 = ""
Dim bSTR2054
bSTR2054 = ""
Dim boolean1027
settingRepository1.GetAttrInfo "POWER_SPECTRAL_DENSITY", bSTR2053, bSTR2054, boolean1027
'--------------------------------------------------
' Parameter 1 : (String) "POWER_SPECTRAL_DENSITY"
' Parameter 2 : (String) "Default value"
' Parameter 3 : (String) "Unlocked"
' Parameter 4 : (Boolean) False
'--------------------------------------------------

long1028 = settingRepository1.GetAttr("POWER_SPECTRAL_DENSITY_Large")
'--------------------------------------------------
' Parameter 1 : (String) "POWER_SPECTRAL_DENSITY_Large"
' Returned value : (Variant) (Long) 1
'--------------------------------------------------

Dim bSTR2055
bSTR2055 = ""
Dim bSTR2056
bSTR2056 = ""
Dim boolean1028
settingRepository1.GetAttrInfo "POWER_SPECTRAL_DENSITY_Large", bSTR2055, bSTR2056, boolean1028
'--------------------------------------------------
' Parameter 1 : (String) "POWER_SPECTRAL_DENSITY_Large"
' Parameter 2 : (String) "Default value"
' Parameter 3 : (String) "Unlocked"
' Parameter 4 : (Boolean) False
'--------------------------------------------------

long1029 = settingRepository1.GetAttr("POWER_SPECTRAL_DENSITY_ExtraLarge")
'--------------------------------------------------
' Parameter 1 : (String) "POWER_SPECTRAL_DENSITY_ExtraLarge"
' Returned value : (Variant) (Long) 1
'--------------------------------------------------

Dim bSTR2057
bSTR2057 = ""
Dim bSTR2058
bSTR2058 = ""
Dim boolean1029
settingRepository1.GetAttrInfo "POWER_SPECTRAL_DENSITY_ExtraLarge", bSTR2057, bSTR2058, boolean1029
'--------------------------------------------------
' Parameter 1 : (String) "POWER_SPECTRAL_DENSITY_ExtraLarge"
' Parameter 2 : (String) "Default value"
' Parameter 3 : (String) "Unlocked"
' Parameter 4 : (Boolean) False
'--------------------------------------------------

long1030 = settingRepository1.GetAttr("POWER_SPECTRAL_DENSITY_Small")
'--------------------------------------------------
' Parameter 1 : (String) "POWER_SPECTRAL_DENSITY_Small"
' Returned value : (Variant) (Long) 1
'--------------------------------------------------

Dim bSTR2059
bSTR2059 = ""
Dim bSTR2060
bSTR2060 = ""
Dim boolean1030
settingRepository1.GetAttrInfo "POWER_SPECTRAL_DENSITY_Small", bSTR2059, bSTR2060, boolean1030
'--------------------------------------------------
' Parameter 1 : (String) "POWER_SPECTRAL_DENSITY_Small"
' Parameter 2 : (String) "Default value"
' Parameter 3 : (String) "Unlocked"
' Parameter 4 : (Boolean) False
'--------------------------------------------------

long1031 = settingRepository1.GetAttr("POWER_SPECTRAL_DENSITY_ExtraSmall")
'--------------------------------------------------
' Parameter 1 : (String) "POWER_SPECTRAL_DENSITY_ExtraSmall"
' Returned value : (Variant) (Long) 1
'--------------------------------------------------

Dim bSTR2061
bSTR2061 = ""
Dim bSTR2062
bSTR2062 = ""
Dim boolean1031
settingRepository1.GetAttrInfo "POWER_SPECTRAL_DENSITY_ExtraSmall", bSTR2061, bSTR2062, boolean1031
'--------------------------------------------------
' Parameter 1 : (String) "POWER_SPECTRAL_DENSITY_ExtraSmall"
' Parameter 2 : (String) "Default value"
' Parameter 3 : (String) "Unlocked"
' Parameter 4 : (Boolean) False
'--------------------------------------------------

long1032 = settingRepository1.GetAttr("POWER_SPECTRAL_DENSITY_Nanometric")
'--------------------------------------------------
' Parameter 1 : (String) "POWER_SPECTRAL_DENSITY_Nanometric"
' Returned value : (Variant) (Long) 1
'--------------------------------------------------

Dim bSTR2063
bSTR2063 = ""
Dim bSTR2064
bSTR2064 = ""
Dim boolean1032
settingRepository1.GetAttrInfo "POWER_SPECTRAL_DENSITY_Nanometric", bSTR2063, bSTR2064, boolean1032
'--------------------------------------------------
' Parameter 1 : (String) "POWER_SPECTRAL_DENSITY_Nanometric"
' Parameter 2 : (String) "Default value"
' Parameter 3 : (String) "Unlocked"
' Parameter 4 : (Boolean) False
'--------------------------------------------------

long1033 = settingRepository1.GetAttr("ACCELERATIONXPRESSURE")
'--------------------------------------------------
' Parameter 1 : (String) "ACCELERATIONXPRESSURE"
' Returned value : (Variant) (Long) 1
'--------------------------------------------------

Dim bSTR2065
bSTR2065 = ""
Dim bSTR2066
bSTR2066 = ""
Dim boolean1033
settingRepository1.GetAttrInfo "ACCELERATIONXPRESSURE", bSTR2065, bSTR2066, boolean1033
'--------------------------------------------------
' Parameter 1 : (String) "ACCELERATIONXPRESSURE"
' Parameter 2 : (String) "Default value"
' Parameter 3 : (String) "Unlocked"
' Parameter 4 : (Boolean) False
'--------------------------------------------------

long1034 = settingRepository1.GetAttr("ACCELERATIONXPRESSURE_Large")
'--------------------------------------------------
' Parameter 1 : (String) "ACCELERATIONXPRESSURE_Large"
' Returned value : (Variant) (Long) 1
'--------------------------------------------------

Dim bSTR2067
bSTR2067 = ""
Dim bSTR2068
bSTR2068 = ""
Dim boolean1034
settingRepository1.GetAttrInfo "ACCELERATIONXPRESSURE_Large", bSTR2067, bSTR2068, boolean1034
'--------------------------------------------------
' Parameter 1 : (String) "ACCELERATIONXPRESSURE_Large"
' Parameter 2 : (String) "Default value"
' Parameter 3 : (String) "Unlocked"
' Parameter 4 : (Boolean) False
'--------------------------------------------------

long1035 = settingRepository1.GetAttr("ACCELERATIONXPRESSURE_ExtraLarge")
'--------------------------------------------------
' Parameter 1 : (String) "ACCELERATIONXPRESSURE_ExtraLarge"
' Returned value : (Variant) (Long) 1
'--------------------------------------------------

Dim bSTR2069
bSTR2069 = ""
Dim bSTR2070
bSTR2070 = ""
Dim boolean1035
settingRepository1.GetAttrInfo "ACCELERATIONXPRESSURE_ExtraLarge", bSTR2069, bSTR2070, boolean1035
'--------------------------------------------------
' Parameter 1 : (String) "ACCELERATIONXPRESSURE_ExtraLarge"
' Parameter 2 : (String) "Default value"
' Parameter 3 : (String) "Unlocked"
' Parameter 4 : (Boolean) False
'--------------------------------------------------

long1036 = settingRepository1.GetAttr("ACCELERATIONXPRESSURE_Small")
'--------------------------------------------------
' Parameter 1 : (String) "ACCELERATIONXPRESSURE_Small"
' Returned value : (Variant) (Long) 1
'--------------------------------------------------

Dim bSTR2071
bSTR2071 = ""
Dim bSTR2072
bSTR2072 = ""
Dim boolean1036
settingRepository1.GetAttrInfo "ACCELERATIONXPRESSURE_Small", bSTR2071, bSTR2072, boolean1036
'--------------------------------------------------
' Parameter 1 : (String) "ACCELERATIONXPRESSURE_Small"
' Parameter 2 : (String) "Default value"
' Parameter 3 : (String) "Unlocked"
' Parameter 4 : (Boolean) False
'--------------------------------------------------

long1037 = settingRepository1.GetAttr("ACCELERATIONXPRESSURE_ExtraSmall")
'--------------------------------------------------
' Parameter 1 : (String) "ACCELERATIONXPRESSURE_ExtraSmall"
' Returned value : (Variant) (Long) 1
'--------------------------------------------------

Dim bSTR2073
bSTR2073 = ""
Dim bSTR2074
bSTR2074 = ""
Dim boolean1037
settingRepository1.GetAttrInfo "ACCELERATIONXPRESSURE_ExtraSmall", bSTR2073, bSTR2074, boolean1037
'--------------------------------------------------
' Parameter 1 : (String) "ACCELERATIONXPRESSURE_ExtraSmall"
' Parameter 2 : (String) "Default value"
' Parameter 3 : (String) "Unlocked"
' Parameter 4 : (Boolean) False
'--------------------------------------------------

long1038 = settingRepository1.GetAttr("ACCELERATIONXPRESSURE_Nanometric")
'--------------------------------------------------
' Parameter 1 : (String) "ACCELERATIONXPRESSURE_Nanometric"
' Returned value : (Variant) (Long) 1
'--------------------------------------------------

Dim bSTR2075
bSTR2075 = ""
Dim bSTR2076
bSTR2076 = ""
Dim boolean1038
settingRepository1.GetAttrInfo "ACCELERATIONXPRESSURE_Nanometric", bSTR2075, bSTR2076, boolean1038
'--------------------------------------------------
' Parameter 1 : (String) "ACCELERATIONXPRESSURE_Nanometric"
' Parameter 2 : (String) "Default value"
' Parameter 3 : (String) "Unlocked"
' Parameter 4 : (Boolean) False
'--------------------------------------------------

long1039 = settingRepository1.GetAttr("VELOCITYXPRESSURE")
'--------------------------------------------------
' Parameter 1 : (String) "VELOCITYXPRESSURE"
' Returned value : (Variant) (Long) 1
'--------------------------------------------------

Dim bSTR2077
bSTR2077 = ""
Dim bSTR2078
bSTR2078 = ""
Dim boolean1039
settingRepository1.GetAttrInfo "VELOCITYXPRESSURE", bSTR2077, bSTR2078, boolean1039
'--------------------------------------------------
' Parameter 1 : (String) "VELOCITYXPRESSURE"
' Parameter 2 : (String) "Default value"
' Parameter 3 : (String) "Unlocked"
' Parameter 4 : (Boolean) False
'--------------------------------------------------

long1040 = settingRepository1.GetAttr("VELOCITYXPRESSURE_Large")
'--------------------------------------------------
' Parameter 1 : (String) "VELOCITYXPRESSURE_Large"
' Returned value : (Variant) (Long) 1
'--------------------------------------------------

Dim bSTR2079
bSTR2079 = ""
Dim bSTR2080
bSTR2080 = ""
Dim boolean1040
settingRepository1.GetAttrInfo "VELOCITYXPRESSURE_Large", bSTR2079, bSTR2080, boolean1040
'--------------------------------------------------
' Parameter 1 : (String) "VELOCITYXPRESSURE_Large"
' Parameter 2 : (String) "Default value"
' Parameter 3 : (String) "Unlocked"
' Parameter 4 : (Boolean) False
'--------------------------------------------------

long1041 = settingRepository1.GetAttr("VELOCITYXPRESSURE_ExtraLarge")
'--------------------------------------------------
' Parameter 1 : (String) "VELOCITYXPRESSURE_ExtraLarge"
' Returned value : (Variant) (Long) 1
'--------------------------------------------------

Dim bSTR2081
bSTR2081 = ""
Dim bSTR2082
bSTR2082 = ""
Dim boolean1041
settingRepository1.GetAttrInfo "VELOCITYXPRESSURE_ExtraLarge", bSTR2081, bSTR2082, boolean1041
'--------------------------------------------------
' Parameter 1 : (String) "VELOCITYXPRESSURE_ExtraLarge"
' Parameter 2 : (String) "Default value"
' Parameter 3 : (String) "Unlocked"
' Parameter 4 : (Boolean) False
'--------------------------------------------------

long1042 = settingRepository1.GetAttr("VELOCITYXPRESSURE_Small")
'--------------------------------------------------
' Parameter 1 : (String) "VELOCITYXPRESSURE_Small"
' Returned value : (Variant) (Long) 1
'--------------------------------------------------

Dim bSTR2083
bSTR2083 = ""
Dim bSTR2084
bSTR2084 = ""
Dim boolean1042
settingRepository1.GetAttrInfo "VELOCITYXPRESSURE_Small", bSTR2083, bSTR2084, boolean1042
'--------------------------------------------------
' Parameter 1 : (String) "VELOCITYXPRESSURE_Small"
' Parameter 2 : (String) "Default value"
' Parameter 3 : (String) "Unlocked"
' Parameter 4 : (Boolean) False
'--------------------------------------------------

long1043 = settingRepository1.GetAttr("VELOCITYXPRESSURE_ExtraSmall")
'--------------------------------------------------
' Parameter 1 : (String) "VELOCITYXPRESSURE_ExtraSmall"
' Returned value : (Variant) (Long) 1
'--------------------------------------------------

Dim bSTR2085
bSTR2085 = ""
Dim bSTR2086
bSTR2086 = ""
Dim boolean1043
settingRepository1.GetAttrInfo "VELOCITYXPRESSURE_ExtraSmall", bSTR2085, bSTR2086, boolean1043
'--------------------------------------------------
' Parameter 1 : (String) "VELOCITYXPRESSURE_ExtraSmall"
' Parameter 2 : (String) "Default value"
' Parameter 3 : (String) "Unlocked"
' Parameter 4 : (Boolean) False
'--------------------------------------------------

long1044 = settingRepository1.GetAttr("VELOCITYXPRESSURE_Nanometric")
'--------------------------------------------------
' Parameter 1 : (String) "VELOCITYXPRESSURE_Nanometric"
' Returned value : (Variant) (Long) 1
'--------------------------------------------------

Dim bSTR2087
bSTR2087 = ""
Dim bSTR2088
bSTR2088 = ""
Dim boolean1044
settingRepository1.GetAttrInfo "VELOCITYXPRESSURE_Nanometric", bSTR2087, bSTR2088, boolean1044
'--------------------------------------------------
' Parameter 1 : (String) "VELOCITYXPRESSURE_Nanometric"
' Parameter 2 : (String) "Default value"
' Parameter 3 : (String) "Unlocked"
' Parameter 4 : (Boolean) False
'--------------------------------------------------

long1045 = settingRepository1.GetAttr("ACCELERATIONXFORCE")
'--------------------------------------------------
' Parameter 1 : (String) "ACCELERATIONXFORCE"
' Returned value : (Variant) (Long) 1
'--------------------------------------------------

Dim bSTR2089
bSTR2089 = ""
Dim bSTR2090
bSTR2090 = ""
Dim boolean1045
settingRepository1.GetAttrInfo "ACCELERATIONXFORCE", bSTR2089, bSTR2090, boolean1045
'--------------------------------------------------
' Parameter 1 : (String) "ACCELERATIONXFORCE"
' Parameter 2 : (String) "Default value"
' Parameter 3 : (String) "Unlocked"
' Parameter 4 : (Boolean) False
'--------------------------------------------------

long1046 = settingRepository1.GetAttr("ACCELERATIONXFORCE_Large")
'--------------------------------------------------
' Parameter 1 : (String) "ACCELERATIONXFORCE_Large"
' Returned value : (Variant) (Long) 1
'--------------------------------------------------

Dim bSTR2091
bSTR2091 = ""
Dim bSTR2092
bSTR2092 = ""
Dim boolean1046
settingRepository1.GetAttrInfo "ACCELERATIONXFORCE_Large", bSTR2091, bSTR2092, boolean1046
'--------------------------------------------------
' Parameter 1 : (String) "ACCELERATIONXFORCE_Large"
' Parameter 2 : (String) "Default value"
' Parameter 3 : (String) "Unlocked"
' Parameter 4 : (Boolean) False
'--------------------------------------------------

long1047 = settingRepository1.GetAttr("ACCELERATIONXFORCE_ExtraLarge")
'--------------------------------------------------
' Parameter 1 : (String) "ACCELERATIONXFORCE_ExtraLarge"
' Returned value : (Variant) (Long) 1
'--------------------------------------------------

Dim bSTR2093
bSTR2093 = ""
Dim bSTR2094
bSTR2094 = ""
Dim boolean1047
settingRepository1.GetAttrInfo "ACCELERATIONXFORCE_ExtraLarge", bSTR2093, bSTR2094, boolean1047
'--------------------------------------------------
' Parameter 1 : (String) "ACCELERATIONXFORCE_ExtraLarge"
' Parameter 2 : (String) "Default value"
' Parameter 3 : (String) "Unlocked"
' Parameter 4 : (Boolean) False
'--------------------------------------------------

long1048 = settingRepository1.GetAttr("ACCELERATIONXFORCE_Small")
'--------------------------------------------------
' Parameter 1 : (String) "ACCELERATIONXFORCE_Small"
' Returned value : (Variant) (Long) 1
'--------------------------------------------------

Dim bSTR2095
bSTR2095 = ""
Dim bSTR2096
bSTR2096 = ""
Dim boolean1048
settingRepository1.GetAttrInfo "ACCELERATIONXFORCE_Small", bSTR2095, bSTR2096, boolean1048
'--------------------------------------------------
' Parameter 1 : (String) "ACCELERATIONXFORCE_Small"
' Parameter 2 : (String) "Default value"
' Parameter 3 : (String) "Unlocked"
' Parameter 4 : (Boolean) False
'--------------------------------------------------

long1049 = settingRepository1.GetAttr("ACCELERATIONXFORCE_ExtraSmall")
'--------------------------------------------------
' Parameter 1 : (String) "ACCELERATIONXFORCE_ExtraSmall"
' Returned value : (Variant) (Long) 1
'--------------------------------------------------

Dim bSTR2097
bSTR2097 = ""
Dim bSTR2098
bSTR2098 = ""
Dim boolean1049
settingRepository1.GetAttrInfo "ACCELERATIONXFORCE_ExtraSmall", bSTR2097, bSTR2098, boolean1049
'--------------------------------------------------
' Parameter 1 : (String) "ACCELERATIONXFORCE_ExtraSmall"
' Parameter 2 : (String) "Default value"
' Parameter 3 : (String) "Unlocked"
' Parameter 4 : (Boolean) False
'--------------------------------------------------

long1050 = settingRepository1.GetAttr("ACCELERATIONXFORCE_Nanometric")
'--------------------------------------------------
' Parameter 1 : (String) "ACCELERATIONXFORCE_Nanometric"
' Returned value : (Variant) (Long) 1
'--------------------------------------------------

Dim bSTR2099
bSTR2099 = ""
Dim bSTR2100
bSTR2100 = ""
Dim boolean1050
settingRepository1.GetAttrInfo "ACCELERATIONXFORCE_Nanometric", bSTR2099, bSTR2100, boolean1050
'--------------------------------------------------
' Parameter 1 : (String) "ACCELERATIONXFORCE_Nanometric"
' Parameter 2 : (String) "Default value"
' Parameter 3 : (String) "Unlocked"
' Parameter 4 : (Boolean) False
'--------------------------------------------------

long1051 = settingRepository1.GetAttr("VELOCITYXFORCE")
'--------------------------------------------------
' Parameter 1 : (String) "VELOCITYXFORCE"
' Returned value : (Variant) (Long) 1
'--------------------------------------------------

Dim bSTR2101
bSTR2101 = ""
Dim bSTR2102
bSTR2102 = ""
Dim boolean1051
settingRepository1.GetAttrInfo "VELOCITYXFORCE", bSTR2101, bSTR2102, boolean1051
'--------------------------------------------------
' Parameter 1 : (String) "VELOCITYXFORCE"
' Parameter 2 : (String) "Default value"
' Parameter 3 : (String) "Unlocked"
' Parameter 4 : (Boolean) False
'--------------------------------------------------

long1052 = settingRepository1.GetAttr("VELOCITYXFORCE_Large")
'--------------------------------------------------
' Parameter 1 : (String) "VELOCITYXFORCE_Large"
' Returned value : (Variant) (Long) 1
'--------------------------------------------------

Dim bSTR2103
bSTR2103 = ""
Dim bSTR2104
bSTR2104 = ""
Dim boolean1052
settingRepository1.GetAttrInfo "VELOCITYXFORCE_Large", bSTR2103, bSTR2104, boolean1052
'--------------------------------------------------
' Parameter 1 : (String) "VELOCITYXFORCE_Large"
' Parameter 2 : (String) "Default value"
' Parameter 3 : (String) "Unlocked"
' Parameter 4 : (Boolean) False
'--------------------------------------------------

long1053 = settingRepository1.GetAttr("VELOCITYXFORCE_ExtraLarge")
'--------------------------------------------------
' Parameter 1 : (String) "VELOCITYXFORCE_ExtraLarge"
' Returned value : (Variant) (Long) 1
'--------------------------------------------------

Dim bSTR2105
bSTR2105 = ""
Dim bSTR2106
bSTR2106 = ""
Dim boolean1053
settingRepository1.GetAttrInfo "VELOCITYXFORCE_ExtraLarge", bSTR2105, bSTR2106, boolean1053
'--------------------------------------------------
' Parameter 1 : (String) "VELOCITYXFORCE_ExtraLarge"
' Parameter 2 : (String) "Default value"
' Parameter 3 : (String) "Unlocked"
' Parameter 4 : (Boolean) False
'--------------------------------------------------

long1054 = settingRepository1.GetAttr("VELOCITYXFORCE_Small")
'--------------------------------------------------
' Parameter 1 : (String) "VELOCITYXFORCE_Small"
' Returned value : (Variant) (Long) 1
'--------------------------------------------------

Dim bSTR2107
bSTR2107 = ""
Dim bSTR2108
bSTR2108 = ""
Dim boolean1054
settingRepository1.GetAttrInfo "VELOCITYXFORCE_Small", bSTR2107, bSTR2108, boolean1054
'--------------------------------------------------
' Parameter 1 : (String) "VELOCITYXFORCE_Small"
' Parameter 2 : (String) "Default value"
' Parameter 3 : (String) "Unlocked"
' Parameter 4 : (Boolean) False
'--------------------------------------------------

long1055 = settingRepository1.GetAttr("VELOCITYXFORCE_ExtraSmall")
'--------------------------------------------------
' Parameter 1 : (String) "VELOCITYXFORCE_ExtraSmall"
' Returned value : (Variant) (Long) 1
'--------------------------------------------------

Dim bSTR2109
bSTR2109 = ""
Dim bSTR2110
bSTR2110 = ""
Dim boolean1055
settingRepository1.GetAttrInfo "VELOCITYXFORCE_ExtraSmall", bSTR2109, bSTR2110, boolean1055
'--------------------------------------------------
' Parameter 1 : (String) "VELOCITYXFORCE_ExtraSmall"
' Parameter 2 : (String) "Default value"
' Parameter 3 : (String) "Unlocked"
' Parameter 4 : (Boolean) False
'--------------------------------------------------

long1056 = settingRepository1.GetAttr("VELOCITYXFORCE_Nanometric")
'--------------------------------------------------
' Parameter 1 : (String) "VELOCITYXFORCE_Nanometric"
' Returned value : (Variant) (Long) 1
'--------------------------------------------------

Dim bSTR2111
bSTR2111 = ""
Dim bSTR2112
bSTR2112 = ""
Dim boolean1056
settingRepository1.GetAttrInfo "VELOCITYXFORCE_Nanometric", bSTR2111, bSTR2112, boolean1056
'--------------------------------------------------
' Parameter 1 : (String) "VELOCITYXFORCE_Nanometric"
' Parameter 2 : (String) "Default value"
' Parameter 3 : (String) "Unlocked"
' Parameter 4 : (Boolean) False
'--------------------------------------------------

long1057 = settingRepository1.GetAttr("PRESSUREXFORCE")
'--------------------------------------------------
' Parameter 1 : (String) "PRESSUREXFORCE"
' Returned value : (Variant) (Long) 1
'--------------------------------------------------

Dim bSTR2113
bSTR2113 = ""
Dim bSTR2114
bSTR2114 = ""
Dim boolean1057
settingRepository1.GetAttrInfo "PRESSUREXFORCE", bSTR2113, bSTR2114, boolean1057
'--------------------------------------------------
' Parameter 1 : (String) "PRESSUREXFORCE"
' Parameter 2 : (String) "Default value"
' Parameter 3 : (String) "Unlocked"
' Parameter 4 : (Boolean) False
'--------------------------------------------------

long1058 = settingRepository1.GetAttr("PRESSUREXFORCE_Large")
'--------------------------------------------------
' Parameter 1 : (String) "PRESSUREXFORCE_Large"
' Returned value : (Variant) (Long) 1
'--------------------------------------------------

Dim bSTR2115
bSTR2115 = ""
Dim bSTR2116
bSTR2116 = ""
Dim boolean1058
settingRepository1.GetAttrInfo "PRESSUREXFORCE_Large", bSTR2115, bSTR2116, boolean1058
'--------------------------------------------------
' Parameter 1 : (String) "PRESSUREXFORCE_Large"
' Parameter 2 : (String) "Default value"
' Parameter 3 : (String) "Unlocked"
' Parameter 4 : (Boolean) False
'--------------------------------------------------

long1059 = settingRepository1.GetAttr("PRESSUREXFORCE_ExtraLarge")
'--------------------------------------------------
' Parameter 1 : (String) "PRESSUREXFORCE_ExtraLarge"
' Returned value : (Variant) (Long) 1
'--------------------------------------------------

Dim bSTR2117
bSTR2117 = ""
Dim bSTR2118
bSTR2118 = ""
Dim boolean1059
settingRepository1.GetAttrInfo "PRESSUREXFORCE_ExtraLarge", bSTR2117, bSTR2118, boolean1059
'--------------------------------------------------
' Parameter 1 : (String) "PRESSUREXFORCE_ExtraLarge"
' Parameter 2 : (String) "Default value"
' Parameter 3 : (String) "Unlocked"
' Parameter 4 : (Boolean) False
'--------------------------------------------------

long1060 = settingRepository1.GetAttr("PRESSUREXFORCE_Small")
'--------------------------------------------------
' Parameter 1 : (String) "PRESSUREXFORCE_Small"
' Returned value : (Variant) (Long) 1
'--------------------------------------------------

Dim bSTR2119
bSTR2119 = ""
Dim bSTR2120
bSTR2120 = ""
Dim boolean1060
settingRepository1.GetAttrInfo "PRESSUREXFORCE_Small", bSTR2119, bSTR2120, boolean1060
'--------------------------------------------------
' Parameter 1 : (String) "PRESSUREXFORCE_Small"
' Parameter 2 : (String) "Default value"
' Parameter 3 : (String) "Unlocked"
' Parameter 4 : (Boolean) False
'--------------------------------------------------

long1061 = settingRepository1.GetAttr("PRESSUREXFORCE_ExtraSmall")
'--------------------------------------------------
' Parameter 1 : (String) "PRESSUREXFORCE_ExtraSmall"
' Returned value : (Variant) (Long) 1
'--------------------------------------------------

Dim bSTR2121
bSTR2121 = ""
Dim bSTR2122
bSTR2122 = ""
Dim boolean1061
settingRepository1.GetAttrInfo "PRESSUREXFORCE_ExtraSmall", bSTR2121, bSTR2122, boolean1061
'--------------------------------------------------
' Parameter 1 : (String) "PRESSUREXFORCE_ExtraSmall"
' Parameter 2 : (String) "Default value"
' Parameter 3 : (String) "Unlocked"
' Parameter 4 : (Boolean) False
'--------------------------------------------------

long1062 = settingRepository1.GetAttr("PRESSUREXFORCE_Nanometric")
'--------------------------------------------------
' Parameter 1 : (String) "PRESSUREXFORCE_Nanometric"
' Returned value : (Variant) (Long) 1
'--------------------------------------------------

Dim bSTR2123
bSTR2123 = ""
Dim bSTR2124
bSTR2124 = ""
Dim boolean1062
settingRepository1.GetAttrInfo "PRESSUREXFORCE_Nanometric", bSTR2123, bSTR2124, boolean1062
'--------------------------------------------------
' Parameter 1 : (String) "PRESSUREXFORCE_Nanometric"
' Parameter 2 : (String) "Default value"
' Parameter 3 : (String) "Unlocked"
' Parameter 4 : (Boolean) False
'--------------------------------------------------

long1063 = settingRepository1.GetAttr("ACCELERATIONXVOLUME_ACCELERATION")
'--------------------------------------------------
' Parameter 1 : (String) "ACCELERATIONXVOLUME_ACCELERATION"
' Returned value : (Variant) (Long) 1
'--------------------------------------------------

Dim bSTR2125
bSTR2125 = ""
Dim bSTR2126
bSTR2126 = ""
Dim boolean1063
settingRepository1.GetAttrInfo "ACCELERATIONXVOLUME_ACCELERATION", bSTR2125, bSTR2126, boolean1063
'--------------------------------------------------
' Parameter 1 : (String) "ACCELERATIONXVOLUME_ACCELERATION"
' Parameter 2 : (String) "Default value"
' Parameter 3 : (String) "Unlocked"
' Parameter 4 : (Boolean) False
'--------------------------------------------------

long1064 = settingRepository1.GetAttr("ACCELERATIONXVOLUME_ACCELERATION_Large")
'--------------------------------------------------
' Parameter 1 : (String) "ACCELERATIONXVOLUME_ACCELERATION_Large"
' Returned value : (Variant) (Long) 1
'--------------------------------------------------

Dim bSTR2127
bSTR2127 = ""
Dim bSTR2128
bSTR2128 = ""
Dim boolean1064
settingRepository1.GetAttrInfo "ACCELERATIONXVOLUME_ACCELERATION_Large", bSTR2127, bSTR2128, boolean1064
'--------------------------------------------------
' Parameter 1 : (String) "ACCELERATIONXVOLUME_ACCELERATION_Large"
' Parameter 2 : (String) "Default value"
' Parameter 3 : (String) "Unlocked"
' Parameter 4 : (Boolean) False
'--------------------------------------------------

long1065 = settingRepository1.GetAttr("ACCELERATIONXVOLUME_ACCELERATION_ExtraLarge")
'--------------------------------------------------
' Parameter 1 : (String) "ACCELERATIONXVOLUME_ACCELERATION_ExtraLarge"
' Returned value : (Variant) (Long) 1
'--------------------------------------------------

Dim bSTR2129
bSTR2129 = ""
Dim bSTR2130
bSTR2130 = ""
Dim boolean1065
settingRepository1.GetAttrInfo "ACCELERATIONXVOLUME_ACCELERATION_ExtraLarge", bSTR2129, bSTR2130, boolean1065
'--------------------------------------------------
' Parameter 1 : (String) "ACCELERATIONXVOLUME_ACCELERATION_ExtraLarge"
' Parameter 2 : (String) "Default value"
' Parameter 3 : (String) "Unlocked"
' Parameter 4 : (Boolean) False
'--------------------------------------------------

long1066 = settingRepository1.GetAttr("ACCELERATIONXVOLUME_ACCELERATION_Small")
'--------------------------------------------------
' Parameter 1 : (String) "ACCELERATIONXVOLUME_ACCELERATION_Small"
' Returned value : (Variant) (Long) 1
'--------------------------------------------------

Dim bSTR2131
bSTR2131 = ""
Dim bSTR2132
bSTR2132 = ""
Dim boolean1066
settingRepository1.GetAttrInfo "ACCELERATIONXVOLUME_ACCELERATION_Small", bSTR2131, bSTR2132, boolean1066
'--------------------------------------------------
' Parameter 1 : (String) "ACCELERATIONXVOLUME_ACCELERATION_Small"
' Parameter 2 : (String) "Default value"
' Parameter 3 : (String) "Unlocked"
' Parameter 4 : (Boolean) False
'--------------------------------------------------

long1067 = settingRepository1.GetAttr("ACCELERATIONXVOLUME_ACCELERATION_ExtraSmall")
'--------------------------------------------------
' Parameter 1 : (String) "ACCELERATIONXVOLUME_ACCELERATION_ExtraSmall"
' Returned value : (Variant) (Long) 1
'--------------------------------------------------

Dim bSTR2133
bSTR2133 = ""
Dim bSTR2134
bSTR2134 = ""
Dim boolean1067
settingRepository1.GetAttrInfo "ACCELERATIONXVOLUME_ACCELERATION_ExtraSmall", bSTR2133, bSTR2134, boolean1067
'--------------------------------------------------
' Parameter 1 : (String) "ACCELERATIONXVOLUME_ACCELERATION_ExtraSmall"
' Parameter 2 : (String) "Default value"
' Parameter 3 : (String) "Unlocked"
' Parameter 4 : (Boolean) False
'--------------------------------------------------

long1068 = settingRepository1.GetAttr("ACCELERATIONXVOLUME_ACCELERATION_Nanometric")
'--------------------------------------------------
' Parameter 1 : (String) "ACCELERATIONXVOLUME_ACCELERATION_Nanometric"
' Returned value : (Variant) (Long) 1
'--------------------------------------------------

Dim bSTR2135
bSTR2135 = ""
Dim bSTR2136
bSTR2136 = ""
Dim boolean1068
settingRepository1.GetAttrInfo "ACCELERATIONXVOLUME_ACCELERATION_Nanometric", bSTR2135, bSTR2136, boolean1068
'--------------------------------------------------
' Parameter 1 : (String) "ACCELERATIONXVOLUME_ACCELERATION_Nanometric"
' Parameter 2 : (String) "Default value"
' Parameter 3 : (String) "Unlocked"
' Parameter 4 : (Boolean) False
'--------------------------------------------------

long1069 = settingRepository1.GetAttr("VELOCITYXVOLUME_ACCELERATION")
'--------------------------------------------------
' Parameter 1 : (String) "VELOCITYXVOLUME_ACCELERATION"
' Returned value : (Variant) (Long) 1
'--------------------------------------------------

Dim bSTR2137
bSTR2137 = ""
Dim bSTR2138
bSTR2138 = ""
Dim boolean1069
settingRepository1.GetAttrInfo "VELOCITYXVOLUME_ACCELERATION", bSTR2137, bSTR2138, boolean1069
'--------------------------------------------------
' Parameter 1 : (String) "VELOCITYXVOLUME_ACCELERATION"
' Parameter 2 : (String) "Default value"
' Parameter 3 : (String) "Unlocked"
' Parameter 4 : (Boolean) False
'--------------------------------------------------

long1070 = settingRepository1.GetAttr("VELOCITYXVOLUME_ACCELERATION_Large")
'--------------------------------------------------
' Parameter 1 : (String) "VELOCITYXVOLUME_ACCELERATION_Large"
' Returned value : (Variant) (Long) 1
'--------------------------------------------------

Dim bSTR2139
bSTR2139 = ""
Dim bSTR2140
bSTR2140 = ""
Dim boolean1070
settingRepository1.GetAttrInfo "VELOCITYXVOLUME_ACCELERATION_Large", bSTR2139, bSTR2140, boolean1070
'--------------------------------------------------
' Parameter 1 : (String) "VELOCITYXVOLUME_ACCELERATION_Large"
' Parameter 2 : (String) "Default value"
' Parameter 3 : (String) "Unlocked"
' Parameter 4 : (Boolean) False
'--------------------------------------------------

long1071 = settingRepository1.GetAttr("VELOCITYXVOLUME_ACCELERATION_ExtraLarge")
'--------------------------------------------------
' Parameter 1 : (String) "VELOCITYXVOLUME_ACCELERATION_ExtraLarge"
' Returned value : (Variant) (Long) 1
'--------------------------------------------------

Dim bSTR2141
bSTR2141 = ""
Dim bSTR2142
bSTR2142 = ""
Dim boolean1071
settingRepository1.GetAttrInfo "VELOCITYXVOLUME_ACCELERATION_ExtraLarge", bSTR2141, bSTR2142, boolean1071
'--------------------------------------------------
' Parameter 1 : (String) "VELOCITYXVOLUME_ACCELERATION_ExtraLarge"
' Parameter 2 : (String) "Default value"
' Parameter 3 : (String) "Unlocked"
' Parameter 4 : (Boolean) False
'--------------------------------------------------

long1072 = settingRepository1.GetAttr("VELOCITYXVOLUME_ACCELERATION_Small")
'--------------------------------------------------
' Parameter 1 : (String) "VELOCITYXVOLUME_ACCELERATION_Small"
' Returned value : (Variant) (Long) 1
'--------------------------------------------------

Dim bSTR2143
bSTR2143 = ""
Dim bSTR2144
bSTR2144 = ""
Dim boolean1072
settingRepository1.GetAttrInfo "VELOCITYXVOLUME_ACCELERATION_Small", bSTR2143, bSTR2144, boolean1072
'--------------------------------------------------
' Parameter 1 : (String) "VELOCITYXVOLUME_ACCELERATION_Small"
' Parameter 2 : (String) "Default value"
' Parameter 3 : (String) "Unlocked"
' Parameter 4 : (Boolean) False
'--------------------------------------------------

long1073 = settingRepository1.GetAttr("VELOCITYXVOLUME_ACCELERATION_ExtraSmall")
'--------------------------------------------------
' Parameter 1 : (String) "VELOCITYXVOLUME_ACCELERATION_ExtraSmall"
' Returned value : (Variant) (Long) 1
'--------------------------------------------------

Dim bSTR2145
bSTR2145 = ""
Dim bSTR2146
bSTR2146 = ""
Dim boolean1073
settingRepository1.GetAttrInfo "VELOCITYXVOLUME_ACCELERATION_ExtraSmall", bSTR2145, bSTR2146, boolean1073
'--------------------------------------------------
' Parameter 1 : (String) "VELOCITYXVOLUME_ACCELERATION_ExtraSmall"
' Parameter 2 : (String) "Default value"
' Parameter 3 : (String) "Unlocked"
' Parameter 4 : (Boolean) False
'--------------------------------------------------

long1074 = settingRepository1.GetAttr("VELOCITYXVOLUME_ACCELERATION_Nanometric")
'--------------------------------------------------
' Parameter 1 : (String) "VELOCITYXVOLUME_ACCELERATION_Nanometric"
' Returned value : (Variant) (Long) 1
'--------------------------------------------------

Dim bSTR2147
bSTR2147 = ""
Dim bSTR2148
bSTR2148 = ""
Dim boolean1074
settingRepository1.GetAttrInfo "VELOCITYXVOLUME_ACCELERATION_Nanometric", bSTR2147, bSTR2148, boolean1074
'--------------------------------------------------
' Parameter 1 : (String) "VELOCITYXVOLUME_ACCELERATION_Nanometric"
' Parameter 2 : (String) "Default value"
' Parameter 3 : (String) "Unlocked"
' Parameter 4 : (Boolean) False
'--------------------------------------------------

long1075 = settingRepository1.GetAttr("DISPLACEMENTXVOLUME_ACCELERATION")
'--------------------------------------------------
' Parameter 1 : (String) "DISPLACEMENTXVOLUME_ACCELERATION"
' Returned value : (Variant) (Long) 1
'--------------------------------------------------

Dim bSTR2149
bSTR2149 = ""
Dim bSTR2150
bSTR2150 = ""
Dim boolean1075
settingRepository1.GetAttrInfo "DISPLACEMENTXVOLUME_ACCELERATION", bSTR2149, bSTR2150, boolean1075
'--------------------------------------------------
' Parameter 1 : (String) "DISPLACEMENTXVOLUME_ACCELERATION"
' Parameter 2 : (String) "Default value"
' Parameter 3 : (String) "Unlocked"
' Parameter 4 : (Boolean) False
'--------------------------------------------------

long1076 = settingRepository1.GetAttr("DISPLACEMENTXVOLUME_ACCELERATION_Large")
'--------------------------------------------------
' Parameter 1 : (String) "DISPLACEMENTXVOLUME_ACCELERATION_Large"
' Returned value : (Variant) (Long) 1
'--------------------------------------------------

Dim bSTR2151
bSTR2151 = ""
Dim bSTR2152
bSTR2152 = ""
Dim boolean1076
settingRepository1.GetAttrInfo "DISPLACEMENTXVOLUME_ACCELERATION_Large", bSTR2151, bSTR2152, boolean1076
'--------------------------------------------------
' Parameter 1 : (String) "DISPLACEMENTXVOLUME_ACCELERATION_Large"
' Parameter 2 : (String) "Default value"
' Parameter 3 : (String) "Unlocked"
' Parameter 4 : (Boolean) False
'--------------------------------------------------

long1077 = settingRepository1.GetAttr("DISPLACEMENTXVOLUME_ACCELERATION_ExtraLarge")
'--------------------------------------------------
' Parameter 1 : (String) "DISPLACEMENTXVOLUME_ACCELERATION_ExtraLarge"
' Returned value : (Variant) (Long) 1
'--------------------------------------------------

Dim bSTR2153
bSTR2153 = ""
Dim bSTR2154
bSTR2154 = ""
Dim boolean1077
settingRepository1.GetAttrInfo "DISPLACEMENTXVOLUME_ACCELERATION_ExtraLarge", bSTR2153, bSTR2154, boolean1077
'--------------------------------------------------
' Parameter 1 : (String) "DISPLACEMENTXVOLUME_ACCELERATION_ExtraLarge"
' Parameter 2 : (String) "Default value"
' Parameter 3 : (String) "Unlocked"
' Parameter 4 : (Boolean) False
'--------------------------------------------------

long1078 = settingRepository1.GetAttr("DISPLACEMENTXVOLUME_ACCELERATION_Small")
'--------------------------------------------------
' Parameter 1 : (String) "DISPLACEMENTXVOLUME_ACCELERATION_Small"
' Returned value : (Variant) (Long) 1
'--------------------------------------------------

Dim bSTR2155
bSTR2155 = ""
Dim bSTR2156
bSTR2156 = ""
Dim boolean1078
settingRepository1.GetAttrInfo "DISPLACEMENTXVOLUME_ACCELERATION_Small", bSTR2155, bSTR2156, boolean1078
'--------------------------------------------------
' Parameter 1 : (String) "DISPLACEMENTXVOLUME_ACCELERATION_Small"
' Parameter 2 : (String) "Default value"
' Parameter 3 : (String) "Unlocked"
' Parameter 4 : (Boolean) False
'--------------------------------------------------

long1079 = settingRepository1.GetAttr("DISPLACEMENTXVOLUME_ACCELERATION_ExtraSmall")
'--------------------------------------------------
' Parameter 1 : (String) "DISPLACEMENTXVOLUME_ACCELERATION_ExtraSmall"
' Returned value : (Variant) (Long) 1
'--------------------------------------------------

Dim bSTR2157
bSTR2157 = ""
Dim bSTR2158
bSTR2158 = ""
Dim boolean1079
settingRepository1.GetAttrInfo "DISPLACEMENTXVOLUME_ACCELERATION_ExtraSmall", bSTR2157, bSTR2158, boolean1079
'--------------------------------------------------
' Parameter 1 : (String) "DISPLACEMENTXVOLUME_ACCELERATION_ExtraSmall"
' Parameter 2 : (String) "Default value"
' Parameter 3 : (String) "Unlocked"
' Parameter 4 : (Boolean) False
'--------------------------------------------------

long1080 = settingRepository1.GetAttr("DISPLACEMENTXVOLUME_ACCELERATION_Nanometric")
'--------------------------------------------------
' Parameter 1 : (String) "DISPLACEMENTXVOLUME_ACCELERATION_Nanometric"
' Returned value : (Variant) (Long) 1
'--------------------------------------------------

Dim bSTR2159
bSTR2159 = ""
Dim bSTR2160
bSTR2160 = ""
Dim boolean1080
settingRepository1.GetAttrInfo "DISPLACEMENTXVOLUME_ACCELERATION_Nanometric", bSTR2159, bSTR2160, boolean1080
'--------------------------------------------------
' Parameter 1 : (String) "DISPLACEMENTXVOLUME_ACCELERATION_Nanometric"
' Parameter 2 : (String) "Default value"
' Parameter 3 : (String) "Unlocked"
' Parameter 4 : (Boolean) False
'--------------------------------------------------

long1081 = settingRepository1.GetAttr("DISPLACEMENTXVOLUME_VELOCITY")
'--------------------------------------------------
' Parameter 1 : (String) "DISPLACEMENTXVOLUME_VELOCITY"
' Returned value : (Variant) (Long) 1
'--------------------------------------------------

Dim bSTR2161
bSTR2161 = ""
Dim bSTR2162
bSTR2162 = ""
Dim boolean1081
settingRepository1.GetAttrInfo "DISPLACEMENTXVOLUME_VELOCITY", bSTR2161, bSTR2162, boolean1081
'--------------------------------------------------
' Parameter 1 : (String) "DISPLACEMENTXVOLUME_VELOCITY"
' Parameter 2 : (String) "Default value"
' Parameter 3 : (String) "Unlocked"
' Parameter 4 : (Boolean) False
'--------------------------------------------------

long1082 = settingRepository1.GetAttr("DISPLACEMENTXVOLUME_VELOCITY_Large")
'--------------------------------------------------
' Parameter 1 : (String) "DISPLACEMENTXVOLUME_VELOCITY_Large"
' Returned value : (Variant) (Long) 1
'--------------------------------------------------

Dim bSTR2163
bSTR2163 = ""
Dim bSTR2164
bSTR2164 = ""
Dim boolean1082
settingRepository1.GetAttrInfo "DISPLACEMENTXVOLUME_VELOCITY_Large", bSTR2163, bSTR2164, boolean1082
'--------------------------------------------------
' Parameter 1 : (String) "DISPLACEMENTXVOLUME_VELOCITY_Large"
' Parameter 2 : (String) "Default value"
' Parameter 3 : (String) "Unlocked"
' Parameter 4 : (Boolean) False
'--------------------------------------------------

long1083 = settingRepository1.GetAttr("DISPLACEMENTXVOLUME_VELOCITY_ExtraLarge")
'--------------------------------------------------
' Parameter 1 : (String) "DISPLACEMENTXVOLUME_VELOCITY_ExtraLarge"
' Returned value : (Variant) (Long) 1
'--------------------------------------------------

Dim bSTR2165
bSTR2165 = ""
Dim bSTR2166
bSTR2166 = ""
Dim boolean1083
settingRepository1.GetAttrInfo "DISPLACEMENTXVOLUME_VELOCITY_ExtraLarge", bSTR2165, bSTR2166, boolean1083
'--------------------------------------------------
' Parameter 1 : (String) "DISPLACEMENTXVOLUME_VELOCITY_ExtraLarge"
' Parameter 2 : (String) "Default value"
' Parameter 3 : (String) "Unlocked"
' Parameter 4 : (Boolean) False
'--------------------------------------------------

long1084 = settingRepository1.GetAttr("DISPLACEMENTXVOLUME_VELOCITY_Small")
'--------------------------------------------------
' Parameter 1 : (String) "DISPLACEMENTXVOLUME_VELOCITY_Small"
' Returned value : (Variant) (Long) 1
'--------------------------------------------------

Dim bSTR2167
bSTR2167 = ""
Dim bSTR2168
bSTR2168 = ""
Dim boolean1084
settingRepository1.GetAttrInfo "DISPLACEMENTXVOLUME_VELOCITY_Small", bSTR2167, bSTR2168, boolean1084
'--------------------------------------------------
' Parameter 1 : (String) "DISPLACEMENTXVOLUME_VELOCITY_Small"
' Parameter 2 : (String) "Default value"
' Parameter 3 : (String) "Unlocked"
' Parameter 4 : (Boolean) False
'--------------------------------------------------

long1085 = settingRepository1.GetAttr("DISPLACEMENTXVOLUME_VELOCITY_ExtraSmall")
'--------------------------------------------------
' Parameter 1 : (String) "DISPLACEMENTXVOLUME_VELOCITY_ExtraSmall"
' Returned value : (Variant) (Long) 1
'--------------------------------------------------

Dim bSTR2169
bSTR2169 = ""
Dim bSTR2170
bSTR2170 = ""
Dim boolean1085
settingRepository1.GetAttrInfo "DISPLACEMENTXVOLUME_VELOCITY_ExtraSmall", bSTR2169, bSTR2170, boolean1085
'--------------------------------------------------
' Parameter 1 : (String) "DISPLACEMENTXVOLUME_VELOCITY_ExtraSmall"
' Parameter 2 : (String) "Default value"
' Parameter 3 : (String) "Unlocked"
' Parameter 4 : (Boolean) False
'--------------------------------------------------

long1086 = settingRepository1.GetAttr("DISPLACEMENTXVOLUME_VELOCITY_Nanometric")
'--------------------------------------------------
' Parameter 1 : (String) "DISPLACEMENTXVOLUME_VELOCITY_Nanometric"
' Returned value : (Variant) (Long) 1
'--------------------------------------------------

Dim bSTR2171
bSTR2171 = ""
Dim bSTR2172
bSTR2172 = ""
Dim boolean1086
settingRepository1.GetAttrInfo "DISPLACEMENTXVOLUME_VELOCITY_Nanometric", bSTR2171, bSTR2172, boolean1086
'--------------------------------------------------
' Parameter 1 : (String) "DISPLACEMENTXVOLUME_VELOCITY_Nanometric"
' Parameter 2 : (String) "Default value"
' Parameter 3 : (String) "Unlocked"
' Parameter 4 : (Boolean) False
'--------------------------------------------------

long1087 = settingRepository1.GetAttr("ILLUMINATION")
'--------------------------------------------------
' Parameter 1 : (String) "ILLUMINATION"
' Returned value : (Variant) (Long) 1
'--------------------------------------------------

Dim bSTR2173
bSTR2173 = ""
Dim bSTR2174
bSTR2174 = ""
Dim boolean1087
settingRepository1.GetAttrInfo "ILLUMINATION", bSTR2173, bSTR2174, boolean1087
'--------------------------------------------------
' Parameter 1 : (String) "ILLUMINATION"
' Parameter 2 : (String) "Default value"
' Parameter 3 : (String) "Unlocked"
' Parameter 4 : (Boolean) False
'--------------------------------------------------

long1088 = settingRepository1.GetAttr("ILLUMINATION_Large")
'--------------------------------------------------
' Parameter 1 : (String) "ILLUMINATION_Large"
' Returned value : (Variant) (Long) 1
'--------------------------------------------------

Dim bSTR2175
bSTR2175 = ""
Dim bSTR2176
bSTR2176 = ""
Dim boolean1088
settingRepository1.GetAttrInfo "ILLUMINATION_Large", bSTR2175, bSTR2176, boolean1088
'--------------------------------------------------
' Parameter 1 : (String) "ILLUMINATION_Large"
' Parameter 2 : (String) "Default value"
' Parameter 3 : (String) "Unlocked"
' Parameter 4 : (Boolean) False
'--------------------------------------------------

long1089 = settingRepository1.GetAttr("ILLUMINATION_ExtraLarge")
'--------------------------------------------------
' Parameter 1 : (String) "ILLUMINATION_ExtraLarge"
' Returned value : (Variant) (Long) 1
'--------------------------------------------------

Dim bSTR2177
bSTR2177 = ""
Dim bSTR2178
bSTR2178 = ""
Dim boolean1089
settingRepository1.GetAttrInfo "ILLUMINATION_ExtraLarge", bSTR2177, bSTR2178, boolean1089
'--------------------------------------------------
' Parameter 1 : (String) "ILLUMINATION_ExtraLarge"
' Parameter 2 : (String) "Default value"
' Parameter 3 : (String) "Unlocked"
' Parameter 4 : (Boolean) False
'--------------------------------------------------

long1090 = settingRepository1.GetAttr("ILLUMINATION_Small")
'--------------------------------------------------
' Parameter 1 : (String) "ILLUMINATION_Small"
' Returned value : (Variant) (Long) 1
'--------------------------------------------------

Dim bSTR2179
bSTR2179 = ""
Dim bSTR2180
bSTR2180 = ""
Dim boolean1090
settingRepository1.GetAttrInfo "ILLUMINATION_Small", bSTR2179, bSTR2180, boolean1090
'--------------------------------------------------
' Parameter 1 : (String) "ILLUMINATION_Small"
' Parameter 2 : (String) "Default value"
' Parameter 3 : (String) "Unlocked"
' Parameter 4 : (Boolean) False
'--------------------------------------------------

long1091 = settingRepository1.GetAttr("ILLUMINATION_ExtraSmall")
'--------------------------------------------------
' Parameter 1 : (String) "ILLUMINATION_ExtraSmall"
' Returned value : (Variant) (Long) 1
'--------------------------------------------------

Dim bSTR2181
bSTR2181 = ""
Dim bSTR2182
bSTR2182 = ""
Dim boolean1091
settingRepository1.GetAttrInfo "ILLUMINATION_ExtraSmall", bSTR2181, bSTR2182, boolean1091
'--------------------------------------------------
' Parameter 1 : (String) "ILLUMINATION_ExtraSmall"
' Parameter 2 : (String) "Default value"
' Parameter 3 : (String) "Unlocked"
' Parameter 4 : (Boolean) False
'--------------------------------------------------

long1092 = settingRepository1.GetAttr("ILLUMINATION_Nanometric")
'--------------------------------------------------
' Parameter 1 : (String) "ILLUMINATION_Nanometric"
' Returned value : (Variant) (Long) 1
'--------------------------------------------------

Dim bSTR2183
bSTR2183 = ""
Dim bSTR2184
bSTR2184 = ""
Dim boolean1092
settingRepository1.GetAttrInfo "ILLUMINATION_Nanometric", bSTR2183, bSTR2184, boolean1092
'--------------------------------------------------
' Parameter 1 : (String) "ILLUMINATION_Nanometric"
' Parameter 2 : (String) "Default value"
' Parameter 3 : (String) "Unlocked"
' Parameter 4 : (Boolean) False
'--------------------------------------------------

long1093 = settingRepository1.GetAttr("LUMEN")
'--------------------------------------------------
' Parameter 1 : (String) "LUMEN"
' Returned value : (Variant) (Long) 1
'--------------------------------------------------

Dim bSTR2185
bSTR2185 = ""
Dim bSTR2186
bSTR2186 = ""
Dim boolean1093
settingRepository1.GetAttrInfo "LUMEN", bSTR2185, bSTR2186, boolean1093
'--------------------------------------------------
' Parameter 1 : (String) "LUMEN"
' Parameter 2 : (String) "Default value"
' Parameter 3 : (String) "Unlocked"
' Parameter 4 : (Boolean) False
'--------------------------------------------------

long1094 = settingRepository1.GetAttr("LUMEN_Large")
'--------------------------------------------------
' Parameter 1 : (String) "LUMEN_Large"
' Returned value : (Variant) (Long) 1
'--------------------------------------------------

Dim bSTR2187
bSTR2187 = ""
Dim bSTR2188
bSTR2188 = ""
Dim boolean1094
settingRepository1.GetAttrInfo "LUMEN_Large", bSTR2187, bSTR2188, boolean1094
'--------------------------------------------------
' Parameter 1 : (String) "LUMEN_Large"
' Parameter 2 : (String) "Default value"
' Parameter 3 : (String) "Unlocked"
' Parameter 4 : (Boolean) False
'--------------------------------------------------

long1095 = settingRepository1.GetAttr("LUMEN_ExtraLarge")
'--------------------------------------------------
' Parameter 1 : (String) "LUMEN_ExtraLarge"
' Returned value : (Variant) (Long) 1
'--------------------------------------------------

Dim bSTR2189
bSTR2189 = ""
Dim bSTR2190
bSTR2190 = ""
Dim boolean1095
settingRepository1.GetAttrInfo "LUMEN_ExtraLarge", bSTR2189, bSTR2190, boolean1095
'--------------------------------------------------
' Parameter 1 : (String) "LUMEN_ExtraLarge"
' Parameter 2 : (String) "Default value"
' Parameter 3 : (String) "Unlocked"
' Parameter 4 : (Boolean) False
'--------------------------------------------------

long1096 = settingRepository1.GetAttr("LUMEN_Small")
'--------------------------------------------------
' Parameter 1 : (String) "LUMEN_Small"
' Returned value : (Variant) (Long) 1
'--------------------------------------------------

Dim bSTR2191
bSTR2191 = ""
Dim bSTR2192
bSTR2192 = ""
Dim boolean1096
settingRepository1.GetAttrInfo "LUMEN_Small", bSTR2191, bSTR2192, boolean1096
'--------------------------------------------------
' Parameter 1 : (String) "LUMEN_Small"
' Parameter 2 : (String) "Default value"
' Parameter 3 : (String) "Unlocked"
' Parameter 4 : (Boolean) False
'--------------------------------------------------

long1097 = settingRepository1.GetAttr("LUMEN_ExtraSmall")
'--------------------------------------------------
' Parameter 1 : (String) "LUMEN_ExtraSmall"
' Returned value : (Variant) (Long) 1
'--------------------------------------------------

Dim bSTR2193
bSTR2193 = ""
Dim bSTR2194
bSTR2194 = ""
Dim boolean1097
settingRepository1.GetAttrInfo "LUMEN_ExtraSmall", bSTR2193, bSTR2194, boolean1097
'--------------------------------------------------
' Parameter 1 : (String) "LUMEN_ExtraSmall"
' Parameter 2 : (String) "Default value"
' Parameter 3 : (String) "Unlocked"
' Parameter 4 : (Boolean) False
'--------------------------------------------------

long1098 = settingRepository1.GetAttr("LUMEN_Nanometric")
'--------------------------------------------------
' Parameter 1 : (String) "LUMEN_Nanometric"
' Returned value : (Variant) (Long) 1
'--------------------------------------------------

Dim bSTR2195
bSTR2195 = ""
Dim bSTR2196
bSTR2196 = ""
Dim boolean1098
settingRepository1.GetAttrInfo "LUMEN_Nanometric", bSTR2195, bSTR2196, boolean1098
'--------------------------------------------------
' Parameter 1 : (String) "LUMEN_Nanometric"
' Parameter 2 : (String) "Default value"
' Parameter 3 : (String) "Unlocked"
' Parameter 4 : (Boolean) False
'--------------------------------------------------

long1099 = settingRepository1.GetAttr("INVERSE_TEMPRTRE")
'--------------------------------------------------
' Parameter 1 : (String) "INVERSE_TEMPRTRE"
' Returned value : (Variant) (Long) 1
'--------------------------------------------------

Dim bSTR2197
bSTR2197 = ""
Dim bSTR2198
bSTR2198 = ""
Dim boolean1099
settingRepository1.GetAttrInfo "INVERSE_TEMPRTRE", bSTR2197, bSTR2198, boolean1099
'--------------------------------------------------
' Parameter 1 : (String) "INVERSE_TEMPRTRE"
' Parameter 2 : (String) "Default value"
' Parameter 3 : (String) "Unlocked"
' Parameter 4 : (Boolean) False
'--------------------------------------------------

long1100 = settingRepository1.GetAttr("INVERSE_TEMPRTRE_Large")
'--------------------------------------------------
' Parameter 1 : (String) "INVERSE_TEMPRTRE_Large"
' Returned value : (Variant) (Long) 1
'--------------------------------------------------

Dim bSTR2199
bSTR2199 = ""
Dim bSTR2200
bSTR2200 = ""
Dim boolean1100
settingRepository1.GetAttrInfo "INVERSE_TEMPRTRE_Large", bSTR2199, bSTR2200, boolean1100
'--------------------------------------------------
' Parameter 1 : (String) "INVERSE_TEMPRTRE_Large"
' Parameter 2 : (String) "Default value"
' Parameter 3 : (String) "Unlocked"
' Parameter 4 : (Boolean) False
'--------------------------------------------------

long1101 = settingRepository1.GetAttr("INVERSE_TEMPRTRE_ExtraLarge")
'--------------------------------------------------
' Parameter 1 : (String) "INVERSE_TEMPRTRE_ExtraLarge"
' Returned value : (Variant) (Long) 1
'--------------------------------------------------

Dim bSTR2201
bSTR2201 = ""
Dim bSTR2202
bSTR2202 = ""
Dim boolean1101
settingRepository1.GetAttrInfo "INVERSE_TEMPRTRE_ExtraLarge", bSTR2201, bSTR2202, boolean1101
'--------------------------------------------------
' Parameter 1 : (String) "INVERSE_TEMPRTRE_ExtraLarge"
' Parameter 2 : (String) "Default value"
' Parameter 3 : (String) "Unlocked"
' Parameter 4 : (Boolean) False
'--------------------------------------------------

long1102 = settingRepository1.GetAttr("INVERSE_TEMPRTRE_Small")
'--------------------------------------------------
' Parameter 1 : (String) "INVERSE_TEMPRTRE_Small"
' Returned value : (Variant) (Long) 1
'--------------------------------------------------

Dim bSTR2203
bSTR2203 = ""
Dim bSTR2204
bSTR2204 = ""
Dim boolean1102
settingRepository1.GetAttrInfo "INVERSE_TEMPRTRE_Small", bSTR2203, bSTR2204, boolean1102
'--------------------------------------------------
' Parameter 1 : (String) "INVERSE_TEMPRTRE_Small"
' Parameter 2 : (String) "Default value"
' Parameter 3 : (String) "Unlocked"
' Parameter 4 : (Boolean) False
'--------------------------------------------------

long1103 = settingRepository1.GetAttr("INVERSE_TEMPRTRE_ExtraSmall")
'--------------------------------------------------
' Parameter 1 : (String) "INVERSE_TEMPRTRE_ExtraSmall"
' Returned value : (Variant) (Long) 1
'--------------------------------------------------

Dim bSTR2205
bSTR2205 = ""
Dim bSTR2206
bSTR2206 = ""
Dim boolean1103
settingRepository1.GetAttrInfo "INVERSE_TEMPRTRE_ExtraSmall", bSTR2205, bSTR2206, boolean1103
'--------------------------------------------------
' Parameter 1 : (String) "INVERSE_TEMPRTRE_ExtraSmall"
' Parameter 2 : (String) "Default value"
' Parameter 3 : (String) "Unlocked"
' Parameter 4 : (Boolean) False
'--------------------------------------------------

long1104 = settingRepository1.GetAttr("INVERSE_TEMPRTRE_Nanometric")
'--------------------------------------------------
' Parameter 1 : (String) "INVERSE_TEMPRTRE_Nanometric"
' Returned value : (Variant) (Long) 1
'--------------------------------------------------

Dim bSTR2207
bSTR2207 = ""
Dim bSTR2208
bSTR2208 = ""
Dim boolean1104
settingRepository1.GetAttrInfo "INVERSE_TEMPRTRE_Nanometric", bSTR2207, bSTR2208, boolean1104
'--------------------------------------------------
' Parameter 1 : (String) "INVERSE_TEMPRTRE_Nanometric"
' Parameter 2 : (String) "Default value"
' Parameter 3 : (String) "Unlocked"
' Parameter 4 : (Boolean) False
'--------------------------------------------------

long1105 = settingRepository1.GetAttr("POWER_SPECTRAL_DENSITY_ROTATION")
'--------------------------------------------------
' Parameter 1 : (String) "POWER_SPECTRAL_DENSITY_ROTATION"
' Returned value : (Variant) (Long) 1
'--------------------------------------------------

Dim bSTR2209
bSTR2209 = ""
Dim bSTR2210
bSTR2210 = ""
Dim boolean1105
settingRepository1.GetAttrInfo "POWER_SPECTRAL_DENSITY_ROTATION", bSTR2209, bSTR2210, boolean1105
'--------------------------------------------------
' Parameter 1 : (String) "POWER_SPECTRAL_DENSITY_ROTATION"
' Parameter 2 : (String) "Default value"
' Parameter 3 : (String) "Unlocked"
' Parameter 4 : (Boolean) False
'--------------------------------------------------

long1106 = settingRepository1.GetAttr("POWER_SPECTRAL_DENSITY_ROTATION_Large")
'--------------------------------------------------
' Parameter 1 : (String) "POWER_SPECTRAL_DENSITY_ROTATION_Large"
' Returned value : (Variant) (Long) 1
'--------------------------------------------------

Dim bSTR2211
bSTR2211 = ""
Dim bSTR2212
bSTR2212 = ""
Dim boolean1106
settingRepository1.GetAttrInfo "POWER_SPECTRAL_DENSITY_ROTATION_Large", bSTR2211, bSTR2212, boolean1106
'--------------------------------------------------
' Parameter 1 : (String) "POWER_SPECTRAL_DENSITY_ROTATION_Large"
' Parameter 2 : (String) "Default value"
' Parameter 3 : (String) "Unlocked"
' Parameter 4 : (Boolean) False
'--------------------------------------------------

long1107 = settingRepository1.GetAttr("POWER_SPECTRAL_DENSITY_ROTATION_ExtraLarge")
'--------------------------------------------------
' Parameter 1 : (String) "POWER_SPECTRAL_DENSITY_ROTATION_ExtraLarge"
' Returned value : (Variant) (Long) 1
'--------------------------------------------------

Dim bSTR2213
bSTR2213 = ""
Dim bSTR2214
bSTR2214 = ""
Dim boolean1107
settingRepository1.GetAttrInfo "POWER_SPECTRAL_DENSITY_ROTATION_ExtraLarge", bSTR2213, bSTR2214, boolean1107
'--------------------------------------------------
' Parameter 1 : (String) "POWER_SPECTRAL_DENSITY_ROTATION_ExtraLarge"
' Parameter 2 : (String) "Default value"
' Parameter 3 : (String) "Unlocked"
' Parameter 4 : (Boolean) False
'--------------------------------------------------

long1108 = settingRepository1.GetAttr("POWER_SPECTRAL_DENSITY_ROTATION_Small")
'--------------------------------------------------
' Parameter 1 : (String) "POWER_SPECTRAL_DENSITY_ROTATION_Small"
' Returned value : (Variant) (Long) 1
'--------------------------------------------------

Dim bSTR2215
bSTR2215 = ""
Dim bSTR2216
bSTR2216 = ""
Dim boolean1108
settingRepository1.GetAttrInfo "POWER_SPECTRAL_DENSITY_ROTATION_Small", bSTR2215, bSTR2216, boolean1108
'--------------------------------------------------
' Parameter 1 : (String) "POWER_SPECTRAL_DENSITY_ROTATION_Small"
' Parameter 2 : (String) "Default value"
' Parameter 3 : (String) "Unlocked"
' Parameter 4 : (Boolean) False
'--------------------------------------------------

long1109 = settingRepository1.GetAttr("POWER_SPECTRAL_DENSITY_ROTATION_ExtraSmall")
'--------------------------------------------------
' Parameter 1 : (String) "POWER_SPECTRAL_DENSITY_ROTATION_ExtraSmall"
' Returned value : (Variant) (Long) 1
'--------------------------------------------------

Dim bSTR2217
bSTR2217 = ""
Dim bSTR2218
bSTR2218 = ""
Dim boolean1109
settingRepository1.GetAttrInfo "POWER_SPECTRAL_DENSITY_ROTATION_ExtraSmall", bSTR2217, bSTR2218, boolean1109
'--------------------------------------------------
' Parameter 1 : (String) "POWER_SPECTRAL_DENSITY_ROTATION_ExtraSmall"
' Parameter 2 : (String) "Default value"
' Parameter 3 : (String) "Unlocked"
' Parameter 4 : (Boolean) False
'--------------------------------------------------

long1110 = settingRepository1.GetAttr("POWER_SPECTRAL_DENSITY_ROTATION_Nanometric")
'--------------------------------------------------
' Parameter 1 : (String) "POWER_SPECTRAL_DENSITY_ROTATION_Nanometric"
' Returned value : (Variant) (Long) 1
'--------------------------------------------------

Dim bSTR2219
bSTR2219 = ""
Dim bSTR2220
bSTR2220 = ""
Dim boolean1110
settingRepository1.GetAttrInfo "POWER_SPECTRAL_DENSITY_ROTATION_Nanometric", bSTR2219, bSTR2220, boolean1110
'--------------------------------------------------
' Parameter 1 : (String) "POWER_SPECTRAL_DENSITY_ROTATION_Nanometric"
' Parameter 2 : (String) "Default value"
' Parameter 3 : (String) "Unlocked"
' Parameter 4 : (Boolean) False
'--------------------------------------------------

long1111 = settingRepository1.GetAttr("POWER_SPECTRAL_DENSITY_ROTATIONAL_VELOCITY")
'--------------------------------------------------
' Parameter 1 : (String) "POWER_SPECTRAL_DENSITY_ROTATIONAL_VELOCITY"
' Returned value : (Variant) (Long) 1
'--------------------------------------------------

Dim bSTR2221
bSTR2221 = ""
Dim bSTR2222
bSTR2222 = ""
Dim boolean1111
settingRepository1.GetAttrInfo "POWER_SPECTRAL_DENSITY_ROTATIONAL_VELOCITY", bSTR2221, bSTR2222, boolean1111
'--------------------------------------------------
' Parameter 1 : (String) "POWER_SPECTRAL_DENSITY_ROTATIONAL_VELOCITY"
' Parameter 2 : (String) "Default value"
' Parameter 3 : (String) "Unlocked"
' Parameter 4 : (Boolean) False
'--------------------------------------------------

long1112 = settingRepository1.GetAttr("POWER_SPECTRAL_DENSITY_ROTATIONAL_VELOCITY_Large")
'--------------------------------------------------
' Parameter 1 : (String) "POWER_SPECTRAL_DENSITY_ROTATIONAL_VELOCITY_Large"
' Returned value : (Variant) (Long) 1
'--------------------------------------------------

Dim bSTR2223
bSTR2223 = ""
Dim bSTR2224
bSTR2224 = ""
Dim boolean1112
settingRepository1.GetAttrInfo "POWER_SPECTRAL_DENSITY_ROTATIONAL_VELOCITY_Large", bSTR2223, bSTR2224, boolean1112
'--------------------------------------------------
' Parameter 1 : (String) "POWER_SPECTRAL_DENSITY_ROTATIONAL_VELOCITY_Large"
' Parameter 2 : (String) "Default value"
' Parameter 3 : (String) "Unlocked"
' Parameter 4 : (Boolean) False
'--------------------------------------------------

long1113 = settingRepository1.GetAttr("POWER_SPECTRAL_DENSITY_ROTATIONAL_VELOCITY_ExtraLarge")
'--------------------------------------------------
' Parameter 1 : (String) "POWER_SPECTRAL_DENSITY_ROTATIONAL_VELOCITY_ExtraLarge"
' Returned value : (Variant) (Long) 1
'--------------------------------------------------

Dim bSTR2225
bSTR2225 = ""
Dim bSTR2226
bSTR2226 = ""
Dim boolean1113
settingRepository1.GetAttrInfo "POWER_SPECTRAL_DENSITY_ROTATIONAL_VELOCITY_ExtraLarge", bSTR2225, bSTR2226, boolean1113
'--------------------------------------------------
' Parameter 1 : (String) "POWER_SPECTRAL_DENSITY_ROTATIONAL_VELOCITY_ExtraLarge"
' Parameter 2 : (String) "Default value"
' Parameter 3 : (String) "Unlocked"
' Parameter 4 : (Boolean) False
'--------------------------------------------------

long1114 = settingRepository1.GetAttr("POWER_SPECTRAL_DENSITY_ROTATIONAL_VELOCITY_Small")
'--------------------------------------------------
' Parameter 1 : (String) "POWER_SPECTRAL_DENSITY_ROTATIONAL_VELOCITY_Small"
' Returned value : (Variant) (Long) 1
'--------------------------------------------------

Dim bSTR2227
bSTR2227 = ""
Dim bSTR2228
bSTR2228 = ""
Dim boolean1114
settingRepository1.GetAttrInfo "POWER_SPECTRAL_DENSITY_ROTATIONAL_VELOCITY_Small", bSTR2227, bSTR2228, boolean1114
'--------------------------------------------------
' Parameter 1 : (String) "POWER_SPECTRAL_DENSITY_ROTATIONAL_VELOCITY_Small"
' Parameter 2 : (String) "Default value"
' Parameter 3 : (String) "Unlocked"
' Parameter 4 : (Boolean) False
'--------------------------------------------------

long1115 = settingRepository1.GetAttr("POWER_SPECTRAL_DENSITY_ROTATIONAL_VELOCITY_ExtraSmall")
'--------------------------------------------------
' Parameter 1 : (String) "POWER_SPECTRAL_DENSITY_ROTATIONAL_VELOCITY_ExtraSmall"
' Returned value : (Variant) (Long) 1
'--------------------------------------------------

Dim bSTR2229
bSTR2229 = ""
Dim bSTR2230
bSTR2230 = ""
Dim boolean1115
settingRepository1.GetAttrInfo "POWER_SPECTRAL_DENSITY_ROTATIONAL_VELOCITY_ExtraSmall", bSTR2229, bSTR2230, boolean1115
'--------------------------------------------------
' Parameter 1 : (String) "POWER_SPECTRAL_DENSITY_ROTATIONAL_VELOCITY_ExtraSmall"
' Parameter 2 : (String) "Default value"
' Parameter 3 : (String) "Unlocked"
' Parameter 4 : (Boolean) False
'--------------------------------------------------

long1116 = settingRepository1.GetAttr("POWER_SPECTRAL_DENSITY_ROTATIONAL_VELOCITY_Nanometric")
'--------------------------------------------------
' Parameter 1 : (String) "POWER_SPECTRAL_DENSITY_ROTATIONAL_VELOCITY_Nanometric"
' Returned value : (Variant) (Long) 1
'--------------------------------------------------

Dim bSTR2231
bSTR2231 = ""
Dim bSTR2232
bSTR2232 = ""
Dim boolean1116
settingRepository1.GetAttrInfo "POWER_SPECTRAL_DENSITY_ROTATIONAL_VELOCITY_Nanometric", bSTR2231, bSTR2232, boolean1116
'--------------------------------------------------
' Parameter 1 : (String) "POWER_SPECTRAL_DENSITY_ROTATIONAL_VELOCITY_Nanometric"
' Parameter 2 : (String) "Default value"
' Parameter 3 : (String) "Unlocked"
' Parameter 4 : (Boolean) False
'--------------------------------------------------

long1117 = settingRepository1.GetAttr("POWER_SPECTRAL_DENSITY_ROTATIONAL_ACCELERATION")
'--------------------------------------------------
' Parameter 1 : (String) "POWER_SPECTRAL_DENSITY_ROTATIONAL_ACCELERATION"
' Returned value : (Variant) (Long) 1
'--------------------------------------------------

Dim bSTR2233
bSTR2233 = ""
Dim bSTR2234
bSTR2234 = ""
Dim boolean1117
settingRepository1.GetAttrInfo "POWER_SPECTRAL_DENSITY_ROTATIONAL_ACCELERATION", bSTR2233, bSTR2234, boolean1117
'--------------------------------------------------
' Parameter 1 : (String) "POWER_SPECTRAL_DENSITY_ROTATIONAL_ACCELERATION"
' Parameter 2 : (String) "Default value"
' Parameter 3 : (String) "Unlocked"
' Parameter 4 : (Boolean) False
'--------------------------------------------------

long1118 = settingRepository1.GetAttr("POWER_SPECTRAL_DENSITY_ROTATIONAL_ACCELERATION_Large")
'--------------------------------------------------
' Parameter 1 : (String) "POWER_SPECTRAL_DENSITY_ROTATIONAL_ACCELERATION_Large"
' Returned value : (Variant) (Long) 1
'--------------------------------------------------

Dim bSTR2235
bSTR2235 = ""
Dim bSTR2236
bSTR2236 = ""
Dim boolean1118
settingRepository1.GetAttrInfo "POWER_SPECTRAL_DENSITY_ROTATIONAL_ACCELERATION_Large", bSTR2235, bSTR2236, boolean1118
'--------------------------------------------------
' Parameter 1 : (String) "POWER_SPECTRAL_DENSITY_ROTATIONAL_ACCELERATION_Large"
' Parameter 2 : (String) "Default value"
' Parameter 3 : (String) "Unlocked"
' Parameter 4 : (Boolean) False
'--------------------------------------------------

long1119 = settingRepository1.GetAttr("POWER_SPECTRAL_DENSITY_ROTATIONAL_ACCELERATION_ExtraLarge")
'--------------------------------------------------
' Parameter 1 : (String) "POWER_SPECTRAL_DENSITY_ROTATIONAL_ACCELERATION_ExtraLarge"
' Returned value : (Variant) (Long) 1
'--------------------------------------------------

Dim bSTR2237
bSTR2237 = ""
Dim bSTR2238
bSTR2238 = ""
Dim boolean1119
settingRepository1.GetAttrInfo "POWER_SPECTRAL_DENSITY_ROTATIONAL_ACCELERATION_ExtraLarge", bSTR2237, bSTR2238, boolean1119
'--------------------------------------------------
' Parameter 1 : (String) "POWER_SPECTRAL_DENSITY_ROTATIONAL_ACCELERATION_ExtraLarge"
' Parameter 2 : (String) "Default value"
' Parameter 3 : (String) "Unlocked"
' Parameter 4 : (Boolean) False
'--------------------------------------------------

long1120 = settingRepository1.GetAttr("POWER_SPECTRAL_DENSITY_ROTATIONAL_ACCELERATION_Small")
'--------------------------------------------------
' Parameter 1 : (String) "POWER_SPECTRAL_DENSITY_ROTATIONAL_ACCELERATION_Small"
' Returned value : (Variant) (Long) 1
'--------------------------------------------------

Dim bSTR2239
bSTR2239 = ""
Dim bSTR2240
bSTR2240 = ""
Dim boolean1120
settingRepository1.GetAttrInfo "POWER_SPECTRAL_DENSITY_ROTATIONAL_ACCELERATION_Small", bSTR2239, bSTR2240, boolean1120
'--------------------------------------------------
' Parameter 1 : (String) "POWER_SPECTRAL_DENSITY_ROTATIONAL_ACCELERATION_Small"
' Parameter 2 : (String) "Default value"
' Parameter 3 : (String) "Unlocked"
' Parameter 4 : (Boolean) False
'--------------------------------------------------

long1121 = settingRepository1.GetAttr("POWER_SPECTRAL_DENSITY_ROTATIONAL_ACCELERATION_ExtraSmall")
'--------------------------------------------------
' Parameter 1 : (String) "POWER_SPECTRAL_DENSITY_ROTATIONAL_ACCELERATION_ExtraSmall"
' Returned value : (Variant) (Long) 1
'--------------------------------------------------

Dim bSTR2241
bSTR2241 = ""
Dim bSTR2242
bSTR2242 = ""
Dim boolean1121
settingRepository1.GetAttrInfo "POWER_SPECTRAL_DENSITY_ROTATIONAL_ACCELERATION_ExtraSmall", bSTR2241, bSTR2242, boolean1121
'--------------------------------------------------
' Parameter 1 : (String) "POWER_SPECTRAL_DENSITY_ROTATIONAL_ACCELERATION_ExtraSmall"
' Parameter 2 : (String) "Default value"
' Parameter 3 : (String) "Unlocked"
' Parameter 4 : (Boolean) False
'--------------------------------------------------

long1122 = settingRepository1.GetAttr("POWER_SPECTRAL_DENSITY_ROTATIONAL_ACCELERATION_Nanometric")
'--------------------------------------------------
' Parameter 1 : (String) "POWER_SPECTRAL_DENSITY_ROTATIONAL_ACCELERATION_Nanometric"
' Returned value : (Variant) (Long) 1
'--------------------------------------------------

Dim bSTR2243
bSTR2243 = ""
Dim bSTR2244
bSTR2244 = ""
Dim boolean1122
settingRepository1.GetAttrInfo "POWER_SPECTRAL_DENSITY_ROTATIONAL_ACCELERATION_Nanometric", bSTR2243, bSTR2244, boolean1122
'--------------------------------------------------
' Parameter 1 : (String) "POWER_SPECTRAL_DENSITY_ROTATIONAL_ACCELERATION_Nanometric"
' Parameter 2 : (String) "Default value"
' Parameter 3 : (String) "Unlocked"
' Parameter 4 : (Boolean) False
'--------------------------------------------------

long1123 = settingRepository1.GetAttr("POWER_SPECTRAL_DENSITY_FORCE")
'--------------------------------------------------
' Parameter 1 : (String) "POWER_SPECTRAL_DENSITY_FORCE"
' Returned value : (Variant) (Long) 1
'--------------------------------------------------

Dim bSTR2245
bSTR2245 = ""
Dim bSTR2246
bSTR2246 = ""
Dim boolean1123
settingRepository1.GetAttrInfo "POWER_SPECTRAL_DENSITY_FORCE", bSTR2245, bSTR2246, boolean1123
'--------------------------------------------------
' Parameter 1 : (String) "POWER_SPECTRAL_DENSITY_FORCE"
' Parameter 2 : (String) "Default value"
' Parameter 3 : (String) "Unlocked"
' Parameter 4 : (Boolean) False
'--------------------------------------------------

long1124 = settingRepository1.GetAttr("POWER_SPECTRAL_DENSITY_FORCE_Large")
'--------------------------------------------------
' Parameter 1 : (String) "POWER_SPECTRAL_DENSITY_FORCE_Large"
' Returned value : (Variant) (Long) 1
'--------------------------------------------------

Dim bSTR2247
bSTR2247 = ""
Dim bSTR2248
bSTR2248 = ""
Dim boolean1124
settingRepository1.GetAttrInfo "POWER_SPECTRAL_DENSITY_FORCE_Large", bSTR2247, bSTR2248, boolean1124
'--------------------------------------------------
' Parameter 1 : (String) "POWER_SPECTRAL_DENSITY_FORCE_Large"
' Parameter 2 : (String) "Default value"
' Parameter 3 : (String) "Unlocked"
' Parameter 4 : (Boolean) False
'--------------------------------------------------

long1125 = settingRepository1.GetAttr("POWER_SPECTRAL_DENSITY_FORCE_ExtraLarge")
'--------------------------------------------------
' Parameter 1 : (String) "POWER_SPECTRAL_DENSITY_FORCE_ExtraLarge"
' Returned value : (Variant) (Long) 1
'--------------------------------------------------

Dim bSTR2249
bSTR2249 = ""
Dim bSTR2250
bSTR2250 = ""
Dim boolean1125
settingRepository1.GetAttrInfo "POWER_SPECTRAL_DENSITY_FORCE_ExtraLarge", bSTR2249, bSTR2250, boolean1125
'--------------------------------------------------
' Parameter 1 : (String) "POWER_SPECTRAL_DENSITY_FORCE_ExtraLarge"
' Parameter 2 : (String) "Default value"
' Parameter 3 : (String) "Unlocked"
' Parameter 4 : (Boolean) False
'--------------------------------------------------

long1126 = settingRepository1.GetAttr("POWER_SPECTRAL_DENSITY_FORCE_Small")
'--------------------------------------------------
' Parameter 1 : (String) "POWER_SPECTRAL_DENSITY_FORCE_Small"
' Returned value : (Variant) (Long) 1
'--------------------------------------------------

Dim bSTR2251
bSTR2251 = ""
Dim bSTR2252
bSTR2252 = ""
Dim boolean1126
settingRepository1.GetAttrInfo "POWER_SPECTRAL_DENSITY_FORCE_Small", bSTR2251, bSTR2252, boolean1126
'--------------------------------------------------
' Parameter 1 : (String) "POWER_SPECTRAL_DENSITY_FORCE_Small"
' Parameter 2 : (String) "Default value"
' Parameter 3 : (String) "Unlocked"
' Parameter 4 : (Boolean) False
'--------------------------------------------------

long1127 = settingRepository1.GetAttr("POWER_SPECTRAL_DENSITY_FORCE_ExtraSmall")
'--------------------------------------------------
' Parameter 1 : (String) "POWER_SPECTRAL_DENSITY_FORCE_ExtraSmall"
' Returned value : (Variant) (Long) 1
'--------------------------------------------------

Dim bSTR2253
bSTR2253 = ""
Dim bSTR2254
bSTR2254 = ""
Dim boolean1127
settingRepository1.GetAttrInfo "POWER_SPECTRAL_DENSITY_FORCE_ExtraSmall", bSTR2253, bSTR2254, boolean1127
'--------------------------------------------------
' Parameter 1 : (String) "POWER_SPECTRAL_DENSITY_FORCE_ExtraSmall"
' Parameter 2 : (String) "Default value"
' Parameter 3 : (String) "Unlocked"
' Parameter 4 : (Boolean) False
'--------------------------------------------------

long1128 = settingRepository1.GetAttr("POWER_SPECTRAL_DENSITY_FORCE_Nanometric")
'--------------------------------------------------
' Parameter 1 : (String) "POWER_SPECTRAL_DENSITY_FORCE_Nanometric"
' Returned value : (Variant) (Long) 1
'--------------------------------------------------

Dim bSTR2255
bSTR2255 = ""
Dim bSTR2256
bSTR2256 = ""
Dim boolean1128
settingRepository1.GetAttrInfo "POWER_SPECTRAL_DENSITY_FORCE_Nanometric", bSTR2255, bSTR2256, boolean1128
'--------------------------------------------------
' Parameter 1 : (String) "POWER_SPECTRAL_DENSITY_FORCE_Nanometric"
' Parameter 2 : (String) "Default value"
' Parameter 3 : (String) "Unlocked"
' Parameter 4 : (Boolean) False
'--------------------------------------------------

long1129 = settingRepository1.GetAttr("POWER_SPECTRAL_DENSITY_MOMENT")
'--------------------------------------------------
' Parameter 1 : (String) "POWER_SPECTRAL_DENSITY_MOMENT"
' Returned value : (Variant) (Long) 1
'--------------------------------------------------

Dim bSTR2257
bSTR2257 = ""
Dim bSTR2258
bSTR2258 = ""
Dim boolean1129
settingRepository1.GetAttrInfo "POWER_SPECTRAL_DENSITY_MOMENT", bSTR2257, bSTR2258, boolean1129
'--------------------------------------------------
' Parameter 1 : (String) "POWER_SPECTRAL_DENSITY_MOMENT"
' Parameter 2 : (String) "Default value"
' Parameter 3 : (String) "Unlocked"
' Parameter 4 : (Boolean) False
'--------------------------------------------------

long1130 = settingRepository1.GetAttr("POWER_SPECTRAL_DENSITY_MOMENT_Large")
'--------------------------------------------------
' Parameter 1 : (String) "POWER_SPECTRAL_DENSITY_MOMENT_Large"
' Returned value : (Variant) (Long) 1
'--------------------------------------------------

Dim bSTR2259
bSTR2259 = ""
Dim bSTR2260
bSTR2260 = ""
Dim boolean1130
settingRepository1.GetAttrInfo "POWER_SPECTRAL_DENSITY_MOMENT_Large", bSTR2259, bSTR2260, boolean1130
'--------------------------------------------------
' Parameter 1 : (String) "POWER_SPECTRAL_DENSITY_MOMENT_Large"
' Parameter 2 : (String) "Default value"
' Parameter 3 : (String) "Unlocked"
' Parameter 4 : (Boolean) False
'--------------------------------------------------

long1131 = settingRepository1.GetAttr("POWER_SPECTRAL_DENSITY_MOMENT_ExtraLarge")
'--------------------------------------------------
' Parameter 1 : (String) "POWER_SPECTRAL_DENSITY_MOMENT_ExtraLarge"
' Returned value : (Variant) (Long) 1
'--------------------------------------------------

Dim bSTR2261
bSTR2261 = ""
Dim bSTR2262
bSTR2262 = ""
Dim boolean1131
settingRepository1.GetAttrInfo "POWER_SPECTRAL_DENSITY_MOMENT_ExtraLarge", bSTR2261, bSTR2262, boolean1131
'--------------------------------------------------
' Parameter 1 : (String) "POWER_SPECTRAL_DENSITY_MOMENT_ExtraLarge"
' Parameter 2 : (String) "Default value"
' Parameter 3 : (String) "Unlocked"
' Parameter 4 : (Boolean) False
'--------------------------------------------------

long1132 = settingRepository1.GetAttr("POWER_SPECTRAL_DENSITY_MOMENT_Small")
'--------------------------------------------------
' Parameter 1 : (String) "POWER_SPECTRAL_DENSITY_MOMENT_Small"
' Returned value : (Variant) (Long) 1
'--------------------------------------------------

Dim bSTR2263
bSTR2263 = ""
Dim bSTR2264
bSTR2264 = ""
Dim boolean1132
settingRepository1.GetAttrInfo "POWER_SPECTRAL_DENSITY_MOMENT_Small", bSTR2263, bSTR2264, boolean1132
'--------------------------------------------------
' Parameter 1 : (String) "POWER_SPECTRAL_DENSITY_MOMENT_Small"
' Parameter 2 : (String) "Default value"
' Parameter 3 : (String) "Unlocked"
' Parameter 4 : (Boolean) False
'--------------------------------------------------

long1133 = settingRepository1.GetAttr("POWER_SPECTRAL_DENSITY_MOMENT_ExtraSmall")
'--------------------------------------------------
' Parameter 1 : (String) "POWER_SPECTRAL_DENSITY_MOMENT_ExtraSmall"
' Returned value : (Variant) (Long) 1
'--------------------------------------------------

Dim bSTR2265
bSTR2265 = ""
Dim bSTR2266
bSTR2266 = ""
Dim boolean1133
settingRepository1.GetAttrInfo "POWER_SPECTRAL_DENSITY_MOMENT_ExtraSmall", bSTR2265, bSTR2266, boolean1133
'--------------------------------------------------
' Parameter 1 : (String) "POWER_SPECTRAL_DENSITY_MOMENT_ExtraSmall"
' Parameter 2 : (String) "Default value"
' Parameter 3 : (String) "Unlocked"
' Parameter 4 : (Boolean) False
'--------------------------------------------------

long1134 = settingRepository1.GetAttr("POWER_SPECTRAL_DENSITY_MOMENT_Nanometric")
'--------------------------------------------------
' Parameter 1 : (String) "POWER_SPECTRAL_DENSITY_MOMENT_Nanometric"
' Returned value : (Variant) (Long) 1
'--------------------------------------------------

Dim bSTR2267
bSTR2267 = ""
Dim bSTR2268
bSTR2268 = ""
Dim boolean1134
settingRepository1.GetAttrInfo "POWER_SPECTRAL_DENSITY_MOMENT_Nanometric", bSTR2267, bSTR2268, boolean1134
'--------------------------------------------------
' Parameter 1 : (String) "POWER_SPECTRAL_DENSITY_MOMENT_Nanometric"
' Parameter 2 : (String) "Default value"
' Parameter 3 : (String) "Unlocked"
' Parameter 4 : (Boolean) False
'--------------------------------------------------

long1135 = settingRepository1.GetAttr("PRESSURE_OVER_AREA")
'--------------------------------------------------
' Parameter 1 : (String) "PRESSURE_OVER_AREA"
' Returned value : (Variant) (Long) 1
'--------------------------------------------------

Dim bSTR2269
bSTR2269 = ""
Dim bSTR2270
bSTR2270 = ""
Dim boolean1135
settingRepository1.GetAttrInfo "PRESSURE_OVER_AREA", bSTR2269, bSTR2270, boolean1135
'--------------------------------------------------
' Parameter 1 : (String) "PRESSURE_OVER_AREA"
' Parameter 2 : (String) "Default value"
' Parameter 3 : (String) "Unlocked"
' Parameter 4 : (Boolean) False
'--------------------------------------------------

long1136 = settingRepository1.GetAttr("PRESSURE_OVER_AREA_Large")
'--------------------------------------------------
' Parameter 1 : (String) "PRESSURE_OVER_AREA_Large"
' Returned value : (Variant) (Long) 1
'--------------------------------------------------

Dim bSTR2271
bSTR2271 = ""
Dim bSTR2272
bSTR2272 = ""
Dim boolean1136
settingRepository1.GetAttrInfo "PRESSURE_OVER_AREA_Large", bSTR2271, bSTR2272, boolean1136
'--------------------------------------------------
' Parameter 1 : (String) "PRESSURE_OVER_AREA_Large"
' Parameter 2 : (String) "Default value"
' Parameter 3 : (String) "Unlocked"
' Parameter 4 : (Boolean) False
'--------------------------------------------------

long1137 = settingRepository1.GetAttr("PRESSURE_OVER_AREA_ExtraLarge")
'--------------------------------------------------
' Parameter 1 : (String) "PRESSURE_OVER_AREA_ExtraLarge"
' Returned value : (Variant) (Long) 1
'--------------------------------------------------

Dim bSTR2273
bSTR2273 = ""
Dim bSTR2274
bSTR2274 = ""
Dim boolean1137
settingRepository1.GetAttrInfo "PRESSURE_OVER_AREA_ExtraLarge", bSTR2273, bSTR2274, boolean1137
'--------------------------------------------------
' Parameter 1 : (String) "PRESSURE_OVER_AREA_ExtraLarge"
' Parameter 2 : (String) "Default value"
' Parameter 3 : (String) "Unlocked"
' Parameter 4 : (Boolean) False
'--------------------------------------------------

long1138 = settingRepository1.GetAttr("PRESSURE_OVER_AREA_Small")
'--------------------------------------------------
' Parameter 1 : (String) "PRESSURE_OVER_AREA_Small"
' Returned value : (Variant) (Long) 1
'--------------------------------------------------

Dim bSTR2275
bSTR2275 = ""
Dim bSTR2276
bSTR2276 = ""
Dim boolean1138
settingRepository1.GetAttrInfo "PRESSURE_OVER_AREA_Small", bSTR2275, bSTR2276, boolean1138
'--------------------------------------------------
' Parameter 1 : (String) "PRESSURE_OVER_AREA_Small"
' Parameter 2 : (String) "Default value"
' Parameter 3 : (String) "Unlocked"
' Parameter 4 : (Boolean) False
'--------------------------------------------------

long1139 = settingRepository1.GetAttr("PRESSURE_OVER_AREA_ExtraSmall")
'--------------------------------------------------
' Parameter 1 : (String) "PRESSURE_OVER_AREA_ExtraSmall"
' Returned value : (Variant) (Long) 1
'--------------------------------------------------

Dim bSTR2277
bSTR2277 = ""
Dim bSTR2278
bSTR2278 = ""
Dim boolean1139
settingRepository1.GetAttrInfo "PRESSURE_OVER_AREA_ExtraSmall", bSTR2277, bSTR2278, boolean1139
'--------------------------------------------------
' Parameter 1 : (String) "PRESSURE_OVER_AREA_ExtraSmall"
' Parameter 2 : (String) "Default value"
' Parameter 3 : (String) "Unlocked"
' Parameter 4 : (Boolean) False
'--------------------------------------------------

long1140 = settingRepository1.GetAttr("PRESSURE_OVER_AREA_Nanometric")
'--------------------------------------------------
' Parameter 1 : (String) "PRESSURE_OVER_AREA_Nanometric"
' Returned value : (Variant) (Long) 1
'--------------------------------------------------

Dim bSTR2279
bSTR2279 = ""
Dim bSTR2280
bSTR2280 = ""
Dim boolean1140
settingRepository1.GetAttrInfo "PRESSURE_OVER_AREA_Nanometric", bSTR2279, bSTR2280, boolean1140
'--------------------------------------------------
' Parameter 1 : (String) "PRESSURE_OVER_AREA_Nanometric"
' Parameter 2 : (String) "Default value"
' Parameter 3 : (String) "Unlocked"
' Parameter 4 : (Boolean) False
'--------------------------------------------------

long1141 = settingRepository1.GetAttr("INVERSE_SQUARE_PRESSURE")
'--------------------------------------------------
' Parameter 1 : (String) "INVERSE_SQUARE_PRESSURE"
' Returned value : (Variant) (Long) 1
'--------------------------------------------------

Dim bSTR2281
bSTR2281 = ""
Dim bSTR2282
bSTR2282 = ""
Dim boolean1141
settingRepository1.GetAttrInfo "INVERSE_SQUARE_PRESSURE", bSTR2281, bSTR2282, boolean1141
'--------------------------------------------------
' Parameter 1 : (String) "INVERSE_SQUARE_PRESSURE"
' Parameter 2 : (String) "Default value"
' Parameter 3 : (String) "Unlocked"
' Parameter 4 : (Boolean) False
'--------------------------------------------------

long1142 = settingRepository1.GetAttr("INVERSE_SQUARE_PRESSURE_Large")
'--------------------------------------------------
' Parameter 1 : (String) "INVERSE_SQUARE_PRESSURE_Large"
' Returned value : (Variant) (Long) 1
'--------------------------------------------------

Dim bSTR2283
bSTR2283 = ""
Dim bSTR2284
bSTR2284 = ""
Dim boolean1142
settingRepository1.GetAttrInfo "INVERSE_SQUARE_PRESSURE_Large", bSTR2283, bSTR2284, boolean1142
'--------------------------------------------------
' Parameter 1 : (String) "INVERSE_SQUARE_PRESSURE_Large"
' Parameter 2 : (String) "Default value"
' Parameter 3 : (String) "Unlocked"
' Parameter 4 : (Boolean) False
'--------------------------------------------------

long1143 = settingRepository1.GetAttr("INVERSE_SQUARE_PRESSURE_ExtraLarge")
'--------------------------------------------------
' Parameter 1 : (String) "INVERSE_SQUARE_PRESSURE_ExtraLarge"
' Returned value : (Variant) (Long) 1
'--------------------------------------------------

Dim bSTR2285
bSTR2285 = ""
Dim bSTR2286
bSTR2286 = ""
Dim boolean1143
settingRepository1.GetAttrInfo "INVERSE_SQUARE_PRESSURE_ExtraLarge", bSTR2285, bSTR2286, boolean1143
'--------------------------------------------------
' Parameter 1 : (String) "INVERSE_SQUARE_PRESSURE_ExtraLarge"
' Parameter 2 : (String) "Default value"
' Parameter 3 : (String) "Unlocked"
' Parameter 4 : (Boolean) False
'--------------------------------------------------

long1144 = settingRepository1.GetAttr("INVERSE_SQUARE_PRESSURE_Small")
'--------------------------------------------------
' Parameter 1 : (String) "INVERSE_SQUARE_PRESSURE_Small"
' Returned value : (Variant) (Long) 1
'--------------------------------------------------

Dim bSTR2287
bSTR2287 = ""
Dim bSTR2288
bSTR2288 = ""
Dim boolean1144
settingRepository1.GetAttrInfo "INVERSE_SQUARE_PRESSURE_Small", bSTR2287, bSTR2288, boolean1144
'--------------------------------------------------
' Parameter 1 : (String) "INVERSE_SQUARE_PRESSURE_Small"
' Parameter 2 : (String) "Default value"
' Parameter 3 : (String) "Unlocked"
' Parameter 4 : (Boolean) False
'--------------------------------------------------

long1145 = settingRepository1.GetAttr("INVERSE_SQUARE_PRESSURE_ExtraSmall")
'--------------------------------------------------
' Parameter 1 : (String) "INVERSE_SQUARE_PRESSURE_ExtraSmall"
' Returned value : (Variant) (Long) 1
'--------------------------------------------------

Dim bSTR2289
bSTR2289 = ""
Dim bSTR2290
bSTR2290 = ""
Dim boolean1145
settingRepository1.GetAttrInfo "INVERSE_SQUARE_PRESSURE_ExtraSmall", bSTR2289, bSTR2290, boolean1145
'--------------------------------------------------
' Parameter 1 : (String) "INVERSE_SQUARE_PRESSURE_ExtraSmall"
' Parameter 2 : (String) "Default value"
' Parameter 3 : (String) "Unlocked"
' Parameter 4 : (Boolean) False
'--------------------------------------------------

long1146 = settingRepository1.GetAttr("INVERSE_SQUARE_PRESSURE_Nanometric")
'--------------------------------------------------
' Parameter 1 : (String) "INVERSE_SQUARE_PRESSURE_Nanometric"
' Returned value : (Variant) (Long) 1
'--------------------------------------------------

Dim bSTR2291
bSTR2291 = ""
Dim bSTR2292
bSTR2292 = ""
Dim boolean1146
settingRepository1.GetAttrInfo "INVERSE_SQUARE_PRESSURE_Nanometric", bSTR2291, bSTR2292, boolean1146
'--------------------------------------------------
' Parameter 1 : (String) "INVERSE_SQUARE_PRESSURE_Nanometric"
' Parameter 2 : (String) "Default value"
' Parameter 3 : (String) "Unlocked"
' Parameter 4 : (Boolean) False
'--------------------------------------------------

long1147 = settingRepository1.GetAttr("PRESSUREXFORCE_OVER_FREQUENCY")
'--------------------------------------------------
' Parameter 1 : (String) "PRESSUREXFORCE_OVER_FREQUENCY"
' Returned value : (Variant) (Long) 1
'--------------------------------------------------

Dim bSTR2293
bSTR2293 = ""
Dim bSTR2294
bSTR2294 = ""
Dim boolean1147
settingRepository1.GetAttrInfo "PRESSUREXFORCE_OVER_FREQUENCY", bSTR2293, bSTR2294, boolean1147
'--------------------------------------------------
' Parameter 1 : (String) "PRESSUREXFORCE_OVER_FREQUENCY"
' Parameter 2 : (String) "Default value"
' Parameter 3 : (String) "Unlocked"
' Parameter 4 : (Boolean) False
'--------------------------------------------------

long1148 = settingRepository1.GetAttr("PRESSUREXFORCE_OVER_FREQUENCY_Large")
'--------------------------------------------------
' Parameter 1 : (String) "PRESSUREXFORCE_OVER_FREQUENCY_Large"
' Returned value : (Variant) (Long) 1
'--------------------------------------------------

Dim bSTR2295
bSTR2295 = ""
Dim bSTR2296
bSTR2296 = ""
Dim boolean1148
settingRepository1.GetAttrInfo "PRESSUREXFORCE_OVER_FREQUENCY_Large", bSTR2295, bSTR2296, boolean1148
'--------------------------------------------------
' Parameter 1 : (String) "PRESSUREXFORCE_OVER_FREQUENCY_Large"
' Parameter 2 : (String) "Default value"
' Parameter 3 : (String) "Unlocked"
' Parameter 4 : (Boolean) False
'--------------------------------------------------

long1149 = settingRepository1.GetAttr("PRESSUREXFORCE_OVER_FREQUENCY_ExtraLarge")
'--------------------------------------------------
' Parameter 1 : (String) "PRESSUREXFORCE_OVER_FREQUENCY_ExtraLarge"
' Returned value : (Variant) (Long) 1
'--------------------------------------------------

Dim bSTR2297
bSTR2297 = ""
Dim bSTR2298
bSTR2298 = ""
Dim boolean1149
settingRepository1.GetAttrInfo "PRESSUREXFORCE_OVER_FREQUENCY_ExtraLarge", bSTR2297, bSTR2298, boolean1149
'--------------------------------------------------
' Parameter 1 : (String) "PRESSUREXFORCE_OVER_FREQUENCY_ExtraLarge"
' Parameter 2 : (String) "Default value"
' Parameter 3 : (String) "Unlocked"
' Parameter 4 : (Boolean) False
'--------------------------------------------------

long1150 = settingRepository1.GetAttr("PRESSUREXFORCE_OVER_FREQUENCY_Small")
'--------------------------------------------------
' Parameter 1 : (String) "PRESSUREXFORCE_OVER_FREQUENCY_Small"
' Returned value : (Variant) (Long) 1
'--------------------------------------------------

Dim bSTR2299
bSTR2299 = ""
Dim bSTR2300
bSTR2300 = ""
Dim boolean1150
settingRepository1.GetAttrInfo "PRESSUREXFORCE_OVER_FREQUENCY_Small", bSTR2299, bSTR2300, boolean1150
'--------------------------------------------------
' Parameter 1 : (String) "PRESSUREXFORCE_OVER_FREQUENCY_Small"
' Parameter 2 : (String) "Default value"
' Parameter 3 : (String) "Unlocked"
' Parameter 4 : (Boolean) False
'--------------------------------------------------

long1151 = settingRepository1.GetAttr("PRESSUREXFORCE_OVER_FREQUENCY_ExtraSmall")
'--------------------------------------------------
' Parameter 1 : (String) "PRESSUREXFORCE_OVER_FREQUENCY_ExtraSmall"
' Returned value : (Variant) (Long) 1
'--------------------------------------------------

Dim bSTR2301
bSTR2301 = ""
Dim bSTR2302
bSTR2302 = ""
Dim boolean1151
settingRepository1.GetAttrInfo "PRESSUREXFORCE_OVER_FREQUENCY_ExtraSmall", bSTR2301, bSTR2302, boolean1151
'--------------------------------------------------
' Parameter 1 : (String) "PRESSUREXFORCE_OVER_FREQUENCY_ExtraSmall"
' Parameter 2 : (String) "Default value"
' Parameter 3 : (String) "Unlocked"
' Parameter 4 : (Boolean) False
'--------------------------------------------------

long1152 = settingRepository1.GetAttr("PRESSUREXFORCE_OVER_FREQUENCY_Nanometric")
'--------------------------------------------------
' Parameter 1 : (String) "PRESSUREXFORCE_OVER_FREQUENCY_Nanometric"
' Returned value : (Variant) (Long) 1
'--------------------------------------------------

Dim bSTR2303
bSTR2303 = ""
Dim bSTR2304
bSTR2304 = ""
Dim boolean1152
settingRepository1.GetAttrInfo "PRESSUREXFORCE_OVER_FREQUENCY_Nanometric", bSTR2303, bSTR2304, boolean1152
'--------------------------------------------------
' Parameter 1 : (String) "PRESSUREXFORCE_OVER_FREQUENCY_Nanometric"
' Parameter 2 : (String) "Default value"
' Parameter 3 : (String) "Unlocked"
' Parameter 4 : (Boolean) False
'--------------------------------------------------

long1153 = settingRepository1.GetAttr("DISPLACEMENTXFORCE_OVER_FREQUENCY")
'--------------------------------------------------
' Parameter 1 : (String) "DISPLACEMENTXFORCE_OVER_FREQUENCY"
' Returned value : (Variant) (Long) 1
'--------------------------------------------------

Dim bSTR2305
bSTR2305 = ""
Dim bSTR2306
bSTR2306 = ""
Dim boolean1153
settingRepository1.GetAttrInfo "DISPLACEMENTXFORCE_OVER_FREQUENCY", bSTR2305, bSTR2306, boolean1153
'--------------------------------------------------
' Parameter 1 : (String) "DISPLACEMENTXFORCE_OVER_FREQUENCY"
' Parameter 2 : (String) "Default value"
' Parameter 3 : (String) "Unlocked"
' Parameter 4 : (Boolean) False
'--------------------------------------------------

long1154 = settingRepository1.GetAttr("DISPLACEMENTXFORCE_OVER_FREQUENCY_Large")
'--------------------------------------------------
' Parameter 1 : (String) "DISPLACEMENTXFORCE_OVER_FREQUENCY_Large"
' Returned value : (Variant) (Long) 1
'--------------------------------------------------

Dim bSTR2307
bSTR2307 = ""
Dim bSTR2308
bSTR2308 = ""
Dim boolean1154
settingRepository1.GetAttrInfo "DISPLACEMENTXFORCE_OVER_FREQUENCY_Large", bSTR2307, bSTR2308, boolean1154
'--------------------------------------------------
' Parameter 1 : (String) "DISPLACEMENTXFORCE_OVER_FREQUENCY_Large"
' Parameter 2 : (String) "Default value"
' Parameter 3 : (String) "Unlocked"
' Parameter 4 : (Boolean) False
'--------------------------------------------------

long1155 = settingRepository1.GetAttr("DISPLACEMENTXFORCE_OVER_FREQUENCY_ExtraLarge")
'--------------------------------------------------
' Parameter 1 : (String) "DISPLACEMENTXFORCE_OVER_FREQUENCY_ExtraLarge"
' Returned value : (Variant) (Long) 1
'--------------------------------------------------

Dim bSTR2309
bSTR2309 = ""
Dim bSTR2310
bSTR2310 = ""
Dim boolean1155
settingRepository1.GetAttrInfo "DISPLACEMENTXFORCE_OVER_FREQUENCY_ExtraLarge", bSTR2309, bSTR2310, boolean1155
'--------------------------------------------------
' Parameter 1 : (String) "DISPLACEMENTXFORCE_OVER_FREQUENCY_ExtraLarge"
' Parameter 2 : (String) "Default value"
' Parameter 3 : (String) "Unlocked"
' Parameter 4 : (Boolean) False
'--------------------------------------------------

long1156 = settingRepository1.GetAttr("DISPLACEMENTXFORCE_OVER_FREQUENCY_Small")
'--------------------------------------------------
' Parameter 1 : (String) "DISPLACEMENTXFORCE_OVER_FREQUENCY_Small"
' Returned value : (Variant) (Long) 1
'--------------------------------------------------

Dim bSTR2311
bSTR2311 = ""
Dim bSTR2312
bSTR2312 = ""
Dim boolean1156
settingRepository1.GetAttrInfo "DISPLACEMENTXFORCE_OVER_FREQUENCY_Small", bSTR2311, bSTR2312, boolean1156
'--------------------------------------------------
' Parameter 1 : (String) "DISPLACEMENTXFORCE_OVER_FREQUENCY_Small"
' Parameter 2 : (String) "Default value"
' Parameter 3 : (String) "Unlocked"
' Parameter 4 : (Boolean) False
'--------------------------------------------------

long1157 = settingRepository1.GetAttr("DISPLACEMENTXFORCE_OVER_FREQUENCY_ExtraSmall")
'--------------------------------------------------
' Parameter 1 : (String) "DISPLACEMENTXFORCE_OVER_FREQUENCY_ExtraSmall"
' Returned value : (Variant) (Long) 1
'--------------------------------------------------

Dim bSTR2313
bSTR2313 = ""
Dim bSTR2314
bSTR2314 = ""
Dim boolean1157
settingRepository1.GetAttrInfo "DISPLACEMENTXFORCE_OVER_FREQUENCY_ExtraSmall", bSTR2313, bSTR2314, boolean1157
'--------------------------------------------------
' Parameter 1 : (String) "DISPLACEMENTXFORCE_OVER_FREQUENCY_ExtraSmall"
' Parameter 2 : (String) "Default value"
' Parameter 3 : (String) "Unlocked"
' Parameter 4 : (Boolean) False
'--------------------------------------------------

long1158 = settingRepository1.GetAttr("DISPLACEMENTXFORCE_OVER_FREQUENCY_Nanometric")
'--------------------------------------------------
' Parameter 1 : (String) "DISPLACEMENTXFORCE_OVER_FREQUENCY_Nanometric"
' Returned value : (Variant) (Long) 1
'--------------------------------------------------

Dim bSTR2315
bSTR2315 = ""
Dim bSTR2316
bSTR2316 = ""
Dim boolean1158
settingRepository1.GetAttrInfo "DISPLACEMENTXFORCE_OVER_FREQUENCY_Nanometric", bSTR2315, bSTR2316, boolean1158
'--------------------------------------------------
' Parameter 1 : (String) "DISPLACEMENTXFORCE_OVER_FREQUENCY_Nanometric"
' Parameter 2 : (String) "Default value"
' Parameter 3 : (String) "Unlocked"
' Parameter 4 : (Boolean) False
'--------------------------------------------------

long1159 = settingRepository1.GetAttr("SQUARE_VOLUME_VELOCITY_OVER_FREQUENCY")
'--------------------------------------------------
' Parameter 1 : (String) "SQUARE_VOLUME_VELOCITY_OVER_FREQUENCY"
' Returned value : (Variant) (Long) 1
'--------------------------------------------------

Dim bSTR2317
bSTR2317 = ""
Dim bSTR2318
bSTR2318 = ""
Dim boolean1159
settingRepository1.GetAttrInfo "SQUARE_VOLUME_VELOCITY_OVER_FREQUENCY", bSTR2317, bSTR2318, boolean1159
'--------------------------------------------------
' Parameter 1 : (String) "SQUARE_VOLUME_VELOCITY_OVER_FREQUENCY"
' Parameter 2 : (String) "Default value"
' Parameter 3 : (String) "Unlocked"
' Parameter 4 : (Boolean) False
'--------------------------------------------------

long1160 = settingRepository1.GetAttr("SQUARE_VOLUME_VELOCITY_OVER_FREQUENCY_Large")
'--------------------------------------------------
' Parameter 1 : (String) "SQUARE_VOLUME_VELOCITY_OVER_FREQUENCY_Large"
' Returned value : (Variant) (Long) 1
'--------------------------------------------------

Dim bSTR2319
bSTR2319 = ""
Dim bSTR2320
bSTR2320 = ""
Dim boolean1160
settingRepository1.GetAttrInfo "SQUARE_VOLUME_VELOCITY_OVER_FREQUENCY_Large", bSTR2319, bSTR2320, boolean1160
'--------------------------------------------------
' Parameter 1 : (String) "SQUARE_VOLUME_VELOCITY_OVER_FREQUENCY_Large"
' Parameter 2 : (String) "Default value"
' Parameter 3 : (String) "Unlocked"
' Parameter 4 : (Boolean) False
'--------------------------------------------------

long1161 = settingRepository1.GetAttr("SQUARE_VOLUME_VELOCITY_OVER_FREQUENCY_ExtraLarge")
'--------------------------------------------------
' Parameter 1 : (String) "SQUARE_VOLUME_VELOCITY_OVER_FREQUENCY_ExtraLarge"
' Returned value : (Variant) (Long) 1
'--------------------------------------------------

Dim bSTR2321
bSTR2321 = ""
Dim bSTR2322
bSTR2322 = ""
Dim boolean1161
settingRepository1.GetAttrInfo "SQUARE_VOLUME_VELOCITY_OVER_FREQUENCY_ExtraLarge", bSTR2321, bSTR2322, boolean1161
'--------------------------------------------------
' Parameter 1 : (String) "SQUARE_VOLUME_VELOCITY_OVER_FREQUENCY_ExtraLarge"
' Parameter 2 : (String) "Default value"
' Parameter 3 : (String) "Unlocked"
' Parameter 4 : (Boolean) False
'--------------------------------------------------

long1162 = settingRepository1.GetAttr("SQUARE_VOLUME_VELOCITY_OVER_FREQUENCY_Small")
'--------------------------------------------------
' Parameter 1 : (String) "SQUARE_VOLUME_VELOCITY_OVER_FREQUENCY_Small"
' Returned value : (Variant) (Long) 1
'--------------------------------------------------

Dim bSTR2323
bSTR2323 = ""
Dim bSTR2324
bSTR2324 = ""
Dim boolean1162
settingRepository1.GetAttrInfo "SQUARE_VOLUME_VELOCITY_OVER_FREQUENCY_Small", bSTR2323, bSTR2324, boolean1162
'--------------------------------------------------
' Parameter 1 : (String) "SQUARE_VOLUME_VELOCITY_OVER_FREQUENCY_Small"
' Parameter 2 : (String) "Default value"
' Parameter 3 : (String) "Unlocked"
' Parameter 4 : (Boolean) False
'--------------------------------------------------

long1163 = settingRepository1.GetAttr("SQUARE_VOLUME_VELOCITY_OVER_FREQUENCY_ExtraSmall")
'--------------------------------------------------
' Parameter 1 : (String) "SQUARE_VOLUME_VELOCITY_OVER_FREQUENCY_ExtraSmall"
' Returned value : (Variant) (Long) 1
'--------------------------------------------------

Dim bSTR2325
bSTR2325 = ""
Dim bSTR2326
bSTR2326 = ""
Dim boolean1163
settingRepository1.GetAttrInfo "SQUARE_VOLUME_VELOCITY_OVER_FREQUENCY_ExtraSmall", bSTR2325, bSTR2326, boolean1163
'--------------------------------------------------
' Parameter 1 : (String) "SQUARE_VOLUME_VELOCITY_OVER_FREQUENCY_ExtraSmall"
' Parameter 2 : (String) "Default value"
' Parameter 3 : (String) "Unlocked"
' Parameter 4 : (Boolean) False
'--------------------------------------------------

long1164 = settingRepository1.GetAttr("SQUARE_VOLUME_VELOCITY_OVER_FREQUENCY_Nanometric")
'--------------------------------------------------
' Parameter 1 : (String) "SQUARE_VOLUME_VELOCITY_OVER_FREQUENCY_Nanometric"
' Returned value : (Variant) (Long) 1
'--------------------------------------------------

Dim bSTR2327
bSTR2327 = ""
Dim bSTR2328
bSTR2328 = ""
Dim boolean1164
settingRepository1.GetAttrInfo "SQUARE_VOLUME_VELOCITY_OVER_FREQUENCY_Nanometric", bSTR2327, bSTR2328, boolean1164
'--------------------------------------------------
' Parameter 1 : (String) "SQUARE_VOLUME_VELOCITY_OVER_FREQUENCY_Nanometric"
' Parameter 2 : (String) "Default value"
' Parameter 3 : (String) "Unlocked"
' Parameter 4 : (Boolean) False
'--------------------------------------------------

long1165 = settingRepository1.GetAttr("SQUARE_VOLUME_ACCELERATION_OVER_FREQUENCY")
'--------------------------------------------------
' Parameter 1 : (String) "SQUARE_VOLUME_ACCELERATION_OVER_FREQUENCY"
' Returned value : (Variant) (Long) 1
'--------------------------------------------------

Dim bSTR2329
bSTR2329 = ""
Dim bSTR2330
bSTR2330 = ""
Dim boolean1165
settingRepository1.GetAttrInfo "SQUARE_VOLUME_ACCELERATION_OVER_FREQUENCY", bSTR2329, bSTR2330, boolean1165
'--------------------------------------------------
' Parameter 1 : (String) "SQUARE_VOLUME_ACCELERATION_OVER_FREQUENCY"
' Parameter 2 : (String) "Default value"
' Parameter 3 : (String) "Unlocked"
' Parameter 4 : (Boolean) False
'--------------------------------------------------

long1166 = settingRepository1.GetAttr("SQUARE_VOLUME_ACCELERATION_OVER_FREQUENCY_Large")
'--------------------------------------------------
' Parameter 1 : (String) "SQUARE_VOLUME_ACCELERATION_OVER_FREQUENCY_Large"
' Returned value : (Variant) (Long) 1
'--------------------------------------------------

Dim bSTR2331
bSTR2331 = ""
Dim bSTR2332
bSTR2332 = ""
Dim boolean1166
settingRepository1.GetAttrInfo "SQUARE_VOLUME_ACCELERATION_OVER_FREQUENCY_Large", bSTR2331, bSTR2332, boolean1166
'--------------------------------------------------
' Parameter 1 : (String) "SQUARE_VOLUME_ACCELERATION_OVER_FREQUENCY_Large"
' Parameter 2 : (String) "Default value"
' Parameter 3 : (String) "Unlocked"
' Parameter 4 : (Boolean) False
'--------------------------------------------------

long1167 = settingRepository1.GetAttr("SQUARE_VOLUME_ACCELERATION_OVER_FREQUENCY_ExtraLarge")
'--------------------------------------------------
' Parameter 1 : (String) "SQUARE_VOLUME_ACCELERATION_OVER_FREQUENCY_ExtraLarge"
' Returned value : (Variant) (Long) 1
'--------------------------------------------------

Dim bSTR2333
bSTR2333 = ""
Dim bSTR2334
bSTR2334 = ""
Dim boolean1167
settingRepository1.GetAttrInfo "SQUARE_VOLUME_ACCELERATION_OVER_FREQUENCY_ExtraLarge", bSTR2333, bSTR2334, boolean1167
'--------------------------------------------------
' Parameter 1 : (String) "SQUARE_VOLUME_ACCELERATION_OVER_FREQUENCY_ExtraLarge"
' Parameter 2 : (String) "Default value"
' Parameter 3 : (String) "Unlocked"
' Parameter 4 : (Boolean) False
'--------------------------------------------------

long1168 = settingRepository1.GetAttr("SQUARE_VOLUME_ACCELERATION_OVER_FREQUENCY_Small")
'--------------------------------------------------
' Parameter 1 : (String) "SQUARE_VOLUME_ACCELERATION_OVER_FREQUENCY_Small"
' Returned value : (Variant) (Long) 1
'--------------------------------------------------

Dim bSTR2335
bSTR2335 = ""
Dim bSTR2336
bSTR2336 = ""
Dim boolean1168
settingRepository1.GetAttrInfo "SQUARE_VOLUME_ACCELERATION_OVER_FREQUENCY_Small", bSTR2335, bSTR2336, boolean1168
'--------------------------------------------------
' Parameter 1 : (String) "SQUARE_VOLUME_ACCELERATION_OVER_FREQUENCY_Small"
' Parameter 2 : (String) "Default value"
' Parameter 3 : (String) "Unlocked"
' Parameter 4 : (Boolean) False
'--------------------------------------------------

long1169 = settingRepository1.GetAttr("SQUARE_VOLUME_ACCELERATION_OVER_FREQUENCY_ExtraSmall")
'--------------------------------------------------
' Parameter 1 : (String) "SQUARE_VOLUME_ACCELERATION_OVER_FREQUENCY_ExtraSmall"
' Returned value : (Variant) (Long) 1
'--------------------------------------------------

Dim bSTR2337
bSTR2337 = ""
Dim bSTR2338
bSTR2338 = ""
Dim boolean1169
settingRepository1.GetAttrInfo "SQUARE_VOLUME_ACCELERATION_OVER_FREQUENCY_ExtraSmall", bSTR2337, bSTR2338, boolean1169
'--------------------------------------------------
' Parameter 1 : (String) "SQUARE_VOLUME_ACCELERATION_OVER_FREQUENCY_ExtraSmall"
' Parameter 2 : (String) "Default value"
' Parameter 3 : (String) "Unlocked"
' Parameter 4 : (Boolean) False
'--------------------------------------------------

long1170 = settingRepository1.GetAttr("SQUARE_VOLUME_ACCELERATION_OVER_FREQUENCY_Nanometric")
'--------------------------------------------------
' Parameter 1 : (String) "SQUARE_VOLUME_ACCELERATION_OVER_FREQUENCY_Nanometric"
' Returned value : (Variant) (Long) 1
'--------------------------------------------------

Dim bSTR2339
bSTR2339 = ""
Dim bSTR2340
bSTR2340 = ""
Dim boolean1170
settingRepository1.GetAttrInfo "SQUARE_VOLUME_ACCELERATION_OVER_FREQUENCY_Nanometric", bSTR2339, bSTR2340, boolean1170
'--------------------------------------------------
' Parameter 1 : (String) "SQUARE_VOLUME_ACCELERATION_OVER_FREQUENCY_Nanometric"
' Parameter 2 : (String) "Default value"
' Parameter 3 : (String) "Unlocked"
' Parameter 4 : (Boolean) False
'--------------------------------------------------

long1171 = settingRepository1.GetAttr("WAVE_LENGTH")
'--------------------------------------------------
' Parameter 1 : (String) "WAVE_LENGTH"
' Returned value : (Variant) (Long) 1
'--------------------------------------------------

Dim bSTR2341
bSTR2341 = ""
Dim bSTR2342
bSTR2342 = ""
Dim boolean1171
settingRepository1.GetAttrInfo "WAVE_LENGTH", bSTR2341, bSTR2342, boolean1171
'--------------------------------------------------
' Parameter 1 : (String) "WAVE_LENGTH"
' Parameter 2 : (String) "Default value"
' Parameter 3 : (String) "Unlocked"
' Parameter 4 : (Boolean) False
'--------------------------------------------------

long1172 = settingRepository1.GetAttr("WAVE_LENGTH_Large")
'--------------------------------------------------
' Parameter 1 : (String) "WAVE_LENGTH_Large"
' Returned value : (Variant) (Long) 1
'--------------------------------------------------

Dim bSTR2343
bSTR2343 = ""
Dim bSTR2344
bSTR2344 = ""
Dim boolean1172
settingRepository1.GetAttrInfo "WAVE_LENGTH_Large", bSTR2343, bSTR2344, boolean1172
'--------------------------------------------------
' Parameter 1 : (String) "WAVE_LENGTH_Large"
' Parameter 2 : (String) "Default value"
' Parameter 3 : (String) "Unlocked"
' Parameter 4 : (Boolean) False
'--------------------------------------------------

long1173 = settingRepository1.GetAttr("WAVE_LENGTH_ExtraLarge")
'--------------------------------------------------
' Parameter 1 : (String) "WAVE_LENGTH_ExtraLarge"
' Returned value : (Variant) (Long) 1
'--------------------------------------------------

Dim bSTR2345
bSTR2345 = ""
Dim bSTR2346
bSTR2346 = ""
Dim boolean1173
settingRepository1.GetAttrInfo "WAVE_LENGTH_ExtraLarge", bSTR2345, bSTR2346, boolean1173
'--------------------------------------------------
' Parameter 1 : (String) "WAVE_LENGTH_ExtraLarge"
' Parameter 2 : (String) "Default value"
' Parameter 3 : (String) "Unlocked"
' Parameter 4 : (Boolean) False
'--------------------------------------------------

long1174 = settingRepository1.GetAttr("WAVE_LENGTH_Small")
'--------------------------------------------------
' Parameter 1 : (String) "WAVE_LENGTH_Small"
' Returned value : (Variant) (Long) 1
'--------------------------------------------------

Dim bSTR2347
bSTR2347 = ""
Dim bSTR2348
bSTR2348 = ""
Dim boolean1174
settingRepository1.GetAttrInfo "WAVE_LENGTH_Small", bSTR2347, bSTR2348, boolean1174
'--------------------------------------------------
' Parameter 1 : (String) "WAVE_LENGTH_Small"
' Parameter 2 : (String) "Default value"
' Parameter 3 : (String) "Unlocked"
' Parameter 4 : (Boolean) False
'--------------------------------------------------

long1175 = settingRepository1.GetAttr("WAVE_LENGTH_ExtraSmall")
'--------------------------------------------------
' Parameter 1 : (String) "WAVE_LENGTH_ExtraSmall"
' Returned value : (Variant) (Long) 1
'--------------------------------------------------

Dim bSTR2349
bSTR2349 = ""
Dim bSTR2350
bSTR2350 = ""
Dim boolean1175
settingRepository1.GetAttrInfo "WAVE_LENGTH_ExtraSmall", bSTR2349, bSTR2350, boolean1175
'--------------------------------------------------
' Parameter 1 : (String) "WAVE_LENGTH_ExtraSmall"
' Parameter 2 : (String) "Default value"
' Parameter 3 : (String) "Unlocked"
' Parameter 4 : (Boolean) False
'--------------------------------------------------

long1176 = settingRepository1.GetAttr("WAVE_LENGTH_Nanometric")
'--------------------------------------------------
' Parameter 1 : (String) "WAVE_LENGTH_Nanometric"
' Returned value : (Variant) (Long) 1
'--------------------------------------------------

Dim bSTR2351
bSTR2351 = ""
Dim bSTR2352
bSTR2352 = ""
Dim boolean1176
settingRepository1.GetAttrInfo "WAVE_LENGTH_Nanometric", bSTR2351, bSTR2352, boolean1176
'--------------------------------------------------
' Parameter 1 : (String) "WAVE_LENGTH_Nanometric"
' Parameter 2 : (String) "Default value"
' Parameter 3 : (String) "Unlocked"
' Parameter 4 : (Boolean) False
'--------------------------------------------------

long1177 = settingRepository1.GetAttr("LUMINOUS_FLUX")
'--------------------------------------------------
' Parameter 1 : (String) "LUMINOUS_FLUX"
' Returned value : (Variant) (Long) 1
'--------------------------------------------------

Dim bSTR2353
bSTR2353 = ""
Dim bSTR2354
bSTR2354 = ""
Dim boolean1177
settingRepository1.GetAttrInfo "LUMINOUS_FLUX", bSTR2353, bSTR2354, boolean1177
'--------------------------------------------------
' Parameter 1 : (String) "LUMINOUS_FLUX"
' Parameter 2 : (String) "Default value"
' Parameter 3 : (String) "Unlocked"
' Parameter 4 : (Boolean) False
'--------------------------------------------------

long1178 = settingRepository1.GetAttr("LUMINOUS_FLUX_Large")
'--------------------------------------------------
' Parameter 1 : (String) "LUMINOUS_FLUX_Large"
' Returned value : (Variant) (Long) 1
'--------------------------------------------------

Dim bSTR2355
bSTR2355 = ""
Dim bSTR2356
bSTR2356 = ""
Dim boolean1178
settingRepository1.GetAttrInfo "LUMINOUS_FLUX_Large", bSTR2355, bSTR2356, boolean1178
'--------------------------------------------------
' Parameter 1 : (String) "LUMINOUS_FLUX_Large"
' Parameter 2 : (String) "Default value"
' Parameter 3 : (String) "Unlocked"
' Parameter 4 : (Boolean) False
'--------------------------------------------------

long1179 = settingRepository1.GetAttr("LUMINOUS_FLUX_ExtraLarge")
'--------------------------------------------------
' Parameter 1 : (String) "LUMINOUS_FLUX_ExtraLarge"
' Returned value : (Variant) (Long) 1
'--------------------------------------------------

Dim bSTR2357
bSTR2357 = ""
Dim bSTR2358
bSTR2358 = ""
Dim boolean1179
settingRepository1.GetAttrInfo "LUMINOUS_FLUX_ExtraLarge", bSTR2357, bSTR2358, boolean1179
'--------------------------------------------------
' Parameter 1 : (String) "LUMINOUS_FLUX_ExtraLarge"
' Parameter 2 : (String) "Default value"
' Parameter 3 : (String) "Unlocked"
' Parameter 4 : (Boolean) False
'--------------------------------------------------

long1180 = settingRepository1.GetAttr("LUMINOUS_FLUX_Small")
'--------------------------------------------------
' Parameter 1 : (String) "LUMINOUS_FLUX_Small"
' Returned value : (Variant) (Long) 1
'--------------------------------------------------

Dim bSTR2359
bSTR2359 = ""
Dim bSTR2360
bSTR2360 = ""
Dim boolean1180
settingRepository1.GetAttrInfo "LUMINOUS_FLUX_Small", bSTR2359, bSTR2360, boolean1180
'--------------------------------------------------
' Parameter 1 : (String) "LUMINOUS_FLUX_Small"
' Parameter 2 : (String) "Default value"
' Parameter 3 : (String) "Unlocked"
' Parameter 4 : (Boolean) False
'--------------------------------------------------

long1181 = settingRepository1.GetAttr("LUMINOUS_FLUX_ExtraSmall")
'--------------------------------------------------
' Parameter 1 : (String) "LUMINOUS_FLUX_ExtraSmall"
' Returned value : (Variant) (Long) 1
'--------------------------------------------------

Dim bSTR2361
bSTR2361 = ""
Dim bSTR2362
bSTR2362 = ""
Dim boolean1181
settingRepository1.GetAttrInfo "LUMINOUS_FLUX_ExtraSmall", bSTR2361, bSTR2362, boolean1181
'--------------------------------------------------
' Parameter 1 : (String) "LUMINOUS_FLUX_ExtraSmall"
' Parameter 2 : (String) "Default value"
' Parameter 3 : (String) "Unlocked"
' Parameter 4 : (Boolean) False
'--------------------------------------------------

long1182 = settingRepository1.GetAttr("LUMINOUS_FLUX_Nanometric")
'--------------------------------------------------
' Parameter 1 : (String) "LUMINOUS_FLUX_Nanometric"
' Returned value : (Variant) (Long) 1
'--------------------------------------------------

Dim bSTR2363
bSTR2363 = ""
Dim bSTR2364
bSTR2364 = ""
Dim boolean1182
settingRepository1.GetAttrInfo "LUMINOUS_FLUX_Nanometric", bSTR2363, bSTR2364, boolean1182
'--------------------------------------------------
' Parameter 1 : (String) "LUMINOUS_FLUX_Nanometric"
' Parameter 2 : (String) "Default value"
' Parameter 3 : (String) "Unlocked"
' Parameter 4 : (Boolean) False
'--------------------------------------------------

long1183 = settingRepository1.GetAttr("RADIANT_FLUX")
'--------------------------------------------------
' Parameter 1 : (String) "RADIANT_FLUX"
' Returned value : (Variant) (Long) 1
'--------------------------------------------------

Dim bSTR2365
bSTR2365 = ""
Dim bSTR2366
bSTR2366 = ""
Dim boolean1183
settingRepository1.GetAttrInfo "RADIANT_FLUX", bSTR2365, bSTR2366, boolean1183
'--------------------------------------------------
' Parameter 1 : (String) "RADIANT_FLUX"
' Parameter 2 : (String) "Default value"
' Parameter 3 : (String) "Unlocked"
' Parameter 4 : (Boolean) False
'--------------------------------------------------

long1184 = settingRepository1.GetAttr("RADIANT_FLUX_Large")
'--------------------------------------------------
' Parameter 1 : (String) "RADIANT_FLUX_Large"
' Returned value : (Variant) (Long) 1
'--------------------------------------------------

Dim bSTR2367
bSTR2367 = ""
Dim bSTR2368
bSTR2368 = ""
Dim boolean1184
settingRepository1.GetAttrInfo "RADIANT_FLUX_Large", bSTR2367, bSTR2368, boolean1184
'--------------------------------------------------
' Parameter 1 : (String) "RADIANT_FLUX_Large"
' Parameter 2 : (String) "Default value"
' Parameter 3 : (String) "Unlocked"
' Parameter 4 : (Boolean) False
'--------------------------------------------------

long1185 = settingRepository1.GetAttr("RADIANT_FLUX_ExtraLarge")
'--------------------------------------------------
' Parameter 1 : (String) "RADIANT_FLUX_ExtraLarge"
' Returned value : (Variant) (Long) 1
'--------------------------------------------------

Dim bSTR2369
bSTR2369 = ""
Dim bSTR2370
bSTR2370 = ""
Dim boolean1185
settingRepository1.GetAttrInfo "RADIANT_FLUX_ExtraLarge", bSTR2369, bSTR2370, boolean1185
'--------------------------------------------------
' Parameter 1 : (String) "RADIANT_FLUX_ExtraLarge"
' Parameter 2 : (String) "Default value"
' Parameter 3 : (String) "Unlocked"
' Parameter 4 : (Boolean) False
'--------------------------------------------------

long1186 = settingRepository1.GetAttr("RADIANT_FLUX_Small")
'--------------------------------------------------
' Parameter 1 : (String) "RADIANT_FLUX_Small"
' Returned value : (Variant) (Long) 1
'--------------------------------------------------

Dim bSTR2371
bSTR2371 = ""
Dim bSTR2372
bSTR2372 = ""
Dim boolean1186
settingRepository1.GetAttrInfo "RADIANT_FLUX_Small", bSTR2371, bSTR2372, boolean1186
'--------------------------------------------------
' Parameter 1 : (String) "RADIANT_FLUX_Small"
' Parameter 2 : (String) "Default value"
' Parameter 3 : (String) "Unlocked"
' Parameter 4 : (Boolean) False
'--------------------------------------------------

long1187 = settingRepository1.GetAttr("RADIANT_FLUX_ExtraSmall")
'--------------------------------------------------
' Parameter 1 : (String) "RADIANT_FLUX_ExtraSmall"
' Returned value : (Variant) (Long) 1
'--------------------------------------------------

Dim bSTR2373
bSTR2373 = ""
Dim bSTR2374
bSTR2374 = ""
Dim boolean1187
settingRepository1.GetAttrInfo "RADIANT_FLUX_ExtraSmall", bSTR2373, bSTR2374, boolean1187
'--------------------------------------------------
' Parameter 1 : (String) "RADIANT_FLUX_ExtraSmall"
' Parameter 2 : (String) "Default value"
' Parameter 3 : (String) "Unlocked"
' Parameter 4 : (Boolean) False
'--------------------------------------------------

long1188 = settingRepository1.GetAttr("RADIANT_FLUX_Nanometric")
'--------------------------------------------------
' Parameter 1 : (String) "RADIANT_FLUX_Nanometric"
' Returned value : (Variant) (Long) 1
'--------------------------------------------------

Dim bSTR2375
bSTR2375 = ""
Dim bSTR2376
bSTR2376 = ""
Dim boolean1188
settingRepository1.GetAttrInfo "RADIANT_FLUX_Nanometric", bSTR2375, bSTR2376, boolean1188
'--------------------------------------------------
' Parameter 1 : (String) "RADIANT_FLUX_Nanometric"
' Parameter 2 : (String) "Default value"
' Parameter 3 : (String) "Unlocked"
' Parameter 4 : (Boolean) False
'--------------------------------------------------

long1189 = settingRepository1.GetAttr("LINEIC_ABSORPTION")
'--------------------------------------------------
' Parameter 1 : (String) "LINEIC_ABSORPTION"
' Returned value : (Variant) (Long) 1
'--------------------------------------------------

Dim bSTR2377
bSTR2377 = ""
Dim bSTR2378
bSTR2378 = ""
Dim boolean1189
settingRepository1.GetAttrInfo "LINEIC_ABSORPTION", bSTR2377, bSTR2378, boolean1189
'--------------------------------------------------
' Parameter 1 : (String) "LINEIC_ABSORPTION"
' Parameter 2 : (String) "Default value"
' Parameter 3 : (String) "Unlocked"
' Parameter 4 : (Boolean) False
'--------------------------------------------------

long1190 = settingRepository1.GetAttr("LINEIC_ABSORPTION_Large")
'--------------------------------------------------
' Parameter 1 : (String) "LINEIC_ABSORPTION_Large"
' Returned value : (Variant) (Long) 1
'--------------------------------------------------

Dim bSTR2379
bSTR2379 = ""
Dim bSTR2380
bSTR2380 = ""
Dim boolean1190
settingRepository1.GetAttrInfo "LINEIC_ABSORPTION_Large", bSTR2379, bSTR2380, boolean1190
'--------------------------------------------------
' Parameter 1 : (String) "LINEIC_ABSORPTION_Large"
' Parameter 2 : (String) "Default value"
' Parameter 3 : (String) "Unlocked"
' Parameter 4 : (Boolean) False
'--------------------------------------------------

long1191 = settingRepository1.GetAttr("LINEIC_ABSORPTION_ExtraLarge")
'--------------------------------------------------
' Parameter 1 : (String) "LINEIC_ABSORPTION_ExtraLarge"
' Returned value : (Variant) (Long) 1
'--------------------------------------------------

Dim bSTR2381
bSTR2381 = ""
Dim bSTR2382
bSTR2382 = ""
Dim boolean1191
settingRepository1.GetAttrInfo "LINEIC_ABSORPTION_ExtraLarge", bSTR2381, bSTR2382, boolean1191
'--------------------------------------------------
' Parameter 1 : (String) "LINEIC_ABSORPTION_ExtraLarge"
' Parameter 2 : (String) "Default value"
' Parameter 3 : (String) "Unlocked"
' Parameter 4 : (Boolean) False
'--------------------------------------------------

long1192 = settingRepository1.GetAttr("LINEIC_ABSORPTION_Small")
'--------------------------------------------------
' Parameter 1 : (String) "LINEIC_ABSORPTION_Small"
' Returned value : (Variant) (Long) 1
'--------------------------------------------------

Dim bSTR2383
bSTR2383 = ""
Dim bSTR2384
bSTR2384 = ""
Dim boolean1192
settingRepository1.GetAttrInfo "LINEIC_ABSORPTION_Small", bSTR2383, bSTR2384, boolean1192
'--------------------------------------------------
' Parameter 1 : (String) "LINEIC_ABSORPTION_Small"
' Parameter 2 : (String) "Default value"
' Parameter 3 : (String) "Unlocked"
' Parameter 4 : (Boolean) False
'--------------------------------------------------

long1193 = settingRepository1.GetAttr("LINEIC_ABSORPTION_ExtraSmall")
'--------------------------------------------------
' Parameter 1 : (String) "LINEIC_ABSORPTION_ExtraSmall"
' Returned value : (Variant) (Long) 1
'--------------------------------------------------

Dim bSTR2385
bSTR2385 = ""
Dim bSTR2386
bSTR2386 = ""
Dim boolean1193
settingRepository1.GetAttrInfo "LINEIC_ABSORPTION_ExtraSmall", bSTR2385, bSTR2386, boolean1193
'--------------------------------------------------
' Parameter 1 : (String) "LINEIC_ABSORPTION_ExtraSmall"
' Parameter 2 : (String) "Default value"
' Parameter 3 : (String) "Unlocked"
' Parameter 4 : (Boolean) False
'--------------------------------------------------

long1194 = settingRepository1.GetAttr("LINEIC_ABSORPTION_Nanometric")
'--------------------------------------------------
' Parameter 1 : (String) "LINEIC_ABSORPTION_Nanometric"
' Returned value : (Variant) (Long) 1
'--------------------------------------------------

Dim bSTR2387
bSTR2387 = ""
Dim bSTR2388
bSTR2388 = ""
Dim boolean1194
settingRepository1.GetAttrInfo "LINEIC_ABSORPTION_Nanometric", bSTR2387, bSTR2388, boolean1194
'--------------------------------------------------
' Parameter 1 : (String) "LINEIC_ABSORPTION_Nanometric"
' Parameter 2 : (String) "Default value"
' Parameter 3 : (String) "Unlocked"
' Parameter 4 : (Boolean) False
'--------------------------------------------------

long1195 = settingRepository1.GetAttr("Ratio")
'--------------------------------------------------
' Parameter 1 : (String) "Ratio"
' Returned value : (Variant) (Long) 1
'--------------------------------------------------

Dim bSTR2389
bSTR2389 = ""
Dim bSTR2390
bSTR2390 = ""
Dim boolean1195
settingRepository1.GetAttrInfo "Ratio", bSTR2389, bSTR2390, boolean1195
'--------------------------------------------------
' Parameter 1 : (String) "Ratio"
' Parameter 2 : (String) "Default value"
' Parameter 3 : (String) "Unlocked"
' Parameter 4 : (Boolean) False
'--------------------------------------------------

long1196 = settingRepository1.GetAttr("Ratio_Large")
'--------------------------------------------------
' Parameter 1 : (String) "Ratio_Large"
' Returned value : (Variant) (Long) 1
'--------------------------------------------------

Dim bSTR2391
bSTR2391 = ""
Dim bSTR2392
bSTR2392 = ""
Dim boolean1196
settingRepository1.GetAttrInfo "Ratio_Large", bSTR2391, bSTR2392, boolean1196
'--------------------------------------------------
' Parameter 1 : (String) "Ratio_Large"
' Parameter 2 : (String) "Default value"
' Parameter 3 : (String) "Unlocked"
' Parameter 4 : (Boolean) False
'--------------------------------------------------

long1197 = settingRepository1.GetAttr("Ratio_ExtraLarge")
'--------------------------------------------------
' Parameter 1 : (String) "Ratio_ExtraLarge"
' Returned value : (Variant) (Long) 1
'--------------------------------------------------

Dim bSTR2393
bSTR2393 = ""
Dim bSTR2394
bSTR2394 = ""
Dim boolean1197
settingRepository1.GetAttrInfo "Ratio_ExtraLarge", bSTR2393, bSTR2394, boolean1197
'--------------------------------------------------
' Parameter 1 : (String) "Ratio_ExtraLarge"
' Parameter 2 : (String) "Default value"
' Parameter 3 : (String) "Unlocked"
' Parameter 4 : (Boolean) False
'--------------------------------------------------

long1198 = settingRepository1.GetAttr("Ratio_Small")
'--------------------------------------------------
' Parameter 1 : (String) "Ratio_Small"
' Returned value : (Variant) (Long) 1
'--------------------------------------------------

Dim bSTR2395
bSTR2395 = ""
Dim bSTR2396
bSTR2396 = ""
Dim boolean1198
settingRepository1.GetAttrInfo "Ratio_Small", bSTR2395, bSTR2396, boolean1198
'--------------------------------------------------
' Parameter 1 : (String) "Ratio_Small"
' Parameter 2 : (String) "Default value"
' Parameter 3 : (String) "Unlocked"
' Parameter 4 : (Boolean) False
'--------------------------------------------------

long1199 = settingRepository1.GetAttr("Ratio_ExtraSmall")
'--------------------------------------------------
' Parameter 1 : (String) "Ratio_ExtraSmall"
' Returned value : (Variant) (Long) 1
'--------------------------------------------------

Dim bSTR2397
bSTR2397 = ""
Dim bSTR2398
bSTR2398 = ""
Dim boolean1199
settingRepository1.GetAttrInfo "Ratio_ExtraSmall", bSTR2397, bSTR2398, boolean1199
'--------------------------------------------------
' Parameter 1 : (String) "Ratio_ExtraSmall"
' Parameter 2 : (String) "Default value"
' Parameter 3 : (String) "Unlocked"
' Parameter 4 : (Boolean) False
'--------------------------------------------------

long1200 = settingRepository1.GetAttr("Ratio_Nanometric")
'--------------------------------------------------
' Parameter 1 : (String) "Ratio_Nanometric"
' Returned value : (Variant) (Long) 1
'--------------------------------------------------

Dim bSTR2399
bSTR2399 = ""
Dim bSTR2400
bSTR2400 = ""
Dim boolean1200
settingRepository1.GetAttrInfo "Ratio_Nanometric", bSTR2399, bSTR2400, boolean1200
'--------------------------------------------------
' Parameter 1 : (String) "Ratio_Nanometric"
' Parameter 2 : (String) "Default value"
' Parameter 3 : (String) "Unlocked"
' Parameter 4 : (Boolean) False
'--------------------------------------------------

long1201 = settingRepository1.GetAttr("RADIANCE")
'--------------------------------------------------
' Parameter 1 : (String) "RADIANCE"
' Returned value : (Variant) (Long) 1
'--------------------------------------------------

Dim bSTR2401
bSTR2401 = ""
Dim bSTR2402
bSTR2402 = ""
Dim boolean1201
settingRepository1.GetAttrInfo "RADIANCE", bSTR2401, bSTR2402, boolean1201
'--------------------------------------------------
' Parameter 1 : (String) "RADIANCE"
' Parameter 2 : (String) "Default value"
' Parameter 3 : (String) "Unlocked"
' Parameter 4 : (Boolean) False
'--------------------------------------------------

long1202 = settingRepository1.GetAttr("RADIANCE_Large")
'--------------------------------------------------
' Parameter 1 : (String) "RADIANCE_Large"
' Returned value : (Variant) (Long) 1
'--------------------------------------------------

Dim bSTR2403
bSTR2403 = ""
Dim bSTR2404
bSTR2404 = ""
Dim boolean1202
settingRepository1.GetAttrInfo "RADIANCE_Large", bSTR2403, bSTR2404, boolean1202
'--------------------------------------------------
' Parameter 1 : (String) "RADIANCE_Large"
' Parameter 2 : (String) "Default value"
' Parameter 3 : (String) "Unlocked"
' Parameter 4 : (Boolean) False
'--------------------------------------------------

long1203 = settingRepository1.GetAttr("RADIANCE_ExtraLarge")
'--------------------------------------------------
' Parameter 1 : (String) "RADIANCE_ExtraLarge"
' Returned value : (Variant) (Long) 1
'--------------------------------------------------

Dim bSTR2405
bSTR2405 = ""
Dim bSTR2406
bSTR2406 = ""
Dim boolean1203
settingRepository1.GetAttrInfo "RADIANCE_ExtraLarge", bSTR2405, bSTR2406, boolean1203
'--------------------------------------------------
' Parameter 1 : (String) "RADIANCE_ExtraLarge"
' Parameter 2 : (String) "Default value"
' Parameter 3 : (String) "Unlocked"
' Parameter 4 : (Boolean) False
'--------------------------------------------------

long1204 = settingRepository1.GetAttr("RADIANCE_Small")
'--------------------------------------------------
' Parameter 1 : (String) "RADIANCE_Small"
' Returned value : (Variant) (Long) 1
'--------------------------------------------------

Dim bSTR2407
bSTR2407 = ""
Dim bSTR2408
bSTR2408 = ""
Dim boolean1204
settingRepository1.GetAttrInfo "RADIANCE_Small", bSTR2407, bSTR2408, boolean1204
'--------------------------------------------------
' Parameter 1 : (String) "RADIANCE_Small"
' Parameter 2 : (String) "Default value"
' Parameter 3 : (String) "Unlocked"
' Parameter 4 : (Boolean) False
'--------------------------------------------------

long1205 = settingRepository1.GetAttr("RADIANCE_ExtraSmall")
'--------------------------------------------------
' Parameter 1 : (String) "RADIANCE_ExtraSmall"
' Returned value : (Variant) (Long) 1
'--------------------------------------------------

Dim bSTR2409
bSTR2409 = ""
Dim bSTR2410
bSTR2410 = ""
Dim boolean1205
settingRepository1.GetAttrInfo "RADIANCE_ExtraSmall", bSTR2409, bSTR2410, boolean1205
'--------------------------------------------------
' Parameter 1 : (String) "RADIANCE_ExtraSmall"
' Parameter 2 : (String) "Default value"
' Parameter 3 : (String) "Unlocked"
' Parameter 4 : (Boolean) False
'--------------------------------------------------

long1206 = settingRepository1.GetAttr("RADIANCE_Nanometric")
'--------------------------------------------------
' Parameter 1 : (String) "RADIANCE_Nanometric"
' Returned value : (Variant) (Long) 1
'--------------------------------------------------

Dim bSTR2411
bSTR2411 = ""
Dim bSTR2412
bSTR2412 = ""
Dim boolean1206
settingRepository1.GetAttrInfo "RADIANCE_Nanometric", bSTR2411, bSTR2412, boolean1206
'--------------------------------------------------
' Parameter 1 : (String) "RADIANCE_Nanometric"
' Parameter 2 : (String) "Default value"
' Parameter 3 : (String) "Unlocked"
' Parameter 4 : (Boolean) False
'--------------------------------------------------

long1207 = settingRepository1.GetAttr("ILLUMINANCE")
'--------------------------------------------------
' Parameter 1 : (String) "ILLUMINANCE"
' Returned value : (Variant) (Long) 1
'--------------------------------------------------

Dim bSTR2413
bSTR2413 = ""
Dim bSTR2414
bSTR2414 = ""
Dim boolean1207
settingRepository1.GetAttrInfo "ILLUMINANCE", bSTR2413, bSTR2414, boolean1207
'--------------------------------------------------
' Parameter 1 : (String) "ILLUMINANCE"
' Parameter 2 : (String) "Default value"
' Parameter 3 : (String) "Unlocked"
' Parameter 4 : (Boolean) False
'--------------------------------------------------

long1208 = settingRepository1.GetAttr("ILLUMINANCE_Large")
'--------------------------------------------------
' Parameter 1 : (String) "ILLUMINANCE_Large"
' Returned value : (Variant) (Long) 1
'--------------------------------------------------

Dim bSTR2415
bSTR2415 = ""
Dim bSTR2416
bSTR2416 = ""
Dim boolean1208
settingRepository1.GetAttrInfo "ILLUMINANCE_Large", bSTR2415, bSTR2416, boolean1208
'--------------------------------------------------
' Parameter 1 : (String) "ILLUMINANCE_Large"
' Parameter 2 : (String) "Default value"
' Parameter 3 : (String) "Unlocked"
' Parameter 4 : (Boolean) False
'--------------------------------------------------

long1209 = settingRepository1.GetAttr("ILLUMINANCE_ExtraLarge")
'--------------------------------------------------
' Parameter 1 : (String) "ILLUMINANCE_ExtraLarge"
' Returned value : (Variant) (Long) 1
'--------------------------------------------------

Dim bSTR2417
bSTR2417 = ""
Dim bSTR2418
bSTR2418 = ""
Dim boolean1209
settingRepository1.GetAttrInfo "ILLUMINANCE_ExtraLarge", bSTR2417, bSTR2418, boolean1209
'--------------------------------------------------
' Parameter 1 : (String) "ILLUMINANCE_ExtraLarge"
' Parameter 2 : (String) "Default value"
' Parameter 3 : (String) "Unlocked"
' Parameter 4 : (Boolean) False
'--------------------------------------------------

long1210 = settingRepository1.GetAttr("ILLUMINANCE_Small")
'--------------------------------------------------
' Parameter 1 : (String) "ILLUMINANCE_Small"
' Returned value : (Variant) (Long) 1
'--------------------------------------------------

Dim bSTR2419
bSTR2419 = ""
Dim bSTR2420
bSTR2420 = ""
Dim boolean1210
settingRepository1.GetAttrInfo "ILLUMINANCE_Small", bSTR2419, bSTR2420, boolean1210
'--------------------------------------------------
' Parameter 1 : (String) "ILLUMINANCE_Small"
' Parameter 2 : (String) "Default value"
' Parameter 3 : (String) "Unlocked"
' Parameter 4 : (Boolean) False
'--------------------------------------------------

long1211 = settingRepository1.GetAttr("ILLUMINANCE_ExtraSmall")
'--------------------------------------------------
' Parameter 1 : (String) "ILLUMINANCE_ExtraSmall"
' Returned value : (Variant) (Long) 1
'--------------------------------------------------

Dim bSTR2421
bSTR2421 = ""
Dim bSTR2422
bSTR2422 = ""
Dim boolean1211
settingRepository1.GetAttrInfo "ILLUMINANCE_ExtraSmall", bSTR2421, bSTR2422, boolean1211
'--------------------------------------------------
' Parameter 1 : (String) "ILLUMINANCE_ExtraSmall"
' Parameter 2 : (String) "Default value"
' Parameter 3 : (String) "Unlocked"
' Parameter 4 : (Boolean) False
'--------------------------------------------------

long1212 = settingRepository1.GetAttr("ILLUMINANCE_Nanometric")
'--------------------------------------------------
' Parameter 1 : (String) "ILLUMINANCE_Nanometric"
' Returned value : (Variant) (Long) 1
'--------------------------------------------------

Dim bSTR2423
bSTR2423 = ""
Dim bSTR2424
bSTR2424 = ""
Dim boolean1212
settingRepository1.GetAttrInfo "ILLUMINANCE_Nanometric", bSTR2423, bSTR2424, boolean1212
'--------------------------------------------------
' Parameter 1 : (String) "ILLUMINANCE_Nanometric"
' Parameter 2 : (String) "Default value"
' Parameter 3 : (String) "Unlocked"
' Parameter 4 : (Boolean) False
'--------------------------------------------------

long1213 = settingRepository1.GetAttr("IRRADIANCE")
'--------------------------------------------------
' Parameter 1 : (String) "IRRADIANCE"
' Returned value : (Variant) (Long) 1
'--------------------------------------------------

Dim bSTR2425
bSTR2425 = ""
Dim bSTR2426
bSTR2426 = ""
Dim boolean1213
settingRepository1.GetAttrInfo "IRRADIANCE", bSTR2425, bSTR2426, boolean1213
'--------------------------------------------------
' Parameter 1 : (String) "IRRADIANCE"
' Parameter 2 : (String) "Default value"
' Parameter 3 : (String) "Unlocked"
' Parameter 4 : (Boolean) False
'--------------------------------------------------

long1214 = settingRepository1.GetAttr("IRRADIANCE_Large")
'--------------------------------------------------
' Parameter 1 : (String) "IRRADIANCE_Large"
' Returned value : (Variant) (Long) 1
'--------------------------------------------------

Dim bSTR2427
bSTR2427 = ""
Dim bSTR2428
bSTR2428 = ""
Dim boolean1214
settingRepository1.GetAttrInfo "IRRADIANCE_Large", bSTR2427, bSTR2428, boolean1214
'--------------------------------------------------
' Parameter 1 : (String) "IRRADIANCE_Large"
' Parameter 2 : (String) "Default value"
' Parameter 3 : (String) "Unlocked"
' Parameter 4 : (Boolean) False
'--------------------------------------------------

long1215 = settingRepository1.GetAttr("IRRADIANCE_ExtraLarge")
'--------------------------------------------------
' Parameter 1 : (String) "IRRADIANCE_ExtraLarge"
' Returned value : (Variant) (Long) 1
'--------------------------------------------------

Dim bSTR2429
bSTR2429 = ""
Dim bSTR2430
bSTR2430 = ""
Dim boolean1215
settingRepository1.GetAttrInfo "IRRADIANCE_ExtraLarge", bSTR2429, bSTR2430, boolean1215
'--------------------------------------------------
' Parameter 1 : (String) "IRRADIANCE_ExtraLarge"
' Parameter 2 : (String) "Default value"
' Parameter 3 : (String) "Unlocked"
' Parameter 4 : (Boolean) False
'--------------------------------------------------

long1216 = settingRepository1.GetAttr("IRRADIANCE_Small")
'--------------------------------------------------
' Parameter 1 : (String) "IRRADIANCE_Small"
' Returned value : (Variant) (Long) 1
'--------------------------------------------------

Dim bSTR2431
bSTR2431 = ""
Dim bSTR2432
bSTR2432 = ""
Dim boolean1216
settingRepository1.GetAttrInfo "IRRADIANCE_Small", bSTR2431, bSTR2432, boolean1216
'--------------------------------------------------
' Parameter 1 : (String) "IRRADIANCE_Small"
' Parameter 2 : (String) "Default value"
' Parameter 3 : (String) "Unlocked"
' Parameter 4 : (Boolean) False
'--------------------------------------------------

long1217 = settingRepository1.GetAttr("IRRADIANCE_ExtraSmall")
'--------------------------------------------------
' Parameter 1 : (String) "IRRADIANCE_ExtraSmall"
' Returned value : (Variant) (Long) 1
'--------------------------------------------------

Dim bSTR2433
bSTR2433 = ""
Dim bSTR2434
bSTR2434 = ""
Dim boolean1217
settingRepository1.GetAttrInfo "IRRADIANCE_ExtraSmall", bSTR2433, bSTR2434, boolean1217
'--------------------------------------------------
' Parameter 1 : (String) "IRRADIANCE_ExtraSmall"
' Parameter 2 : (String) "Default value"
' Parameter 3 : (String) "Unlocked"
' Parameter 4 : (Boolean) False
'--------------------------------------------------

long1218 = settingRepository1.GetAttr("IRRADIANCE_Nanometric")
'--------------------------------------------------
' Parameter 1 : (String) "IRRADIANCE_Nanometric"
' Returned value : (Variant) (Long) 1
'--------------------------------------------------

Dim bSTR2435
bSTR2435 = ""
Dim bSTR2436
bSTR2436 = ""
Dim boolean1218
settingRepository1.GetAttrInfo "IRRADIANCE_Nanometric", bSTR2435, bSTR2436, boolean1218
'--------------------------------------------------
' Parameter 1 : (String) "IRRADIANCE_Nanometric"
' Parameter 2 : (String) "Default value"
' Parameter 3 : (String) "Unlocked"
' Parameter 4 : (Boolean) False
'--------------------------------------------------

long1219 = settingRepository1.GetAttr("LUMINOUS_INTENSITY")
'--------------------------------------------------
' Parameter 1 : (String) "LUMINOUS_INTENSITY"
' Returned value : (Variant) (Long) 1
'--------------------------------------------------

Dim bSTR2437
bSTR2437 = ""
Dim bSTR2438
bSTR2438 = ""
Dim boolean1219
settingRepository1.GetAttrInfo "LUMINOUS_INTENSITY", bSTR2437, bSTR2438, boolean1219
'--------------------------------------------------
' Parameter 1 : (String) "LUMINOUS_INTENSITY"
' Parameter 2 : (String) "Default value"
' Parameter 3 : (String) "Unlocked"
' Parameter 4 : (Boolean) False
'--------------------------------------------------

long1220 = settingRepository1.GetAttr("LUMINOUS_INTENSITY_Large")
'--------------------------------------------------
' Parameter 1 : (String) "LUMINOUS_INTENSITY_Large"
' Returned value : (Variant) (Long) 1
'--------------------------------------------------

Dim bSTR2439
bSTR2439 = ""
Dim bSTR2440
bSTR2440 = ""
Dim boolean1220
settingRepository1.GetAttrInfo "LUMINOUS_INTENSITY_Large", bSTR2439, bSTR2440, boolean1220
'--------------------------------------------------
' Parameter 1 : (String) "LUMINOUS_INTENSITY_Large"
' Parameter 2 : (String) "Default value"
' Parameter 3 : (String) "Unlocked"
' Parameter 4 : (Boolean) False
'--------------------------------------------------

long1221 = settingRepository1.GetAttr("LUMINOUS_INTENSITY_ExtraLarge")
'--------------------------------------------------
' Parameter 1 : (String) "LUMINOUS_INTENSITY_ExtraLarge"
' Returned value : (Variant) (Long) 1
'--------------------------------------------------

Dim bSTR2441
bSTR2441 = ""
Dim bSTR2442
bSTR2442 = ""
Dim boolean1221
settingRepository1.GetAttrInfo "LUMINOUS_INTENSITY_ExtraLarge", bSTR2441, bSTR2442, boolean1221
'--------------------------------------------------
' Parameter 1 : (String) "LUMINOUS_INTENSITY_ExtraLarge"
' Parameter 2 : (String) "Default value"
' Parameter 3 : (String) "Unlocked"
' Parameter 4 : (Boolean) False
'--------------------------------------------------

long1222 = settingRepository1.GetAttr("LUMINOUS_INTENSITY_Small")
'--------------------------------------------------
' Parameter 1 : (String) "LUMINOUS_INTENSITY_Small"
' Returned value : (Variant) (Long) 1
'--------------------------------------------------

Dim bSTR2443
bSTR2443 = ""
Dim bSTR2444
bSTR2444 = ""
Dim boolean1222
settingRepository1.GetAttrInfo "LUMINOUS_INTENSITY_Small", bSTR2443, bSTR2444, boolean1222
'--------------------------------------------------
' Parameter 1 : (String) "LUMINOUS_INTENSITY_Small"
' Parameter 2 : (String) "Default value"
' Parameter 3 : (String) "Unlocked"
' Parameter 4 : (Boolean) False
'--------------------------------------------------

long1223 = settingRepository1.GetAttr("LUMINOUS_INTENSITY_ExtraSmall")
'--------------------------------------------------
' Parameter 1 : (String) "LUMINOUS_INTENSITY_ExtraSmall"
' Returned value : (Variant) (Long) 1
'--------------------------------------------------

Dim bSTR2445
bSTR2445 = ""
Dim bSTR2446
bSTR2446 = ""
Dim boolean1223
settingRepository1.GetAttrInfo "LUMINOUS_INTENSITY_ExtraSmall", bSTR2445, bSTR2446, boolean1223
'--------------------------------------------------
' Parameter 1 : (String) "LUMINOUS_INTENSITY_ExtraSmall"
' Parameter 2 : (String) "Default value"
' Parameter 3 : (String) "Unlocked"
' Parameter 4 : (Boolean) False
'--------------------------------------------------

long1224 = settingRepository1.GetAttr("LUMINOUS_INTENSITY_Nanometric")
'--------------------------------------------------
' Parameter 1 : (String) "LUMINOUS_INTENSITY_Nanometric"
' Returned value : (Variant) (Long) 1
'--------------------------------------------------

Dim bSTR2447
bSTR2447 = ""
Dim bSTR2448
bSTR2448 = ""
Dim boolean1224
settingRepository1.GetAttrInfo "LUMINOUS_INTENSITY_Nanometric", bSTR2447, bSTR2448, boolean1224
'--------------------------------------------------
' Parameter 1 : (String) "LUMINOUS_INTENSITY_Nanometric"
' Parameter 2 : (String) "Default value"
' Parameter 3 : (String) "Unlocked"
' Parameter 4 : (Boolean) False
'--------------------------------------------------

long1225 = settingRepository1.GetAttr("RADIANT_INTENSITY")
'--------------------------------------------------
' Parameter 1 : (String) "RADIANT_INTENSITY"
' Returned value : (Variant) (Long) 1
'--------------------------------------------------

Dim bSTR2449
bSTR2449 = ""
Dim bSTR2450
bSTR2450 = ""
Dim boolean1225
settingRepository1.GetAttrInfo "RADIANT_INTENSITY", bSTR2449, bSTR2450, boolean1225
'--------------------------------------------------
' Parameter 1 : (String) "RADIANT_INTENSITY"
' Parameter 2 : (String) "Default value"
' Parameter 3 : (String) "Unlocked"
' Parameter 4 : (Boolean) False
'--------------------------------------------------

long1226 = settingRepository1.GetAttr("RADIANT_INTENSITY_Large")
'--------------------------------------------------
' Parameter 1 : (String) "RADIANT_INTENSITY_Large"
' Returned value : (Variant) (Long) 1
'--------------------------------------------------

Dim bSTR2451
bSTR2451 = ""
Dim bSTR2452
bSTR2452 = ""
Dim boolean1226
settingRepository1.GetAttrInfo "RADIANT_INTENSITY_Large", bSTR2451, bSTR2452, boolean1226
'--------------------------------------------------
' Parameter 1 : (String) "RADIANT_INTENSITY_Large"
' Parameter 2 : (String) "Default value"
' Parameter 3 : (String) "Unlocked"
' Parameter 4 : (Boolean) False
'--------------------------------------------------

long1227 = settingRepository1.GetAttr("RADIANT_INTENSITY_ExtraLarge")
'--------------------------------------------------
' Parameter 1 : (String) "RADIANT_INTENSITY_ExtraLarge"
' Returned value : (Variant) (Long) 1
'--------------------------------------------------

Dim bSTR2453
bSTR2453 = ""
Dim bSTR2454
bSTR2454 = ""
Dim boolean1227
settingRepository1.GetAttrInfo "RADIANT_INTENSITY_ExtraLarge", bSTR2453, bSTR2454, boolean1227
'--------------------------------------------------
' Parameter 1 : (String) "RADIANT_INTENSITY_ExtraLarge"
' Parameter 2 : (String) "Default value"
' Parameter 3 : (String) "Unlocked"
' Parameter 4 : (Boolean) False
'--------------------------------------------------

long1228 = settingRepository1.GetAttr("RADIANT_INTENSITY_Small")
'--------------------------------------------------
' Parameter 1 : (String) "RADIANT_INTENSITY_Small"
' Returned value : (Variant) (Long) 1
'--------------------------------------------------

Dim bSTR2455
bSTR2455 = ""
Dim bSTR2456
bSTR2456 = ""
Dim boolean1228
settingRepository1.GetAttrInfo "RADIANT_INTENSITY_Small", bSTR2455, bSTR2456, boolean1228
'--------------------------------------------------
' Parameter 1 : (String) "RADIANT_INTENSITY_Small"
' Parameter 2 : (String) "Default value"
' Parameter 3 : (String) "Unlocked"
' Parameter 4 : (Boolean) False
'--------------------------------------------------

long1229 = settingRepository1.GetAttr("RADIANT_INTENSITY_ExtraSmall")
'--------------------------------------------------
' Parameter 1 : (String) "RADIANT_INTENSITY_ExtraSmall"
' Returned value : (Variant) (Long) 1
'--------------------------------------------------

Dim bSTR2457
bSTR2457 = ""
Dim bSTR2458
bSTR2458 = ""
Dim boolean1229
settingRepository1.GetAttrInfo "RADIANT_INTENSITY_ExtraSmall", bSTR2457, bSTR2458, boolean1229
'--------------------------------------------------
' Parameter 1 : (String) "RADIANT_INTENSITY_ExtraSmall"
' Parameter 2 : (String) "Default value"
' Parameter 3 : (String) "Unlocked"
' Parameter 4 : (Boolean) False
'--------------------------------------------------

long1230 = settingRepository1.GetAttr("RADIANT_INTENSITY_Nanometric")
'--------------------------------------------------
' Parameter 1 : (String) "RADIANT_INTENSITY_Nanometric"
' Returned value : (Variant) (Long) 1
'--------------------------------------------------

Dim bSTR2459
bSTR2459 = ""
Dim bSTR2460
bSTR2460 = ""
Dim boolean1230
settingRepository1.GetAttrInfo "RADIANT_INTENSITY_Nanometric", bSTR2459, bSTR2460, boolean1230
'--------------------------------------------------
' Parameter 1 : (String) "RADIANT_INTENSITY_Nanometric"
' Parameter 2 : (String) "Default value"
' Parameter 3 : (String) "Unlocked"
' Parameter 4 : (Boolean) False
'--------------------------------------------------

long1231 = settingRepository1.GetAttr("HEAT_GENERATION_RATE")
'--------------------------------------------------
' Parameter 1 : (String) "HEAT_GENERATION_RATE"
' Returned value : (Variant) (Long) 1
'--------------------------------------------------

Dim bSTR2461
bSTR2461 = ""
Dim bSTR2462
bSTR2462 = ""
Dim boolean1231
settingRepository1.GetAttrInfo "HEAT_GENERATION_RATE", bSTR2461, bSTR2462, boolean1231
'--------------------------------------------------
' Parameter 1 : (String) "HEAT_GENERATION_RATE"
' Parameter 2 : (String) "Default value"
' Parameter 3 : (String) "Unlocked"
' Parameter 4 : (Boolean) False
'--------------------------------------------------

long1232 = settingRepository1.GetAttr("HEAT_GENERATION_RATE_Large")
'--------------------------------------------------
' Parameter 1 : (String) "HEAT_GENERATION_RATE_Large"
' Returned value : (Variant) (Long) 1
'--------------------------------------------------

Dim bSTR2463
bSTR2463 = ""
Dim bSTR2464
bSTR2464 = ""
Dim boolean1232
settingRepository1.GetAttrInfo "HEAT_GENERATION_RATE_Large", bSTR2463, bSTR2464, boolean1232
'--------------------------------------------------
' Parameter 1 : (String) "HEAT_GENERATION_RATE_Large"
' Parameter 2 : (String) "Default value"
' Parameter 3 : (String) "Unlocked"
' Parameter 4 : (Boolean) False
'--------------------------------------------------

long1233 = settingRepository1.GetAttr("HEAT_GENERATION_RATE_ExtraLarge")
'--------------------------------------------------
' Parameter 1 : (String) "HEAT_GENERATION_RATE_ExtraLarge"
' Returned value : (Variant) (Long) 1
'--------------------------------------------------

Dim bSTR2465
bSTR2465 = ""
Dim bSTR2466
bSTR2466 = ""
Dim boolean1233
settingRepository1.GetAttrInfo "HEAT_GENERATION_RATE_ExtraLarge", bSTR2465, bSTR2466, boolean1233
'--------------------------------------------------
' Parameter 1 : (String) "HEAT_GENERATION_RATE_ExtraLarge"
' Parameter 2 : (String) "Default value"
' Parameter 3 : (String) "Unlocked"
' Parameter 4 : (Boolean) False
'--------------------------------------------------

long1234 = settingRepository1.GetAttr("HEAT_GENERATION_RATE_Small")
'--------------------------------------------------
' Parameter 1 : (String) "HEAT_GENERATION_RATE_Small"
' Returned value : (Variant) (Long) 1
'--------------------------------------------------

Dim bSTR2467
bSTR2467 = ""
Dim bSTR2468
bSTR2468 = ""
Dim boolean1234
settingRepository1.GetAttrInfo "HEAT_GENERATION_RATE_Small", bSTR2467, bSTR2468, boolean1234
'--------------------------------------------------
' Parameter 1 : (String) "HEAT_GENERATION_RATE_Small"
' Parameter 2 : (String) "Default value"
' Parameter 3 : (String) "Unlocked"
' Parameter 4 : (Boolean) False
'--------------------------------------------------

long1235 = settingRepository1.GetAttr("HEAT_GENERATION_RATE_ExtraSmall")
'--------------------------------------------------
' Parameter 1 : (String) "HEAT_GENERATION_RATE_ExtraSmall"
' Returned value : (Variant) (Long) 1
'--------------------------------------------------

Dim bSTR2469
bSTR2469 = ""
Dim bSTR2470
bSTR2470 = ""
Dim boolean1235
settingRepository1.GetAttrInfo "HEAT_GENERATION_RATE_ExtraSmall", bSTR2469, bSTR2470, boolean1235
'--------------------------------------------------
' Parameter 1 : (String) "HEAT_GENERATION_RATE_ExtraSmall"
' Parameter 2 : (String) "Default value"
' Parameter 3 : (String) "Unlocked"
' Parameter 4 : (Boolean) False
'--------------------------------------------------

long1236 = settingRepository1.GetAttr("HEAT_GENERATION_RATE_Nanometric")
'--------------------------------------------------
' Parameter 1 : (String) "HEAT_GENERATION_RATE_Nanometric"
' Returned value : (Variant) (Long) 1
'--------------------------------------------------

Dim bSTR2471
bSTR2471 = ""
Dim bSTR2472
bSTR2472 = ""
Dim boolean1236
settingRepository1.GetAttrInfo "HEAT_GENERATION_RATE_Nanometric", bSTR2471, bSTR2472, boolean1236
'--------------------------------------------------
' Parameter 1 : (String) "HEAT_GENERATION_RATE_Nanometric"
' Parameter 2 : (String) "Default value"
' Parameter 3 : (String) "Unlocked"
' Parameter 4 : (Boolean) False
'--------------------------------------------------

long1237 = settingRepository1.GetAttr("Exothermy")
'--------------------------------------------------
' Parameter 1 : (String) "Exothermy"
' Returned value : (Variant) (Long) 1
'--------------------------------------------------

Dim bSTR2473
bSTR2473 = ""
Dim bSTR2474
bSTR2474 = ""
Dim boolean1237
settingRepository1.GetAttrInfo "Exothermy", bSTR2473, bSTR2474, boolean1237
'--------------------------------------------------
' Parameter 1 : (String) "Exothermy"
' Parameter 2 : (String) "Default value"
' Parameter 3 : (String) "Unlocked"
' Parameter 4 : (Boolean) False
'--------------------------------------------------

long1238 = settingRepository1.GetAttr("Exothermy_Large")
'--------------------------------------------------
' Parameter 1 : (String) "Exothermy_Large"
' Returned value : (Variant) (Long) 1
'--------------------------------------------------

Dim bSTR2475
bSTR2475 = ""
Dim bSTR2476
bSTR2476 = ""
Dim boolean1238
settingRepository1.GetAttrInfo "Exothermy_Large", bSTR2475, bSTR2476, boolean1238
'--------------------------------------------------
' Parameter 1 : (String) "Exothermy_Large"
' Parameter 2 : (String) "Default value"
' Parameter 3 : (String) "Unlocked"
' Parameter 4 : (Boolean) False
'--------------------------------------------------

long1239 = settingRepository1.GetAttr("Exothermy_ExtraLarge")
'--------------------------------------------------
' Parameter 1 : (String) "Exothermy_ExtraLarge"
' Returned value : (Variant) (Long) 1
'--------------------------------------------------

Dim bSTR2477
bSTR2477 = ""
Dim bSTR2478
bSTR2478 = ""
Dim boolean1239
settingRepository1.GetAttrInfo "Exothermy_ExtraLarge", bSTR2477, bSTR2478, boolean1239
'--------------------------------------------------
' Parameter 1 : (String) "Exothermy_ExtraLarge"
' Parameter 2 : (String) "Default value"
' Parameter 3 : (String) "Unlocked"
' Parameter 4 : (Boolean) False
'--------------------------------------------------

long1240 = settingRepository1.GetAttr("Exothermy_Small")
'--------------------------------------------------
' Parameter 1 : (String) "Exothermy_Small"
' Returned value : (Variant) (Long) 1
'--------------------------------------------------

Dim bSTR2479
bSTR2479 = ""
Dim bSTR2480
bSTR2480 = ""
Dim boolean1240
settingRepository1.GetAttrInfo "Exothermy_Small", bSTR2479, bSTR2480, boolean1240
'--------------------------------------------------
' Parameter 1 : (String) "Exothermy_Small"
' Parameter 2 : (String) "Default value"
' Parameter 3 : (String) "Unlocked"
' Parameter 4 : (Boolean) False
'--------------------------------------------------

long1241 = settingRepository1.GetAttr("Exothermy_ExtraSmall")
'--------------------------------------------------
' Parameter 1 : (String) "Exothermy_ExtraSmall"
' Returned value : (Variant) (Long) 1
'--------------------------------------------------

Dim bSTR2481
bSTR2481 = ""
Dim bSTR2482
bSTR2482 = ""
Dim boolean1241
settingRepository1.GetAttrInfo "Exothermy_ExtraSmall", bSTR2481, bSTR2482, boolean1241
'--------------------------------------------------
' Parameter 1 : (String) "Exothermy_ExtraSmall"
' Parameter 2 : (String) "Default value"
' Parameter 3 : (String) "Unlocked"
' Parameter 4 : (Boolean) False
'--------------------------------------------------

long1242 = settingRepository1.GetAttr("Exothermy_Nanometric")
'--------------------------------------------------
' Parameter 1 : (String) "Exothermy_Nanometric"
' Returned value : (Variant) (Long) 1
'--------------------------------------------------

Dim bSTR2483
bSTR2483 = ""
Dim bSTR2484
bSTR2484 = ""
Dim boolean1242
settingRepository1.GetAttrInfo "Exothermy_Nanometric", bSTR2483, bSTR2484, boolean1242
'--------------------------------------------------
' Parameter 1 : (String) "Exothermy_Nanometric"
' Parameter 2 : (String) "Default value"
' Parameter 3 : (String) "Unlocked"
' Parameter 4 : (Boolean) False
'--------------------------------------------------

long1243 = settingRepository1.GetAttr("ACOUSTIC_POWER")
'--------------------------------------------------
' Parameter 1 : (String) "ACOUSTIC_POWER"
' Returned value : (Variant) (Long) 1
'--------------------------------------------------

Dim bSTR2485
bSTR2485 = ""
Dim bSTR2486
bSTR2486 = ""
Dim boolean1243
settingRepository1.GetAttrInfo "ACOUSTIC_POWER", bSTR2485, bSTR2486, boolean1243
'--------------------------------------------------
' Parameter 1 : (String) "ACOUSTIC_POWER"
' Parameter 2 : (String) "Default value"
' Parameter 3 : (String) "Unlocked"
' Parameter 4 : (Boolean) False
'--------------------------------------------------

long1244 = settingRepository1.GetAttr("ACOUSTIC_POWER_Large")
'--------------------------------------------------
' Parameter 1 : (String) "ACOUSTIC_POWER_Large"
' Returned value : (Variant) (Long) 1
'--------------------------------------------------

Dim bSTR2487
bSTR2487 = ""
Dim bSTR2488
bSTR2488 = ""
Dim boolean1244
settingRepository1.GetAttrInfo "ACOUSTIC_POWER_Large", bSTR2487, bSTR2488, boolean1244
'--------------------------------------------------
' Parameter 1 : (String) "ACOUSTIC_POWER_Large"
' Parameter 2 : (String) "Default value"
' Parameter 3 : (String) "Unlocked"
' Parameter 4 : (Boolean) False
'--------------------------------------------------

long1245 = settingRepository1.GetAttr("ACOUSTIC_POWER_ExtraLarge")
'--------------------------------------------------
' Parameter 1 : (String) "ACOUSTIC_POWER_ExtraLarge"
' Returned value : (Variant) (Long) 1
'--------------------------------------------------

Dim bSTR2489
bSTR2489 = ""
Dim bSTR2490
bSTR2490 = ""
Dim boolean1245
settingRepository1.GetAttrInfo "ACOUSTIC_POWER_ExtraLarge", bSTR2489, bSTR2490, boolean1245
'--------------------------------------------------
' Parameter 1 : (String) "ACOUSTIC_POWER_ExtraLarge"
' Parameter 2 : (String) "Default value"
' Parameter 3 : (String) "Unlocked"
' Parameter 4 : (Boolean) False
'--------------------------------------------------

long1246 = settingRepository1.GetAttr("ACOUSTIC_POWER_Small")
'--------------------------------------------------
' Parameter 1 : (String) "ACOUSTIC_POWER_Small"
' Returned value : (Variant) (Long) 1
'--------------------------------------------------

Dim bSTR2491
bSTR2491 = ""
Dim bSTR2492
bSTR2492 = ""
Dim boolean1246
settingRepository1.GetAttrInfo "ACOUSTIC_POWER_Small", bSTR2491, bSTR2492, boolean1246
'--------------------------------------------------
' Parameter 1 : (String) "ACOUSTIC_POWER_Small"
' Parameter 2 : (String) "Default value"
' Parameter 3 : (String) "Unlocked"
' Parameter 4 : (Boolean) False
'--------------------------------------------------

long1247 = settingRepository1.GetAttr("ACOUSTIC_POWER_ExtraSmall")
'--------------------------------------------------
' Parameter 1 : (String) "ACOUSTIC_POWER_ExtraSmall"
' Returned value : (Variant) (Long) 1
'--------------------------------------------------

Dim bSTR2493
bSTR2493 = ""
Dim bSTR2494
bSTR2494 = ""
Dim boolean1247
settingRepository1.GetAttrInfo "ACOUSTIC_POWER_ExtraSmall", bSTR2493, bSTR2494, boolean1247
'--------------------------------------------------
' Parameter 1 : (String) "ACOUSTIC_POWER_ExtraSmall"
' Parameter 2 : (String) "Default value"
' Parameter 3 : (String) "Unlocked"
' Parameter 4 : (Boolean) False
'--------------------------------------------------

long1248 = settingRepository1.GetAttr("ACOUSTIC_POWER_Nanometric")
'--------------------------------------------------
' Parameter 1 : (String) "ACOUSTIC_POWER_Nanometric"
' Returned value : (Variant) (Long) 1
'--------------------------------------------------

Dim bSTR2495
bSTR2495 = ""
Dim bSTR2496
bSTR2496 = ""
Dim boolean1248
settingRepository1.GetAttrInfo "ACOUSTIC_POWER_Nanometric", bSTR2495, bSTR2496, boolean1248
'--------------------------------------------------
' Parameter 1 : (String) "ACOUSTIC_POWER_Nanometric"
' Parameter 2 : (String) "Default value"
' Parameter 3 : (String) "Unlocked"
' Parameter 4 : (Boolean) False
'--------------------------------------------------

long1249 = settingRepository1.GetAttr("INVERSE_VELOCITY")
'--------------------------------------------------
' Parameter 1 : (String) "INVERSE_VELOCITY"
' Returned value : (Variant) (Long) 1
'--------------------------------------------------

Dim bSTR2497
bSTR2497 = ""
Dim bSTR2498
bSTR2498 = ""
Dim boolean1249
settingRepository1.GetAttrInfo "INVERSE_VELOCITY", bSTR2497, bSTR2498, boolean1249
'--------------------------------------------------
' Parameter 1 : (String) "INVERSE_VELOCITY"
' Parameter 2 : (String) "Default value"
' Parameter 3 : (String) "Unlocked"
' Parameter 4 : (Boolean) False
'--------------------------------------------------

long1250 = settingRepository1.GetAttr("INVERSE_VELOCITY_Large")
'--------------------------------------------------
' Parameter 1 : (String) "INVERSE_VELOCITY_Large"
' Returned value : (Variant) (Long) 1
'--------------------------------------------------

Dim bSTR2499
bSTR2499 = ""
Dim bSTR2500
bSTR2500 = ""
Dim boolean1250
settingRepository1.GetAttrInfo "INVERSE_VELOCITY_Large", bSTR2499, bSTR2500, boolean1250
'--------------------------------------------------
' Parameter 1 : (String) "INVERSE_VELOCITY_Large"
' Parameter 2 : (String) "Default value"
' Parameter 3 : (String) "Unlocked"
' Parameter 4 : (Boolean) False
'--------------------------------------------------

long1251 = settingRepository1.GetAttr("INVERSE_VELOCITY_ExtraLarge")
'--------------------------------------------------
' Parameter 1 : (String) "INVERSE_VELOCITY_ExtraLarge"
' Returned value : (Variant) (Long) 1
'--------------------------------------------------

Dim bSTR2501
bSTR2501 = ""
Dim bSTR2502
bSTR2502 = ""
Dim boolean1251
settingRepository1.GetAttrInfo "INVERSE_VELOCITY_ExtraLarge", bSTR2501, bSTR2502, boolean1251
'--------------------------------------------------
' Parameter 1 : (String) "INVERSE_VELOCITY_ExtraLarge"
' Parameter 2 : (String) "Default value"
' Parameter 3 : (String) "Unlocked"
' Parameter 4 : (Boolean) False
'--------------------------------------------------

long1252 = settingRepository1.GetAttr("INVERSE_VELOCITY_Small")
'--------------------------------------------------
' Parameter 1 : (String) "INVERSE_VELOCITY_Small"
' Returned value : (Variant) (Long) 1
'--------------------------------------------------

Dim bSTR2503
bSTR2503 = ""
Dim bSTR2504
bSTR2504 = ""
Dim boolean1252
settingRepository1.GetAttrInfo "INVERSE_VELOCITY_Small", bSTR2503, bSTR2504, boolean1252
'--------------------------------------------------
' Parameter 1 : (String) "INVERSE_VELOCITY_Small"
' Parameter 2 : (String) "Default value"
' Parameter 3 : (String) "Unlocked"
' Parameter 4 : (Boolean) False
'--------------------------------------------------

long1253 = settingRepository1.GetAttr("INVERSE_VELOCITY_ExtraSmall")
'--------------------------------------------------
' Parameter 1 : (String) "INVERSE_VELOCITY_ExtraSmall"
' Returned value : (Variant) (Long) 1
'--------------------------------------------------

Dim bSTR2505
bSTR2505 = ""
Dim bSTR2506
bSTR2506 = ""
Dim boolean1253
settingRepository1.GetAttrInfo "INVERSE_VELOCITY_ExtraSmall", bSTR2505, bSTR2506, boolean1253
'--------------------------------------------------
' Parameter 1 : (String) "INVERSE_VELOCITY_ExtraSmall"
' Parameter 2 : (String) "Default value"
' Parameter 3 : (String) "Unlocked"
' Parameter 4 : (Boolean) False
'--------------------------------------------------

long1254 = settingRepository1.GetAttr("INVERSE_VELOCITY_Nanometric")
'--------------------------------------------------
' Parameter 1 : (String) "INVERSE_VELOCITY_Nanometric"
' Returned value : (Variant) (Long) 1
'--------------------------------------------------

Dim bSTR2507
bSTR2507 = ""
Dim bSTR2508
bSTR2508 = ""
Dim boolean1254
settingRepository1.GetAttrInfo "INVERSE_VELOCITY_Nanometric", bSTR2507, bSTR2508, boolean1254
'--------------------------------------------------
' Parameter 1 : (String) "INVERSE_VELOCITY_Nanometric"
' Parameter 2 : (String) "Default value"
' Parameter 3 : (String) "Unlocked"
' Parameter 4 : (Boolean) False
'--------------------------------------------------

long1255 = settingRepository1.GetAttr("WARPING_COEFFICIENT")
'--------------------------------------------------
' Parameter 1 : (String) "WARPING_COEFFICIENT"
' Returned value : (Variant) (Long) 1
'--------------------------------------------------

Dim bSTR2509
bSTR2509 = ""
Dim bSTR2510
bSTR2510 = ""
Dim boolean1255
settingRepository1.GetAttrInfo "WARPING_COEFFICIENT", bSTR2509, bSTR2510, boolean1255
'--------------------------------------------------
' Parameter 1 : (String) "WARPING_COEFFICIENT"
' Parameter 2 : (String) "Default value"
' Parameter 3 : (String) "Unlocked"
' Parameter 4 : (Boolean) False
'--------------------------------------------------

long1256 = settingRepository1.GetAttr("WARPING_COEFFICIENT_Large")
'--------------------------------------------------
' Parameter 1 : (String) "WARPING_COEFFICIENT_Large"
' Returned value : (Variant) (Long) 1
'--------------------------------------------------

Dim bSTR2511
bSTR2511 = ""
Dim bSTR2512
bSTR2512 = ""
Dim boolean1256
settingRepository1.GetAttrInfo "WARPING_COEFFICIENT_Large", bSTR2511, bSTR2512, boolean1256
'--------------------------------------------------
' Parameter 1 : (String) "WARPING_COEFFICIENT_Large"
' Parameter 2 : (String) "Default value"
' Parameter 3 : (String) "Unlocked"
' Parameter 4 : (Boolean) False
'--------------------------------------------------

long1257 = settingRepository1.GetAttr("WARPING_COEFFICIENT_ExtraLarge")
'--------------------------------------------------
' Parameter 1 : (String) "WARPING_COEFFICIENT_ExtraLarge"
' Returned value : (Variant) (Long) 1
'--------------------------------------------------

Dim bSTR2513
bSTR2513 = ""
Dim bSTR2514
bSTR2514 = ""
Dim boolean1257
settingRepository1.GetAttrInfo "WARPING_COEFFICIENT_ExtraLarge", bSTR2513, bSTR2514, boolean1257
'--------------------------------------------------
' Parameter 1 : (String) "WARPING_COEFFICIENT_ExtraLarge"
' Parameter 2 : (String) "Default value"
' Parameter 3 : (String) "Unlocked"
' Parameter 4 : (Boolean) False
'--------------------------------------------------

long1258 = settingRepository1.GetAttr("WARPING_COEFFICIENT_Small")
'--------------------------------------------------
' Parameter 1 : (String) "WARPING_COEFFICIENT_Small"
' Returned value : (Variant) (Long) 1
'--------------------------------------------------

Dim bSTR2515
bSTR2515 = ""
Dim bSTR2516
bSTR2516 = ""
Dim boolean1258
settingRepository1.GetAttrInfo "WARPING_COEFFICIENT_Small", bSTR2515, bSTR2516, boolean1258
'--------------------------------------------------
' Parameter 1 : (String) "WARPING_COEFFICIENT_Small"
' Parameter 2 : (String) "Default value"
' Parameter 3 : (String) "Unlocked"
' Parameter 4 : (Boolean) False
'--------------------------------------------------

long1259 = settingRepository1.GetAttr("WARPING_COEFFICIENT_ExtraSmall")
'--------------------------------------------------
' Parameter 1 : (String) "WARPING_COEFFICIENT_ExtraSmall"
' Returned value : (Variant) (Long) 1
'--------------------------------------------------

Dim bSTR2517
bSTR2517 = ""
Dim bSTR2518
bSTR2518 = ""
Dim boolean1259
settingRepository1.GetAttrInfo "WARPING_COEFFICIENT_ExtraSmall", bSTR2517, bSTR2518, boolean1259
'--------------------------------------------------
' Parameter 1 : (String) "WARPING_COEFFICIENT_ExtraSmall"
' Parameter 2 : (String) "Default value"
' Parameter 3 : (String) "Unlocked"
' Parameter 4 : (Boolean) False
'--------------------------------------------------

long1260 = settingRepository1.GetAttr("WARPING_COEFFICIENT_Nanometric")
'--------------------------------------------------
' Parameter 1 : (String) "WARPING_COEFFICIENT_Nanometric"
' Returned value : (Variant) (Long) 1
'--------------------------------------------------

Dim bSTR2519
bSTR2519 = ""
Dim bSTR2520
bSTR2520 = ""
Dim boolean1260
settingRepository1.GetAttrInfo "WARPING_COEFFICIENT_Nanometric", bSTR2519, bSTR2520, boolean1260
'--------------------------------------------------
' Parameter 1 : (String) "WARPING_COEFFICIENT_Nanometric"
' Parameter 2 : (String) "Default value"
' Parameter 3 : (String) "Unlocked"
' Parameter 4 : (Boolean) False
'--------------------------------------------------

long1261 = settingRepository1.GetAttr("SPECIFIC_HEAT_CAPACITY_LINEAR_PART")
'--------------------------------------------------
' Parameter 1 : (String) "SPECIFIC_HEAT_CAPACITY_LINEAR_PART"
' Returned value : (Variant) (Long) 1
'--------------------------------------------------

Dim bSTR2521
bSTR2521 = ""
Dim bSTR2522
bSTR2522 = ""
Dim boolean1261
settingRepository1.GetAttrInfo "SPECIFIC_HEAT_CAPACITY_LINEAR_PART", bSTR2521, bSTR2522, boolean1261
'--------------------------------------------------
' Parameter 1 : (String) "SPECIFIC_HEAT_CAPACITY_LINEAR_PART"
' Parameter 2 : (String) "Default value"
' Parameter 3 : (String) "Unlocked"
' Parameter 4 : (Boolean) False
'--------------------------------------------------

long1262 = settingRepository1.GetAttr("SPECIFIC_HEAT_CAPACITY_LINEAR_PART_Large")
'--------------------------------------------------
' Parameter 1 : (String) "SPECIFIC_HEAT_CAPACITY_LINEAR_PART_Large"
' Returned value : (Variant) (Long) 1
'--------------------------------------------------

Dim bSTR2523
bSTR2523 = ""
Dim bSTR2524
bSTR2524 = ""
Dim boolean1262
settingRepository1.GetAttrInfo "SPECIFIC_HEAT_CAPACITY_LINEAR_PART_Large", bSTR2523, bSTR2524, boolean1262
'--------------------------------------------------
' Parameter 1 : (String) "SPECIFIC_HEAT_CAPACITY_LINEAR_PART_Large"
' Parameter 2 : (String) "Default value"
' Parameter 3 : (String) "Unlocked"
' Parameter 4 : (Boolean) False
'--------------------------------------------------

long1263 = settingRepository1.GetAttr("SPECIFIC_HEAT_CAPACITY_LINEAR_PART_ExtraLarge")
'--------------------------------------------------
' Parameter 1 : (String) "SPECIFIC_HEAT_CAPACITY_LINEAR_PART_ExtraLarge"
' Returned value : (Variant) (Long) 1
'--------------------------------------------------

Dim bSTR2525
bSTR2525 = ""
Dim bSTR2526
bSTR2526 = ""
Dim boolean1263
settingRepository1.GetAttrInfo "SPECIFIC_HEAT_CAPACITY_LINEAR_PART_ExtraLarge", bSTR2525, bSTR2526, boolean1263
'--------------------------------------------------
' Parameter 1 : (String) "SPECIFIC_HEAT_CAPACITY_LINEAR_PART_ExtraLarge"
' Parameter 2 : (String) "Default value"
' Parameter 3 : (String) "Unlocked"
' Parameter 4 : (Boolean) False
'--------------------------------------------------

long1264 = settingRepository1.GetAttr("SPECIFIC_HEAT_CAPACITY_LINEAR_PART_Small")
'--------------------------------------------------
' Parameter 1 : (String) "SPECIFIC_HEAT_CAPACITY_LINEAR_PART_Small"
' Returned value : (Variant) (Long) 1
'--------------------------------------------------

Dim bSTR2527
bSTR2527 = ""
Dim bSTR2528
bSTR2528 = ""
Dim boolean1264
settingRepository1.GetAttrInfo "SPECIFIC_HEAT_CAPACITY_LINEAR_PART_Small", bSTR2527, bSTR2528, boolean1264
'--------------------------------------------------
' Parameter 1 : (String) "SPECIFIC_HEAT_CAPACITY_LINEAR_PART_Small"
' Parameter 2 : (String) "Default value"
' Parameter 3 : (String) "Unlocked"
' Parameter 4 : (Boolean) False
'--------------------------------------------------

long1265 = settingRepository1.GetAttr("SPECIFIC_HEAT_CAPACITY_LINEAR_PART_ExtraSmall")
'--------------------------------------------------
' Parameter 1 : (String) "SPECIFIC_HEAT_CAPACITY_LINEAR_PART_ExtraSmall"
' Returned value : (Variant) (Long) 1
'--------------------------------------------------

Dim bSTR2529
bSTR2529 = ""
Dim bSTR2530
bSTR2530 = ""
Dim boolean1265
settingRepository1.GetAttrInfo "SPECIFIC_HEAT_CAPACITY_LINEAR_PART_ExtraSmall", bSTR2529, bSTR2530, boolean1265
'--------------------------------------------------
' Parameter 1 : (String) "SPECIFIC_HEAT_CAPACITY_LINEAR_PART_ExtraSmall"
' Parameter 2 : (String) "Default value"
' Parameter 3 : (String) "Unlocked"
' Parameter 4 : (Boolean) False
'--------------------------------------------------

long1266 = settingRepository1.GetAttr("SPECIFIC_HEAT_CAPACITY_LINEAR_PART_Nanometric")
'--------------------------------------------------
' Parameter 1 : (String) "SPECIFIC_HEAT_CAPACITY_LINEAR_PART_Nanometric"
' Returned value : (Variant) (Long) 1
'--------------------------------------------------

Dim bSTR2531
bSTR2531 = ""
Dim bSTR2532
bSTR2532 = ""
Dim boolean1266
settingRepository1.GetAttrInfo "SPECIFIC_HEAT_CAPACITY_LINEAR_PART_Nanometric", bSTR2531, bSTR2532, boolean1266
'--------------------------------------------------
' Parameter 1 : (String) "SPECIFIC_HEAT_CAPACITY_LINEAR_PART_Nanometric"
' Parameter 2 : (String) "Default value"
' Parameter 3 : (String) "Unlocked"
' Parameter 4 : (Boolean) False
'--------------------------------------------------

long1267 = settingRepository1.GetAttr("SPECIFIC_HEAT_CAPACITY_QUADRATIC_PART")
'--------------------------------------------------
' Parameter 1 : (String) "SPECIFIC_HEAT_CAPACITY_QUADRATIC_PART"
' Returned value : (Variant) (Long) 1
'--------------------------------------------------

Dim bSTR2533
bSTR2533 = ""
Dim bSTR2534
bSTR2534 = ""
Dim boolean1267
settingRepository1.GetAttrInfo "SPECIFIC_HEAT_CAPACITY_QUADRATIC_PART", bSTR2533, bSTR2534, boolean1267
'--------------------------------------------------
' Parameter 1 : (String) "SPECIFIC_HEAT_CAPACITY_QUADRATIC_PART"
' Parameter 2 : (String) "Default value"
' Parameter 3 : (String) "Unlocked"
' Parameter 4 : (Boolean) False
'--------------------------------------------------

long1268 = settingRepository1.GetAttr("SPECIFIC_HEAT_CAPACITY_QUADRATIC_PART_Large")
'--------------------------------------------------
' Parameter 1 : (String) "SPECIFIC_HEAT_CAPACITY_QUADRATIC_PART_Large"
' Returned value : (Variant) (Long) 1
'--------------------------------------------------

Dim bSTR2535
bSTR2535 = ""
Dim bSTR2536
bSTR2536 = ""
Dim boolean1268
settingRepository1.GetAttrInfo "SPECIFIC_HEAT_CAPACITY_QUADRATIC_PART_Large", bSTR2535, bSTR2536, boolean1268
'--------------------------------------------------
' Parameter 1 : (String) "SPECIFIC_HEAT_CAPACITY_QUADRATIC_PART_Large"
' Parameter 2 : (String) "Default value"
' Parameter 3 : (String) "Unlocked"
' Parameter 4 : (Boolean) False
'--------------------------------------------------

long1269 = settingRepository1.GetAttr("SPECIFIC_HEAT_CAPACITY_QUADRATIC_PART_ExtraLarge")
'--------------------------------------------------
' Parameter 1 : (String) "SPECIFIC_HEAT_CAPACITY_QUADRATIC_PART_ExtraLarge"
' Returned value : (Variant) (Long) 1
'--------------------------------------------------

Dim bSTR2537
bSTR2537 = ""
Dim bSTR2538
bSTR2538 = ""
Dim boolean1269
settingRepository1.GetAttrInfo "SPECIFIC_HEAT_CAPACITY_QUADRATIC_PART_ExtraLarge", bSTR2537, bSTR2538, boolean1269
'--------------------------------------------------
' Parameter 1 : (String) "SPECIFIC_HEAT_CAPACITY_QUADRATIC_PART_ExtraLarge"
' Parameter 2 : (String) "Default value"
' Parameter 3 : (String) "Unlocked"
' Parameter 4 : (Boolean) False
'--------------------------------------------------

long1270 = settingRepository1.GetAttr("SPECIFIC_HEAT_CAPACITY_QUADRATIC_PART_Small")
'--------------------------------------------------
' Parameter 1 : (String) "SPECIFIC_HEAT_CAPACITY_QUADRATIC_PART_Small"
' Returned value : (Variant) (Long) 1
'--------------------------------------------------

Dim bSTR2539
bSTR2539 = ""
Dim bSTR2540
bSTR2540 = ""
Dim boolean1270
settingRepository1.GetAttrInfo "SPECIFIC_HEAT_CAPACITY_QUADRATIC_PART_Small", bSTR2539, bSTR2540, boolean1270
'--------------------------------------------------
' Parameter 1 : (String) "SPECIFIC_HEAT_CAPACITY_QUADRATIC_PART_Small"
' Parameter 2 : (String) "Default value"
' Parameter 3 : (String) "Unlocked"
' Parameter 4 : (Boolean) False
'--------------------------------------------------

long1271 = settingRepository1.GetAttr("SPECIFIC_HEAT_CAPACITY_QUADRATIC_PART_ExtraSmall")
'--------------------------------------------------
' Parameter 1 : (String) "SPECIFIC_HEAT_CAPACITY_QUADRATIC_PART_ExtraSmall"
' Returned value : (Variant) (Long) 1
'--------------------------------------------------

Dim bSTR2541
bSTR2541 = ""
Dim bSTR2542
bSTR2542 = ""
Dim boolean1271
settingRepository1.GetAttrInfo "SPECIFIC_HEAT_CAPACITY_QUADRATIC_PART_ExtraSmall", bSTR2541, bSTR2542, boolean1271
'--------------------------------------------------
' Parameter 1 : (String) "SPECIFIC_HEAT_CAPACITY_QUADRATIC_PART_ExtraSmall"
' Parameter 2 : (String) "Default value"
' Parameter 3 : (String) "Unlocked"
' Parameter 4 : (Boolean) False
'--------------------------------------------------

long1272 = settingRepository1.GetAttr("SPECIFIC_HEAT_CAPACITY_QUADRATIC_PART_Nanometric")
'--------------------------------------------------
' Parameter 1 : (String) "SPECIFIC_HEAT_CAPACITY_QUADRATIC_PART_Nanometric"
' Returned value : (Variant) (Long) 1
'--------------------------------------------------

Dim bSTR2543
bSTR2543 = ""
Dim bSTR2544
bSTR2544 = ""
Dim boolean1272
settingRepository1.GetAttrInfo "SPECIFIC_HEAT_CAPACITY_QUADRATIC_PART_Nanometric", bSTR2543, bSTR2544, boolean1272
'--------------------------------------------------
' Parameter 1 : (String) "SPECIFIC_HEAT_CAPACITY_QUADRATIC_PART_Nanometric"
' Parameter 2 : (String) "Default value"
' Parameter 3 : (String) "Unlocked"
' Parameter 4 : (Boolean) False
'--------------------------------------------------

long1273 = settingRepository1.GetAttr("SPECIFIC_HEAT_CAPACITY_CUBIC_PART")
'--------------------------------------------------
' Parameter 1 : (String) "SPECIFIC_HEAT_CAPACITY_CUBIC_PART"
' Returned value : (Variant) (Long) 1
'--------------------------------------------------

Dim bSTR2545
bSTR2545 = ""
Dim bSTR2546
bSTR2546 = ""
Dim boolean1273
settingRepository1.GetAttrInfo "SPECIFIC_HEAT_CAPACITY_CUBIC_PART", bSTR2545, bSTR2546, boolean1273
'--------------------------------------------------
' Parameter 1 : (String) "SPECIFIC_HEAT_CAPACITY_CUBIC_PART"
' Parameter 2 : (String) "Default value"
' Parameter 3 : (String) "Unlocked"
' Parameter 4 : (Boolean) False
'--------------------------------------------------

long1274 = settingRepository1.GetAttr("SPECIFIC_HEAT_CAPACITY_CUBIC_PART_Large")
'--------------------------------------------------
' Parameter 1 : (String) "SPECIFIC_HEAT_CAPACITY_CUBIC_PART_Large"
' Returned value : (Variant) (Long) 1
'--------------------------------------------------

Dim bSTR2547
bSTR2547 = ""
Dim bSTR2548
bSTR2548 = ""
Dim boolean1274
settingRepository1.GetAttrInfo "SPECIFIC_HEAT_CAPACITY_CUBIC_PART_Large", bSTR2547, bSTR2548, boolean1274
'--------------------------------------------------
' Parameter 1 : (String) "SPECIFIC_HEAT_CAPACITY_CUBIC_PART_Large"
' Parameter 2 : (String) "Default value"
' Parameter 3 : (String) "Unlocked"
' Parameter 4 : (Boolean) False
'--------------------------------------------------

long1275 = settingRepository1.GetAttr("SPECIFIC_HEAT_CAPACITY_CUBIC_PART_ExtraLarge")
'--------------------------------------------------
' Parameter 1 : (String) "SPECIFIC_HEAT_CAPACITY_CUBIC_PART_ExtraLarge"
' Returned value : (Variant) (Long) 1
'--------------------------------------------------

Dim bSTR2549
bSTR2549 = ""
Dim bSTR2550
bSTR2550 = ""
Dim boolean1275
settingRepository1.GetAttrInfo "SPECIFIC_HEAT_CAPACITY_CUBIC_PART_ExtraLarge", bSTR2549, bSTR2550, boolean1275
'--------------------------------------------------
' Parameter 1 : (String) "SPECIFIC_HEAT_CAPACITY_CUBIC_PART_ExtraLarge"
' Parameter 2 : (String) "Default value"
' Parameter 3 : (String) "Unlocked"
' Parameter 4 : (Boolean) False
'--------------------------------------------------

long1276 = settingRepository1.GetAttr("SPECIFIC_HEAT_CAPACITY_CUBIC_PART_Small")
'--------------------------------------------------
' Parameter 1 : (String) "SPECIFIC_HEAT_CAPACITY_CUBIC_PART_Small"
' Returned value : (Variant) (Long) 1
'--------------------------------------------------

Dim bSTR2551
bSTR2551 = ""
Dim bSTR2552
bSTR2552 = ""
Dim boolean1276
settingRepository1.GetAttrInfo "SPECIFIC_HEAT_CAPACITY_CUBIC_PART_Small", bSTR2551, bSTR2552, boolean1276
'--------------------------------------------------
' Parameter 1 : (String) "SPECIFIC_HEAT_CAPACITY_CUBIC_PART_Small"
' Parameter 2 : (String) "Default value"
' Parameter 3 : (String) "Unlocked"
' Parameter 4 : (Boolean) False
'--------------------------------------------------

long1277 = settingRepository1.GetAttr("SPECIFIC_HEAT_CAPACITY_CUBIC_PART_ExtraSmall")
'--------------------------------------------------
' Parameter 1 : (String) "SPECIFIC_HEAT_CAPACITY_CUBIC_PART_ExtraSmall"
' Returned value : (Variant) (Long) 1
'--------------------------------------------------

Dim bSTR2553
bSTR2553 = ""
Dim bSTR2554
bSTR2554 = ""
Dim boolean1277
settingRepository1.GetAttrInfo "SPECIFIC_HEAT_CAPACITY_CUBIC_PART_ExtraSmall", bSTR2553, bSTR2554, boolean1277
'--------------------------------------------------
' Parameter 1 : (String) "SPECIFIC_HEAT_CAPACITY_CUBIC_PART_ExtraSmall"
' Parameter 2 : (String) "Default value"
' Parameter 3 : (String) "Unlocked"
' Parameter 4 : (Boolean) False
'--------------------------------------------------

long1278 = settingRepository1.GetAttr("SPECIFIC_HEAT_CAPACITY_CUBIC_PART_Nanometric")
'--------------------------------------------------
' Parameter 1 : (String) "SPECIFIC_HEAT_CAPACITY_CUBIC_PART_Nanometric"
' Returned value : (Variant) (Long) 1
'--------------------------------------------------

Dim bSTR2555
bSTR2555 = ""
Dim bSTR2556
bSTR2556 = ""
Dim boolean1278
settingRepository1.GetAttrInfo "SPECIFIC_HEAT_CAPACITY_CUBIC_PART_Nanometric", bSTR2555, bSTR2556, boolean1278
'--------------------------------------------------
' Parameter 1 : (String) "SPECIFIC_HEAT_CAPACITY_CUBIC_PART_Nanometric"
' Parameter 2 : (String) "Default value"
' Parameter 3 : (String) "Unlocked"
' Parameter 4 : (Boolean) False
'--------------------------------------------------

long1279 = settingRepository1.GetAttr("TORQUE")
'--------------------------------------------------
' Parameter 1 : (String) "TORQUE"
' Returned value : (Variant) (Long) 1
'--------------------------------------------------

Dim bSTR2557
bSTR2557 = ""
Dim bSTR2558
bSTR2558 = ""
Dim boolean1279
settingRepository1.GetAttrInfo "TORQUE", bSTR2557, bSTR2558, boolean1279
'--------------------------------------------------
' Parameter 1 : (String) "TORQUE"
' Parameter 2 : (String) "Default value"
' Parameter 3 : (String) "Unlocked"
' Parameter 4 : (Boolean) False
'--------------------------------------------------

long1280 = settingRepository1.GetAttr("TORQUE_Large")
'--------------------------------------------------
' Parameter 1 : (String) "TORQUE_Large"
' Returned value : (Variant) (Long) 1
'--------------------------------------------------

Dim bSTR2559
bSTR2559 = ""
Dim bSTR2560
bSTR2560 = ""
Dim boolean1280
settingRepository1.GetAttrInfo "TORQUE_Large", bSTR2559, bSTR2560, boolean1280
'--------------------------------------------------
' Parameter 1 : (String) "TORQUE_Large"
' Parameter 2 : (String) "Default value"
' Parameter 3 : (String) "Unlocked"
' Parameter 4 : (Boolean) False
'--------------------------------------------------

long1281 = settingRepository1.GetAttr("TORQUE_ExtraLarge")
'--------------------------------------------------
' Parameter 1 : (String) "TORQUE_ExtraLarge"
' Returned value : (Variant) (Long) 1
'--------------------------------------------------

Dim bSTR2561
bSTR2561 = ""
Dim bSTR2562
bSTR2562 = ""
Dim boolean1281
settingRepository1.GetAttrInfo "TORQUE_ExtraLarge", bSTR2561, bSTR2562, boolean1281
'--------------------------------------------------
' Parameter 1 : (String) "TORQUE_ExtraLarge"
' Parameter 2 : (String) "Default value"
' Parameter 3 : (String) "Unlocked"
' Parameter 4 : (Boolean) False
'--------------------------------------------------

long1282 = settingRepository1.GetAttr("TORQUE_Small")
'--------------------------------------------------
' Parameter 1 : (String) "TORQUE_Small"
' Returned value : (Variant) (Long) 1
'--------------------------------------------------

Dim bSTR2563
bSTR2563 = ""
Dim bSTR2564
bSTR2564 = ""
Dim boolean1282
settingRepository1.GetAttrInfo "TORQUE_Small", bSTR2563, bSTR2564, boolean1282
'--------------------------------------------------
' Parameter 1 : (String) "TORQUE_Small"
' Parameter 2 : (String) "Default value"
' Parameter 3 : (String) "Unlocked"
' Parameter 4 : (Boolean) False
'--------------------------------------------------

long1283 = settingRepository1.GetAttr("TORQUE_ExtraSmall")
'--------------------------------------------------
' Parameter 1 : (String) "TORQUE_ExtraSmall"
' Returned value : (Variant) (Long) 1
'--------------------------------------------------

Dim bSTR2565
bSTR2565 = ""
Dim bSTR2566
bSTR2566 = ""
Dim boolean1283
settingRepository1.GetAttrInfo "TORQUE_ExtraSmall", bSTR2565, bSTR2566, boolean1283
'--------------------------------------------------
' Parameter 1 : (String) "TORQUE_ExtraSmall"
' Parameter 2 : (String) "Default value"
' Parameter 3 : (String) "Unlocked"
' Parameter 4 : (Boolean) False
'--------------------------------------------------

long1284 = settingRepository1.GetAttr("TORQUE_Nanometric")
'--------------------------------------------------
' Parameter 1 : (String) "TORQUE_Nanometric"
' Returned value : (Variant) (Long) 1
'--------------------------------------------------

Dim bSTR2567
bSTR2567 = ""
Dim bSTR2568
bSTR2568 = ""
Dim boolean1284
settingRepository1.GetAttrInfo "TORQUE_Nanometric", bSTR2567, bSTR2568, boolean1284
'--------------------------------------------------
' Parameter 1 : (String) "TORQUE_Nanometric"
' Parameter 2 : (String) "Default value"
' Parameter 3 : (String) "Unlocked"
' Parameter 4 : (Boolean) False
'--------------------------------------------------

long1285 = settingRepository1.GetAttr("ELECTRICAL_CONDUCTIVITY")
'--------------------------------------------------
' Parameter 1 : (String) "ELECTRICAL_CONDUCTIVITY"
' Returned value : (Variant) (Long) 1
'--------------------------------------------------

Dim bSTR2569
bSTR2569 = ""
Dim bSTR2570
bSTR2570 = ""
Dim boolean1285
settingRepository1.GetAttrInfo "ELECTRICAL_CONDUCTIVITY", bSTR2569, bSTR2570, boolean1285
'--------------------------------------------------
' Parameter 1 : (String) "ELECTRICAL_CONDUCTIVITY"
' Parameter 2 : (String) "Default value"
' Parameter 3 : (String) "Unlocked"
' Parameter 4 : (Boolean) False
'--------------------------------------------------

long1286 = settingRepository1.GetAttr("ELECTRICAL_CONDUCTIVITY_Large")
'--------------------------------------------------
' Parameter 1 : (String) "ELECTRICAL_CONDUCTIVITY_Large"
' Returned value : (Variant) (Long) 1
'--------------------------------------------------

Dim bSTR2571
bSTR2571 = ""
Dim bSTR2572
bSTR2572 = ""
Dim boolean1286
settingRepository1.GetAttrInfo "ELECTRICAL_CONDUCTIVITY_Large", bSTR2571, bSTR2572, boolean1286
'--------------------------------------------------
' Parameter 1 : (String) "ELECTRICAL_CONDUCTIVITY_Large"
' Parameter 2 : (String) "Default value"
' Parameter 3 : (String) "Unlocked"
' Parameter 4 : (Boolean) False
'--------------------------------------------------

long1287 = settingRepository1.GetAttr("ELECTRICAL_CONDUCTIVITY_ExtraLarge")
'--------------------------------------------------
' Parameter 1 : (String) "ELECTRICAL_CONDUCTIVITY_ExtraLarge"
' Returned value : (Variant) (Long) 1
'--------------------------------------------------

Dim bSTR2573
bSTR2573 = ""
Dim bSTR2574
bSTR2574 = ""
Dim boolean1287
settingRepository1.GetAttrInfo "ELECTRICAL_CONDUCTIVITY_ExtraLarge", bSTR2573, bSTR2574, boolean1287
'--------------------------------------------------
' Parameter 1 : (String) "ELECTRICAL_CONDUCTIVITY_ExtraLarge"
' Parameter 2 : (String) "Default value"
' Parameter 3 : (String) "Unlocked"
' Parameter 4 : (Boolean) False
'--------------------------------------------------

long1288 = settingRepository1.GetAttr("ELECTRICAL_CONDUCTIVITY_Small")
'--------------------------------------------------
' Parameter 1 : (String) "ELECTRICAL_CONDUCTIVITY_Small"
' Returned value : (Variant) (Long) 1
'--------------------------------------------------

Dim bSTR2575
bSTR2575 = ""
Dim bSTR2576
bSTR2576 = ""
Dim boolean1288
settingRepository1.GetAttrInfo "ELECTRICAL_CONDUCTIVITY_Small", bSTR2575, bSTR2576, boolean1288
'--------------------------------------------------
' Parameter 1 : (String) "ELECTRICAL_CONDUCTIVITY_Small"
' Parameter 2 : (String) "Default value"
' Parameter 3 : (String) "Unlocked"
' Parameter 4 : (Boolean) False
'--------------------------------------------------

long1289 = settingRepository1.GetAttr("ELECTRICAL_CONDUCTIVITY_ExtraSmall")
'--------------------------------------------------
' Parameter 1 : (String) "ELECTRICAL_CONDUCTIVITY_ExtraSmall"
' Returned value : (Variant) (Long) 1
'--------------------------------------------------

Dim bSTR2577
bSTR2577 = ""
Dim bSTR2578
bSTR2578 = ""
Dim boolean1289
settingRepository1.GetAttrInfo "ELECTRICAL_CONDUCTIVITY_ExtraSmall", bSTR2577, bSTR2578, boolean1289
'--------------------------------------------------
' Parameter 1 : (String) "ELECTRICAL_CONDUCTIVITY_ExtraSmall"
' Parameter 2 : (String) "Default value"
' Parameter 3 : (String) "Unlocked"
' Parameter 4 : (Boolean) False
'--------------------------------------------------

long1290 = settingRepository1.GetAttr("ELECTRICAL_CONDUCTIVITY_Nanometric")
'--------------------------------------------------
' Parameter 1 : (String) "ELECTRICAL_CONDUCTIVITY_Nanometric"
' Returned value : (Variant) (Long) 1
'--------------------------------------------------

Dim bSTR2579
bSTR2579 = ""
Dim bSTR2580
bSTR2580 = ""
Dim boolean1290
settingRepository1.GetAttrInfo "ELECTRICAL_CONDUCTIVITY_Nanometric", bSTR2579, bSTR2580, boolean1290
'--------------------------------------------------
' Parameter 1 : (String) "ELECTRICAL_CONDUCTIVITY_Nanometric"
' Parameter 2 : (String) "Default value"
' Parameter 3 : (String) "Unlocked"
' Parameter 4 : (Boolean) False
'--------------------------------------------------

long1291 = settingRepository1.GetAttr("MAGNETIC_PERMEABILITY")
'--------------------------------------------------
' Parameter 1 : (String) "MAGNETIC_PERMEABILITY"
' Returned value : (Variant) (Long) 1
'--------------------------------------------------

Dim bSTR2581
bSTR2581 = ""
Dim bSTR2582
bSTR2582 = ""
Dim boolean1291
settingRepository1.GetAttrInfo "MAGNETIC_PERMEABILITY", bSTR2581, bSTR2582, boolean1291
'--------------------------------------------------
' Parameter 1 : (String) "MAGNETIC_PERMEABILITY"
' Parameter 2 : (String) "Default value"
' Parameter 3 : (String) "Unlocked"
' Parameter 4 : (Boolean) False
'--------------------------------------------------

long1292 = settingRepository1.GetAttr("MAGNETIC_PERMEABILITY_Large")
'--------------------------------------------------
' Parameter 1 : (String) "MAGNETIC_PERMEABILITY_Large"
' Returned value : (Variant) (Long) 1
'--------------------------------------------------

Dim bSTR2583
bSTR2583 = ""
Dim bSTR2584
bSTR2584 = ""
Dim boolean1292
settingRepository1.GetAttrInfo "MAGNETIC_PERMEABILITY_Large", bSTR2583, bSTR2584, boolean1292
'--------------------------------------------------
' Parameter 1 : (String) "MAGNETIC_PERMEABILITY_Large"
' Parameter 2 : (String) "Default value"
' Parameter 3 : (String) "Unlocked"
' Parameter 4 : (Boolean) False
'--------------------------------------------------

long1293 = settingRepository1.GetAttr("MAGNETIC_PERMEABILITY_ExtraLarge")
'--------------------------------------------------
' Parameter 1 : (String) "MAGNETIC_PERMEABILITY_ExtraLarge"
' Returned value : (Variant) (Long) 1
'--------------------------------------------------

Dim bSTR2585
bSTR2585 = ""
Dim bSTR2586
bSTR2586 = ""
Dim boolean1293
settingRepository1.GetAttrInfo "MAGNETIC_PERMEABILITY_ExtraLarge", bSTR2585, bSTR2586, boolean1293
'--------------------------------------------------
' Parameter 1 : (String) "MAGNETIC_PERMEABILITY_ExtraLarge"
' Parameter 2 : (String) "Default value"
' Parameter 3 : (String) "Unlocked"
' Parameter 4 : (Boolean) False
'--------------------------------------------------

long1294 = settingRepository1.GetAttr("MAGNETIC_PERMEABILITY_Small")
'--------------------------------------------------
' Parameter 1 : (String) "MAGNETIC_PERMEABILITY_Small"
' Returned value : (Variant) (Long) 1
'--------------------------------------------------

Dim bSTR2587
bSTR2587 = ""
Dim bSTR2588
bSTR2588 = ""
Dim boolean1294
settingRepository1.GetAttrInfo "MAGNETIC_PERMEABILITY_Small", bSTR2587, bSTR2588, boolean1294
'--------------------------------------------------
' Parameter 1 : (String) "MAGNETIC_PERMEABILITY_Small"
' Parameter 2 : (String) "Default value"
' Parameter 3 : (String) "Unlocked"
' Parameter 4 : (Boolean) False
'--------------------------------------------------

long1295 = settingRepository1.GetAttr("MAGNETIC_PERMEABILITY_ExtraSmall")
'--------------------------------------------------
' Parameter 1 : (String) "MAGNETIC_PERMEABILITY_ExtraSmall"
' Returned value : (Variant) (Long) 1
'--------------------------------------------------

Dim bSTR2589
bSTR2589 = ""
Dim bSTR2590
bSTR2590 = ""
Dim boolean1295
settingRepository1.GetAttrInfo "MAGNETIC_PERMEABILITY_ExtraSmall", bSTR2589, bSTR2590, boolean1295
'--------------------------------------------------
' Parameter 1 : (String) "MAGNETIC_PERMEABILITY_ExtraSmall"
' Parameter 2 : (String) "Default value"
' Parameter 3 : (String) "Unlocked"
' Parameter 4 : (Boolean) False
'--------------------------------------------------

long1296 = settingRepository1.GetAttr("MAGNETIC_PERMEABILITY_Nanometric")
'--------------------------------------------------
' Parameter 1 : (String) "MAGNETIC_PERMEABILITY_Nanometric"
' Returned value : (Variant) (Long) 1
'--------------------------------------------------

Dim bSTR2591
bSTR2591 = ""
Dim bSTR2592
bSTR2592 = ""
Dim boolean1296
settingRepository1.GetAttrInfo "MAGNETIC_PERMEABILITY_Nanometric", bSTR2591, bSTR2592, boolean1296
'--------------------------------------------------
' Parameter 1 : (String) "MAGNETIC_PERMEABILITY_Nanometric"
' Parameter 2 : (String) "Default value"
' Parameter 3 : (String) "Unlocked"
' Parameter 4 : (Boolean) False
'--------------------------------------------------

long1297 = settingRepository1.GetAttr("CURRENT_DENSITY")
'--------------------------------------------------
' Parameter 1 : (String) "CURRENT_DENSITY"
' Returned value : (Variant) (Long) 1
'--------------------------------------------------

Dim bSTR2593
bSTR2593 = ""
Dim bSTR2594
bSTR2594 = ""
Dim boolean1297
settingRepository1.GetAttrInfo "CURRENT_DENSITY", bSTR2593, bSTR2594, boolean1297
'--------------------------------------------------
' Parameter 1 : (String) "CURRENT_DENSITY"
' Parameter 2 : (String) "Default value"
' Parameter 3 : (String) "Unlocked"
' Parameter 4 : (Boolean) False
'--------------------------------------------------

long1298 = settingRepository1.GetAttr("CURRENT_DENSITY_Large")
'--------------------------------------------------
' Parameter 1 : (String) "CURRENT_DENSITY_Large"
' Returned value : (Variant) (Long) 1
'--------------------------------------------------

Dim bSTR2595
bSTR2595 = ""
Dim bSTR2596
bSTR2596 = ""
Dim boolean1298
settingRepository1.GetAttrInfo "CURRENT_DENSITY_Large", bSTR2595, bSTR2596, boolean1298
'--------------------------------------------------
' Parameter 1 : (String) "CURRENT_DENSITY_Large"
' Parameter 2 : (String) "Default value"
' Parameter 3 : (String) "Unlocked"
' Parameter 4 : (Boolean) False
'--------------------------------------------------

long1299 = settingRepository1.GetAttr("CURRENT_DENSITY_ExtraLarge")
'--------------------------------------------------
' Parameter 1 : (String) "CURRENT_DENSITY_ExtraLarge"
' Returned value : (Variant) (Long) 1
'--------------------------------------------------

Dim bSTR2597
bSTR2597 = ""
Dim bSTR2598
bSTR2598 = ""
Dim boolean1299
settingRepository1.GetAttrInfo "CURRENT_DENSITY_ExtraLarge", bSTR2597, bSTR2598, boolean1299
'--------------------------------------------------
' Parameter 1 : (String) "CURRENT_DENSITY_ExtraLarge"
' Parameter 2 : (String) "Default value"
' Parameter 3 : (String) "Unlocked"
' Parameter 4 : (Boolean) False
'--------------------------------------------------

long1300 = settingRepository1.GetAttr("CURRENT_DENSITY_Small")
'--------------------------------------------------
' Parameter 1 : (String) "CURRENT_DENSITY_Small"
' Returned value : (Variant) (Long) 1
'--------------------------------------------------

Dim bSTR2599
bSTR2599 = ""
Dim bSTR2600
bSTR2600 = ""
Dim boolean1300
settingRepository1.GetAttrInfo "CURRENT_DENSITY_Small", bSTR2599, bSTR2600, boolean1300
'--------------------------------------------------
' Parameter 1 : (String) "CURRENT_DENSITY_Small"
' Parameter 2 : (String) "Default value"
' Parameter 3 : (String) "Unlocked"
' Parameter 4 : (Boolean) False
'--------------------------------------------------

long1301 = settingRepository1.GetAttr("CURRENT_DENSITY_ExtraSmall")
'--------------------------------------------------
' Parameter 1 : (String) "CURRENT_DENSITY_ExtraSmall"
' Returned value : (Variant) (Long) 1
'--------------------------------------------------

Dim bSTR2601
bSTR2601 = ""
Dim bSTR2602
bSTR2602 = ""
Dim boolean1301
settingRepository1.GetAttrInfo "CURRENT_DENSITY_ExtraSmall", bSTR2601, bSTR2602, boolean1301
'--------------------------------------------------
' Parameter 1 : (String) "CURRENT_DENSITY_ExtraSmall"
' Parameter 2 : (String) "Default value"
' Parameter 3 : (String) "Unlocked"
' Parameter 4 : (Boolean) False
'--------------------------------------------------

long1302 = settingRepository1.GetAttr("CURRENT_DENSITY_Nanometric")
'--------------------------------------------------
' Parameter 1 : (String) "CURRENT_DENSITY_Nanometric"
' Returned value : (Variant) (Long) 1
'--------------------------------------------------

Dim bSTR2603
bSTR2603 = ""
Dim bSTR2604
bSTR2604 = ""
Dim boolean1302
settingRepository1.GetAttrInfo "CURRENT_DENSITY_Nanometric", bSTR2603, bSTR2604, boolean1302
'--------------------------------------------------
' Parameter 1 : (String) "CURRENT_DENSITY_Nanometric"
' Parameter 2 : (String) "Default value"
' Parameter 3 : (String) "Unlocked"
' Parameter 4 : (Boolean) False
'--------------------------------------------------

long1303 = settingRepository1.GetAttr("JOULE_HEATING")
'--------------------------------------------------
' Parameter 1 : (String) "JOULE_HEATING"
' Returned value : (Variant) (Long) 1
'--------------------------------------------------

Dim bSTR2605
bSTR2605 = ""
Dim bSTR2606
bSTR2606 = ""
Dim boolean1303
settingRepository1.GetAttrInfo "JOULE_HEATING", bSTR2605, bSTR2606, boolean1303
'--------------------------------------------------
' Parameter 1 : (String) "JOULE_HEATING"
' Parameter 2 : (String) "Default value"
' Parameter 3 : (String) "Unlocked"
' Parameter 4 : (Boolean) False
'--------------------------------------------------

long1304 = settingRepository1.GetAttr("JOULE_HEATING_Large")
'--------------------------------------------------
' Parameter 1 : (String) "JOULE_HEATING_Large"
' Returned value : (Variant) (Long) 1
'--------------------------------------------------

Dim bSTR2607
bSTR2607 = ""
Dim bSTR2608
bSTR2608 = ""
Dim boolean1304
settingRepository1.GetAttrInfo "JOULE_HEATING_Large", bSTR2607, bSTR2608, boolean1304
'--------------------------------------------------
' Parameter 1 : (String) "JOULE_HEATING_Large"
' Parameter 2 : (String) "Default value"
' Parameter 3 : (String) "Unlocked"
' Parameter 4 : (Boolean) False
'--------------------------------------------------

long1305 = settingRepository1.GetAttr("JOULE_HEATING_ExtraLarge")
'--------------------------------------------------
' Parameter 1 : (String) "JOULE_HEATING_ExtraLarge"
' Returned value : (Variant) (Long) 1
'--------------------------------------------------

Dim bSTR2609
bSTR2609 = ""
Dim bSTR2610
bSTR2610 = ""
Dim boolean1305
settingRepository1.GetAttrInfo "JOULE_HEATING_ExtraLarge", bSTR2609, bSTR2610, boolean1305
'--------------------------------------------------
' Parameter 1 : (String) "JOULE_HEATING_ExtraLarge"
' Parameter 2 : (String) "Default value"
' Parameter 3 : (String) "Unlocked"
' Parameter 4 : (Boolean) False
'--------------------------------------------------

long1306 = settingRepository1.GetAttr("JOULE_HEATING_Small")
'--------------------------------------------------
' Parameter 1 : (String) "JOULE_HEATING_Small"
' Returned value : (Variant) (Long) 1
'--------------------------------------------------

Dim bSTR2611
bSTR2611 = ""
Dim bSTR2612
bSTR2612 = ""
Dim boolean1306
settingRepository1.GetAttrInfo "JOULE_HEATING_Small", bSTR2611, bSTR2612, boolean1306
'--------------------------------------------------
' Parameter 1 : (String) "JOULE_HEATING_Small"
' Parameter 2 : (String) "Default value"
' Parameter 3 : (String) "Unlocked"
' Parameter 4 : (Boolean) False
'--------------------------------------------------

long1307 = settingRepository1.GetAttr("JOULE_HEATING_ExtraSmall")
'--------------------------------------------------
' Parameter 1 : (String) "JOULE_HEATING_ExtraSmall"
' Returned value : (Variant) (Long) 1
'--------------------------------------------------

Dim bSTR2613
bSTR2613 = ""
Dim bSTR2614
bSTR2614 = ""
Dim boolean1307
settingRepository1.GetAttrInfo "JOULE_HEATING_ExtraSmall", bSTR2613, bSTR2614, boolean1307
'--------------------------------------------------
' Parameter 1 : (String) "JOULE_HEATING_ExtraSmall"
' Parameter 2 : (String) "Default value"
' Parameter 3 : (String) "Unlocked"
' Parameter 4 : (Boolean) False
'--------------------------------------------------

long1308 = settingRepository1.GetAttr("JOULE_HEATING_Nanometric")
'--------------------------------------------------
' Parameter 1 : (String) "JOULE_HEATING_Nanometric"
' Returned value : (Variant) (Long) 1
'--------------------------------------------------

Dim bSTR2615
bSTR2615 = ""
Dim bSTR2616
bSTR2616 = ""
Dim boolean1308
settingRepository1.GetAttrInfo "JOULE_HEATING_Nanometric", bSTR2615, bSTR2616, boolean1308
'--------------------------------------------------
' Parameter 1 : (String) "JOULE_HEATING_Nanometric"
' Parameter 2 : (String) "Default value"
' Parameter 3 : (String) "Unlocked"
' Parameter 4 : (Boolean) False
'--------------------------------------------------

long1309 = settingRepository1.GetAttr("WAVENUMBER")
'--------------------------------------------------
' Parameter 1 : (String) "WAVENUMBER"
' Returned value : (Variant) (Long) 1
'--------------------------------------------------

Dim bSTR2617
bSTR2617 = ""
Dim bSTR2618
bSTR2618 = ""
Dim boolean1309
settingRepository1.GetAttrInfo "WAVENUMBER", bSTR2617, bSTR2618, boolean1309
'--------------------------------------------------
' Parameter 1 : (String) "WAVENUMBER"
' Parameter 2 : (String) "Default value"
' Parameter 3 : (String) "Unlocked"
' Parameter 4 : (Boolean) False
'--------------------------------------------------

long1310 = settingRepository1.GetAttr("WAVENUMBER_Large")
'--------------------------------------------------
' Parameter 1 : (String) "WAVENUMBER_Large"
' Returned value : (Variant) (Long) 1
'--------------------------------------------------

Dim bSTR2619
bSTR2619 = ""
Dim bSTR2620
bSTR2620 = ""
Dim boolean1310
settingRepository1.GetAttrInfo "WAVENUMBER_Large", bSTR2619, bSTR2620, boolean1310
'--------------------------------------------------
' Parameter 1 : (String) "WAVENUMBER_Large"
' Parameter 2 : (String) "Default value"
' Parameter 3 : (String) "Unlocked"
' Parameter 4 : (Boolean) False
'--------------------------------------------------

long1311 = settingRepository1.GetAttr("WAVENUMBER_ExtraLarge")
'--------------------------------------------------
' Parameter 1 : (String) "WAVENUMBER_ExtraLarge"
' Returned value : (Variant) (Long) 1
'--------------------------------------------------

Dim bSTR2621
bSTR2621 = ""
Dim bSTR2622
bSTR2622 = ""
Dim boolean1311
settingRepository1.GetAttrInfo "WAVENUMBER_ExtraLarge", bSTR2621, bSTR2622, boolean1311
'--------------------------------------------------
' Parameter 1 : (String) "WAVENUMBER_ExtraLarge"
' Parameter 2 : (String) "Default value"
' Parameter 3 : (String) "Unlocked"
' Parameter 4 : (Boolean) False
'--------------------------------------------------

long1312 = settingRepository1.GetAttr("WAVENUMBER_Small")
'--------------------------------------------------
' Parameter 1 : (String) "WAVENUMBER_Small"
' Returned value : (Variant) (Long) 1
'--------------------------------------------------

Dim bSTR2623
bSTR2623 = ""
Dim bSTR2624
bSTR2624 = ""
Dim boolean1312
settingRepository1.GetAttrInfo "WAVENUMBER_Small", bSTR2623, bSTR2624, boolean1312
'--------------------------------------------------
' Parameter 1 : (String) "WAVENUMBER_Small"
' Parameter 2 : (String) "Default value"
' Parameter 3 : (String) "Unlocked"
' Parameter 4 : (Boolean) False
'--------------------------------------------------

long1313 = settingRepository1.GetAttr("WAVENUMBER_ExtraSmall")
'--------------------------------------------------
' Parameter 1 : (String) "WAVENUMBER_ExtraSmall"
' Returned value : (Variant) (Long) 1
'--------------------------------------------------

Dim bSTR2625
bSTR2625 = ""
Dim bSTR2626
bSTR2626 = ""
Dim boolean1313
settingRepository1.GetAttrInfo "WAVENUMBER_ExtraSmall", bSTR2625, bSTR2626, boolean1313
'--------------------------------------------------
' Parameter 1 : (String) "WAVENUMBER_ExtraSmall"
' Parameter 2 : (String) "Default value"
' Parameter 3 : (String) "Unlocked"
' Parameter 4 : (Boolean) False
'--------------------------------------------------

long1314 = settingRepository1.GetAttr("WAVENUMBER_Nanometric")
'--------------------------------------------------
' Parameter 1 : (String) "WAVENUMBER_Nanometric"
' Returned value : (Variant) (Long) 1
'--------------------------------------------------

Dim bSTR2627
bSTR2627 = ""
Dim bSTR2628
bSTR2628 = ""
Dim boolean1314
settingRepository1.GetAttrInfo "WAVENUMBER_Nanometric", bSTR2627, bSTR2628, boolean1314
'--------------------------------------------------
' Parameter 1 : (String) "WAVENUMBER_Nanometric"
' Parameter 2 : (String) "Default value"
' Parameter 3 : (String) "Unlocked"
' Parameter 4 : (Boolean) False
'--------------------------------------------------

long1315 = settingRepository1.GetAttr("CIRCULARWAVENUMBER")
'--------------------------------------------------
' Parameter 1 : (String) "CIRCULARWAVENUMBER"
' Returned value : (Variant) (Long) 1
'--------------------------------------------------

Dim bSTR2629
bSTR2629 = ""
Dim bSTR2630
bSTR2630 = ""
Dim boolean1315
settingRepository1.GetAttrInfo "CIRCULARWAVENUMBER", bSTR2629, bSTR2630, boolean1315
'--------------------------------------------------
' Parameter 1 : (String) "CIRCULARWAVENUMBER"
' Parameter 2 : (String) "Default value"
' Parameter 3 : (String) "Unlocked"
' Parameter 4 : (Boolean) False
'--------------------------------------------------

long1316 = settingRepository1.GetAttr("CIRCULARWAVENUMBER_Large")
'--------------------------------------------------
' Parameter 1 : (String) "CIRCULARWAVENUMBER_Large"
' Returned value : (Variant) (Long) 1
'--------------------------------------------------

Dim bSTR2631
bSTR2631 = ""
Dim bSTR2632
bSTR2632 = ""
Dim boolean1316
settingRepository1.GetAttrInfo "CIRCULARWAVENUMBER_Large", bSTR2631, bSTR2632, boolean1316
'--------------------------------------------------
' Parameter 1 : (String) "CIRCULARWAVENUMBER_Large"
' Parameter 2 : (String) "Default value"
' Parameter 3 : (String) "Unlocked"
' Parameter 4 : (Boolean) False
'--------------------------------------------------

long1317 = settingRepository1.GetAttr("CIRCULARWAVENUMBER_ExtraLarge")
'--------------------------------------------------
' Parameter 1 : (String) "CIRCULARWAVENUMBER_ExtraLarge"
' Returned value : (Variant) (Long) 1
'--------------------------------------------------

Dim bSTR2633
bSTR2633 = ""
Dim bSTR2634
bSTR2634 = ""
Dim boolean1317
settingRepository1.GetAttrInfo "CIRCULARWAVENUMBER_ExtraLarge", bSTR2633, bSTR2634, boolean1317
'--------------------------------------------------
' Parameter 1 : (String) "CIRCULARWAVENUMBER_ExtraLarge"
' Parameter 2 : (String) "Default value"
' Parameter 3 : (String) "Unlocked"
' Parameter 4 : (Boolean) False
'--------------------------------------------------

long1318 = settingRepository1.GetAttr("CIRCULARWAVENUMBER_Small")
'--------------------------------------------------
' Parameter 1 : (String) "CIRCULARWAVENUMBER_Small"
' Returned value : (Variant) (Long) 1
'--------------------------------------------------

Dim bSTR2635
bSTR2635 = ""
Dim bSTR2636
bSTR2636 = ""
Dim boolean1318
settingRepository1.GetAttrInfo "CIRCULARWAVENUMBER_Small", bSTR2635, bSTR2636, boolean1318
'--------------------------------------------------
' Parameter 1 : (String) "CIRCULARWAVENUMBER_Small"
' Parameter 2 : (String) "Default value"
' Parameter 3 : (String) "Unlocked"
' Parameter 4 : (Boolean) False
'--------------------------------------------------

long1319 = settingRepository1.GetAttr("CIRCULARWAVENUMBER_ExtraSmall")
'--------------------------------------------------
' Parameter 1 : (String) "CIRCULARWAVENUMBER_ExtraSmall"
' Returned value : (Variant) (Long) 1
'--------------------------------------------------

Dim bSTR2637
bSTR2637 = ""
Dim bSTR2638
bSTR2638 = ""
Dim boolean1319
settingRepository1.GetAttrInfo "CIRCULARWAVENUMBER_ExtraSmall", bSTR2637, bSTR2638, boolean1319
'--------------------------------------------------
' Parameter 1 : (String) "CIRCULARWAVENUMBER_ExtraSmall"
' Parameter 2 : (String) "Default value"
' Parameter 3 : (String) "Unlocked"
' Parameter 4 : (Boolean) False
'--------------------------------------------------

long1320 = settingRepository1.GetAttr("CIRCULARWAVENUMBER_Nanometric")
'--------------------------------------------------
' Parameter 1 : (String) "CIRCULARWAVENUMBER_Nanometric"
' Returned value : (Variant) (Long) 1
'--------------------------------------------------

Dim bSTR2639
bSTR2639 = ""
Dim bSTR2640
bSTR2640 = ""
Dim boolean1320
settingRepository1.GetAttrInfo "CIRCULARWAVENUMBER_Nanometric", bSTR2639, bSTR2640, boolean1320
'--------------------------------------------------
' Parameter 1 : (String) "CIRCULARWAVENUMBER_Nanometric"
' Parameter 2 : (String) "Default value"
' Parameter 3 : (String) "Unlocked"
' Parameter 4 : (Boolean) False
'--------------------------------------------------

long1321 = settingRepository1.GetAttr("DAMPINGCOEFFICIENT")
'--------------------------------------------------
' Parameter 1 : (String) "DAMPINGCOEFFICIENT"
' Returned value : (Variant) (Long) 1
'--------------------------------------------------

Dim bSTR2641
bSTR2641 = ""
Dim bSTR2642
bSTR2642 = ""
Dim boolean1321
settingRepository1.GetAttrInfo "DAMPINGCOEFFICIENT", bSTR2641, bSTR2642, boolean1321
'--------------------------------------------------
' Parameter 1 : (String) "DAMPINGCOEFFICIENT"
' Parameter 2 : (String) "Default value"
' Parameter 3 : (String) "Unlocked"
' Parameter 4 : (Boolean) False
'--------------------------------------------------

long1322 = settingRepository1.GetAttr("DAMPINGCOEFFICIENT_Large")
'--------------------------------------------------
' Parameter 1 : (String) "DAMPINGCOEFFICIENT_Large"
' Returned value : (Variant) (Long) 1
'--------------------------------------------------

Dim bSTR2643
bSTR2643 = ""
Dim bSTR2644
bSTR2644 = ""
Dim boolean1322
settingRepository1.GetAttrInfo "DAMPINGCOEFFICIENT_Large", bSTR2643, bSTR2644, boolean1322
'--------------------------------------------------
' Parameter 1 : (String) "DAMPINGCOEFFICIENT_Large"
' Parameter 2 : (String) "Default value"
' Parameter 3 : (String) "Unlocked"
' Parameter 4 : (Boolean) False
'--------------------------------------------------

long1323 = settingRepository1.GetAttr("DAMPINGCOEFFICIENT_ExtraLarge")
'--------------------------------------------------
' Parameter 1 : (String) "DAMPINGCOEFFICIENT_ExtraLarge"
' Returned value : (Variant) (Long) 1
'--------------------------------------------------

Dim bSTR2645
bSTR2645 = ""
Dim bSTR2646
bSTR2646 = ""
Dim boolean1323
settingRepository1.GetAttrInfo "DAMPINGCOEFFICIENT_ExtraLarge", bSTR2645, bSTR2646, boolean1323
'--------------------------------------------------
' Parameter 1 : (String) "DAMPINGCOEFFICIENT_ExtraLarge"
' Parameter 2 : (String) "Default value"
' Parameter 3 : (String) "Unlocked"
' Parameter 4 : (Boolean) False
'--------------------------------------------------

long1324 = settingRepository1.GetAttr("DAMPINGCOEFFICIENT_Small")
'--------------------------------------------------
' Parameter 1 : (String) "DAMPINGCOEFFICIENT_Small"
' Returned value : (Variant) (Long) 1
'--------------------------------------------------

Dim bSTR2647
bSTR2647 = ""
Dim bSTR2648
bSTR2648 = ""
Dim boolean1324
settingRepository1.GetAttrInfo "DAMPINGCOEFFICIENT_Small", bSTR2647, bSTR2648, boolean1324
'--------------------------------------------------
' Parameter 1 : (String) "DAMPINGCOEFFICIENT_Small"
' Parameter 2 : (String) "Default value"
' Parameter 3 : (String) "Unlocked"
' Parameter 4 : (Boolean) False
'--------------------------------------------------

long1325 = settingRepository1.GetAttr("DAMPINGCOEFFICIENT_ExtraSmall")
'--------------------------------------------------
' Parameter 1 : (String) "DAMPINGCOEFFICIENT_ExtraSmall"
' Returned value : (Variant) (Long) 1
'--------------------------------------------------

Dim bSTR2649
bSTR2649 = ""
Dim bSTR2650
bSTR2650 = ""
Dim boolean1325
settingRepository1.GetAttrInfo "DAMPINGCOEFFICIENT_ExtraSmall", bSTR2649, bSTR2650, boolean1325
'--------------------------------------------------
' Parameter 1 : (String) "DAMPINGCOEFFICIENT_ExtraSmall"
' Parameter 2 : (String) "Default value"
' Parameter 3 : (String) "Unlocked"
' Parameter 4 : (Boolean) False
'--------------------------------------------------

long1326 = settingRepository1.GetAttr("DAMPINGCOEFFICIENT_Nanometric")
'--------------------------------------------------
' Parameter 1 : (String) "DAMPINGCOEFFICIENT_Nanometric"
' Returned value : (Variant) (Long) 1
'--------------------------------------------------

Dim bSTR2651
bSTR2651 = ""
Dim bSTR2652
bSTR2652 = ""
Dim boolean1326
settingRepository1.GetAttrInfo "DAMPINGCOEFFICIENT_Nanometric", bSTR2651, bSTR2652, boolean1326
'--------------------------------------------------
' Parameter 1 : (String) "DAMPINGCOEFFICIENT_Nanometric"
' Parameter 2 : (String) "Default value"
' Parameter 3 : (String) "Unlocked"
' Parameter 4 : (Boolean) False
'--------------------------------------------------

long1327 = settingRepository1.GetAttr("LOGARITHMICDECREMENT")
'--------------------------------------------------
' Parameter 1 : (String) "LOGARITHMICDECREMENT"
' Returned value : (Variant) (Long) 1
'--------------------------------------------------

Dim bSTR2653
bSTR2653 = ""
Dim bSTR2654
bSTR2654 = ""
Dim boolean1327
settingRepository1.GetAttrInfo "LOGARITHMICDECREMENT", bSTR2653, bSTR2654, boolean1327
'--------------------------------------------------
' Parameter 1 : (String) "LOGARITHMICDECREMENT"
' Parameter 2 : (String) "Default value"
' Parameter 3 : (String) "Unlocked"
' Parameter 4 : (Boolean) False
'--------------------------------------------------

long1328 = settingRepository1.GetAttr("LOGARITHMICDECREMENT_Large")
'--------------------------------------------------
' Parameter 1 : (String) "LOGARITHMICDECREMENT_Large"
' Returned value : (Variant) (Long) 1
'--------------------------------------------------

Dim bSTR2655
bSTR2655 = ""
Dim bSTR2656
bSTR2656 = ""
Dim boolean1328
settingRepository1.GetAttrInfo "LOGARITHMICDECREMENT_Large", bSTR2655, bSTR2656, boolean1328
'--------------------------------------------------
' Parameter 1 : (String) "LOGARITHMICDECREMENT_Large"
' Parameter 2 : (String) "Default value"
' Parameter 3 : (String) "Unlocked"
' Parameter 4 : (Boolean) False
'--------------------------------------------------

long1329 = settingRepository1.GetAttr("LOGARITHMICDECREMENT_ExtraLarge")
'--------------------------------------------------
' Parameter 1 : (String) "LOGARITHMICDECREMENT_ExtraLarge"
' Returned value : (Variant) (Long) 1
'--------------------------------------------------

Dim bSTR2657
bSTR2657 = ""
Dim bSTR2658
bSTR2658 = ""
Dim boolean1329
settingRepository1.GetAttrInfo "LOGARITHMICDECREMENT_ExtraLarge", bSTR2657, bSTR2658, boolean1329
'--------------------------------------------------
' Parameter 1 : (String) "LOGARITHMICDECREMENT_ExtraLarge"
' Parameter 2 : (String) "Default value"
' Parameter 3 : (String) "Unlocked"
' Parameter 4 : (Boolean) False
'--------------------------------------------------

long1330 = settingRepository1.GetAttr("LOGARITHMICDECREMENT_Small")
'--------------------------------------------------
' Parameter 1 : (String) "LOGARITHMICDECREMENT_Small"
' Returned value : (Variant) (Long) 1
'--------------------------------------------------

Dim bSTR2659
bSTR2659 = ""
Dim bSTR2660
bSTR2660 = ""
Dim boolean1330
settingRepository1.GetAttrInfo "LOGARITHMICDECREMENT_Small", bSTR2659, bSTR2660, boolean1330
'--------------------------------------------------
' Parameter 1 : (String) "LOGARITHMICDECREMENT_Small"
' Parameter 2 : (String) "Default value"
' Parameter 3 : (String) "Unlocked"
' Parameter 4 : (Boolean) False
'--------------------------------------------------

long1331 = settingRepository1.GetAttr("LOGARITHMICDECREMENT_ExtraSmall")
'--------------------------------------------------
' Parameter 1 : (String) "LOGARITHMICDECREMENT_ExtraSmall"
' Returned value : (Variant) (Long) 1
'--------------------------------------------------

Dim bSTR2661
bSTR2661 = ""
Dim bSTR2662
bSTR2662 = ""
Dim boolean1331
settingRepository1.GetAttrInfo "LOGARITHMICDECREMENT_ExtraSmall", bSTR2661, bSTR2662, boolean1331
'--------------------------------------------------
' Parameter 1 : (String) "LOGARITHMICDECREMENT_ExtraSmall"
' Parameter 2 : (String) "Default value"
' Parameter 3 : (String) "Unlocked"
' Parameter 4 : (Boolean) False
'--------------------------------------------------

long1332 = settingRepository1.GetAttr("LOGARITHMICDECREMENT_Nanometric")
'--------------------------------------------------
' Parameter 1 : (String) "LOGARITHMICDECREMENT_Nanometric"
' Returned value : (Variant) (Long) 1
'--------------------------------------------------

Dim bSTR2663
bSTR2663 = ""
Dim bSTR2664
bSTR2664 = ""
Dim boolean1332
settingRepository1.GetAttrInfo "LOGARITHMICDECREMENT_Nanometric", bSTR2663, bSTR2664, boolean1332
'--------------------------------------------------
' Parameter 1 : (String) "LOGARITHMICDECREMENT_Nanometric"
' Parameter 2 : (String) "Default value"
' Parameter 3 : (String) "Unlocked"
' Parameter 4 : (Boolean) False
'--------------------------------------------------

long1333 = settingRepository1.GetAttr("ATTENUATIONCOEFFICIENT")
'--------------------------------------------------
' Parameter 1 : (String) "ATTENUATIONCOEFFICIENT"
' Returned value : (Variant) (Long) 1
'--------------------------------------------------

Dim bSTR2665
bSTR2665 = ""
Dim bSTR2666
bSTR2666 = ""
Dim boolean1333
settingRepository1.GetAttrInfo "ATTENUATIONCOEFFICIENT", bSTR2665, bSTR2666, boolean1333
'--------------------------------------------------
' Parameter 1 : (String) "ATTENUATIONCOEFFICIENT"
' Parameter 2 : (String) "Default value"
' Parameter 3 : (String) "Unlocked"
' Parameter 4 : (Boolean) False
'--------------------------------------------------

long1334 = settingRepository1.GetAttr("ATTENUATIONCOEFFICIENT_Large")
'--------------------------------------------------
' Parameter 1 : (String) "ATTENUATIONCOEFFICIENT_Large"
' Returned value : (Variant) (Long) 1
'--------------------------------------------------

Dim bSTR2667
bSTR2667 = ""
Dim bSTR2668
bSTR2668 = ""
Dim boolean1334
settingRepository1.GetAttrInfo "ATTENUATIONCOEFFICIENT_Large", bSTR2667, bSTR2668, boolean1334
'--------------------------------------------------
' Parameter 1 : (String) "ATTENUATIONCOEFFICIENT_Large"
' Parameter 2 : (String) "Default value"
' Parameter 3 : (String) "Unlocked"
' Parameter 4 : (Boolean) False
'--------------------------------------------------

long1335 = settingRepository1.GetAttr("ATTENUATIONCOEFFICIENT_ExtraLarge")
'--------------------------------------------------
' Parameter 1 : (String) "ATTENUATIONCOEFFICIENT_ExtraLarge"
' Returned value : (Variant) (Long) 1
'--------------------------------------------------

Dim bSTR2669
bSTR2669 = ""
Dim bSTR2670
bSTR2670 = ""
Dim boolean1335
settingRepository1.GetAttrInfo "ATTENUATIONCOEFFICIENT_ExtraLarge", bSTR2669, bSTR2670, boolean1335
'--------------------------------------------------
' Parameter 1 : (String) "ATTENUATIONCOEFFICIENT_ExtraLarge"
' Parameter 2 : (String) "Default value"
' Parameter 3 : (String) "Unlocked"
' Parameter 4 : (Boolean) False
'--------------------------------------------------

long1336 = settingRepository1.GetAttr("ATTENUATIONCOEFFICIENT_Small")
'--------------------------------------------------
' Parameter 1 : (String) "ATTENUATIONCOEFFICIENT_Small"
' Returned value : (Variant) (Long) 1
'--------------------------------------------------

Dim bSTR2671
bSTR2671 = ""
Dim bSTR2672
bSTR2672 = ""
Dim boolean1336
settingRepository1.GetAttrInfo "ATTENUATIONCOEFFICIENT_Small", bSTR2671, bSTR2672, boolean1336
'--------------------------------------------------
' Parameter 1 : (String) "ATTENUATIONCOEFFICIENT_Small"
' Parameter 2 : (String) "Default value"
' Parameter 3 : (String) "Unlocked"
' Parameter 4 : (Boolean) False
'--------------------------------------------------

long1337 = settingRepository1.GetAttr("ATTENUATIONCOEFFICIENT_ExtraSmall")
'--------------------------------------------------
' Parameter 1 : (String) "ATTENUATIONCOEFFICIENT_ExtraSmall"
' Returned value : (Variant) (Long) 1
'--------------------------------------------------

Dim bSTR2673
bSTR2673 = ""
Dim bSTR2674
bSTR2674 = ""
Dim boolean1337
settingRepository1.GetAttrInfo "ATTENUATIONCOEFFICIENT_ExtraSmall", bSTR2673, bSTR2674, boolean1337
'--------------------------------------------------
' Parameter 1 : (String) "ATTENUATIONCOEFFICIENT_ExtraSmall"
' Parameter 2 : (String) "Default value"
' Parameter 3 : (String) "Unlocked"
' Parameter 4 : (Boolean) False
'--------------------------------------------------

long1338 = settingRepository1.GetAttr("ATTENUATIONCOEFFICIENT_Nanometric")
'--------------------------------------------------
' Parameter 1 : (String) "ATTENUATIONCOEFFICIENT_Nanometric"
' Returned value : (Variant) (Long) 1
'--------------------------------------------------

Dim bSTR2675
bSTR2675 = ""
Dim bSTR2676
bSTR2676 = ""
Dim boolean1338
settingRepository1.GetAttrInfo "ATTENUATIONCOEFFICIENT_Nanometric", bSTR2675, bSTR2676, boolean1338
'--------------------------------------------------
' Parameter 1 : (String) "ATTENUATIONCOEFFICIENT_Nanometric"
' Parameter 2 : (String) "Default value"
' Parameter 3 : (String) "Unlocked"
' Parameter 4 : (Boolean) False
'--------------------------------------------------

long1339 = settingRepository1.GetAttr("PHASECOEFFICIENT")
'--------------------------------------------------
' Parameter 1 : (String) "PHASECOEFFICIENT"
' Returned value : (Variant) (Long) 1
'--------------------------------------------------

Dim bSTR2677
bSTR2677 = ""
Dim bSTR2678
bSTR2678 = ""
Dim boolean1339
settingRepository1.GetAttrInfo "PHASECOEFFICIENT", bSTR2677, bSTR2678, boolean1339
'--------------------------------------------------
' Parameter 1 : (String) "PHASECOEFFICIENT"
' Parameter 2 : (String) "Default value"
' Parameter 3 : (String) "Unlocked"
' Parameter 4 : (Boolean) False
'--------------------------------------------------

long1340 = settingRepository1.GetAttr("PHASECOEFFICIENT_Large")
'--------------------------------------------------
' Parameter 1 : (String) "PHASECOEFFICIENT_Large"
' Returned value : (Variant) (Long) 1
'--------------------------------------------------

Dim bSTR2679
bSTR2679 = ""
Dim bSTR2680
bSTR2680 = ""
Dim boolean1340
settingRepository1.GetAttrInfo "PHASECOEFFICIENT_Large", bSTR2679, bSTR2680, boolean1340
'--------------------------------------------------
' Parameter 1 : (String) "PHASECOEFFICIENT_Large"
' Parameter 2 : (String) "Default value"
' Parameter 3 : (String) "Unlocked"
' Parameter 4 : (Boolean) False
'--------------------------------------------------

long1341 = settingRepository1.GetAttr("PHASECOEFFICIENT_ExtraLarge")
'--------------------------------------------------
' Parameter 1 : (String) "PHASECOEFFICIENT_ExtraLarge"
' Returned value : (Variant) (Long) 1
'--------------------------------------------------

Dim bSTR2681
bSTR2681 = ""
Dim bSTR2682
bSTR2682 = ""
Dim boolean1341
settingRepository1.GetAttrInfo "PHASECOEFFICIENT_ExtraLarge", bSTR2681, bSTR2682, boolean1341
'--------------------------------------------------
' Parameter 1 : (String) "PHASECOEFFICIENT_ExtraLarge"
' Parameter 2 : (String) "Default value"
' Parameter 3 : (String) "Unlocked"
' Parameter 4 : (Boolean) False
'--------------------------------------------------

long1342 = settingRepository1.GetAttr("PHASECOEFFICIENT_Small")
'--------------------------------------------------
' Parameter 1 : (String) "PHASECOEFFICIENT_Small"
' Returned value : (Variant) (Long) 1
'--------------------------------------------------

Dim bSTR2683
bSTR2683 = ""
Dim bSTR2684
bSTR2684 = ""
Dim boolean1342
settingRepository1.GetAttrInfo "PHASECOEFFICIENT_Small", bSTR2683, bSTR2684, boolean1342
'--------------------------------------------------
' Parameter 1 : (String) "PHASECOEFFICIENT_Small"
' Parameter 2 : (String) "Default value"
' Parameter 3 : (String) "Unlocked"
' Parameter 4 : (Boolean) False
'--------------------------------------------------

long1343 = settingRepository1.GetAttr("PHASECOEFFICIENT_ExtraSmall")
'--------------------------------------------------
' Parameter 1 : (String) "PHASECOEFFICIENT_ExtraSmall"
' Returned value : (Variant) (Long) 1
'--------------------------------------------------

Dim bSTR2685
bSTR2685 = ""
Dim bSTR2686
bSTR2686 = ""
Dim boolean1343
settingRepository1.GetAttrInfo "PHASECOEFFICIENT_ExtraSmall", bSTR2685, bSTR2686, boolean1343
'--------------------------------------------------
' Parameter 1 : (String) "PHASECOEFFICIENT_ExtraSmall"
' Parameter 2 : (String) "Default value"
' Parameter 3 : (String) "Unlocked"
' Parameter 4 : (Boolean) False
'--------------------------------------------------

long1344 = settingRepository1.GetAttr("PHASECOEFFICIENT_Nanometric")
'--------------------------------------------------
' Parameter 1 : (String) "PHASECOEFFICIENT_Nanometric"
' Returned value : (Variant) (Long) 1
'--------------------------------------------------

Dim bSTR2687
bSTR2687 = ""
Dim bSTR2688
bSTR2688 = ""
Dim boolean1344
settingRepository1.GetAttrInfo "PHASECOEFFICIENT_Nanometric", bSTR2687, bSTR2688, boolean1344
'--------------------------------------------------
' Parameter 1 : (String) "PHASECOEFFICIENT_Nanometric"
' Parameter 2 : (String) "Default value"
' Parameter 3 : (String) "Unlocked"
' Parameter 4 : (Boolean) False
'--------------------------------------------------

long1345 = settingRepository1.GetAttr("PROPAGATIONCOEFFICIENT")
'--------------------------------------------------
' Parameter 1 : (String) "PROPAGATIONCOEFFICIENT"
' Returned value : (Variant) (Long) 1
'--------------------------------------------------

Dim bSTR2689
bSTR2689 = ""
Dim bSTR2690
bSTR2690 = ""
Dim boolean1345
settingRepository1.GetAttrInfo "PROPAGATIONCOEFFICIENT", bSTR2689, bSTR2690, boolean1345
'--------------------------------------------------
' Parameter 1 : (String) "PROPAGATIONCOEFFICIENT"
' Parameter 2 : (String) "Default value"
' Parameter 3 : (String) "Unlocked"
' Parameter 4 : (Boolean) False
'--------------------------------------------------

long1346 = settingRepository1.GetAttr("PROPAGATIONCOEFFICIENT_Large")
'--------------------------------------------------
' Parameter 1 : (String) "PROPAGATIONCOEFFICIENT_Large"
' Returned value : (Variant) (Long) 1
'--------------------------------------------------

Dim bSTR2691
bSTR2691 = ""
Dim bSTR2692
bSTR2692 = ""
Dim boolean1346
settingRepository1.GetAttrInfo "PROPAGATIONCOEFFICIENT_Large", bSTR2691, bSTR2692, boolean1346
'--------------------------------------------------
' Parameter 1 : (String) "PROPAGATIONCOEFFICIENT_Large"
' Parameter 2 : (String) "Default value"
' Parameter 3 : (String) "Unlocked"
' Parameter 4 : (Boolean) False
'--------------------------------------------------

long1347 = settingRepository1.GetAttr("PROPAGATIONCOEFFICIENT_ExtraLarge")
'--------------------------------------------------
' Parameter 1 : (String) "PROPAGATIONCOEFFICIENT_ExtraLarge"
' Returned value : (Variant) (Long) 1
'--------------------------------------------------

Dim bSTR2693
bSTR2693 = ""
Dim bSTR2694
bSTR2694 = ""
Dim boolean1347
settingRepository1.GetAttrInfo "PROPAGATIONCOEFFICIENT_ExtraLarge", bSTR2693, bSTR2694, boolean1347
'--------------------------------------------------
' Parameter 1 : (String) "PROPAGATIONCOEFFICIENT_ExtraLarge"
' Parameter 2 : (String) "Default value"
' Parameter 3 : (String) "Unlocked"
' Parameter 4 : (Boolean) False
'--------------------------------------------------

long1348 = settingRepository1.GetAttr("PROPAGATIONCOEFFICIENT_Small")
'--------------------------------------------------
' Parameter 1 : (String) "PROPAGATIONCOEFFICIENT_Small"
' Returned value : (Variant) (Long) 1
'--------------------------------------------------

Dim bSTR2695
bSTR2695 = ""
Dim bSTR2696
bSTR2696 = ""
Dim boolean1348
settingRepository1.GetAttrInfo "PROPAGATIONCOEFFICIENT_Small", bSTR2695, bSTR2696, boolean1348
'--------------------------------------------------
' Parameter 1 : (String) "PROPAGATIONCOEFFICIENT_Small"
' Parameter 2 : (String) "Default value"
' Parameter 3 : (String) "Unlocked"
' Parameter 4 : (Boolean) False
'--------------------------------------------------

long1349 = settingRepository1.GetAttr("PROPAGATIONCOEFFICIENT_ExtraSmall")
'--------------------------------------------------
' Parameter 1 : (String) "PROPAGATIONCOEFFICIENT_ExtraSmall"
' Returned value : (Variant) (Long) 1
'--------------------------------------------------

Dim bSTR2697
bSTR2697 = ""
Dim bSTR2698
bSTR2698 = ""
Dim boolean1349
settingRepository1.GetAttrInfo "PROPAGATIONCOEFFICIENT_ExtraSmall", bSTR2697, bSTR2698, boolean1349
'--------------------------------------------------
' Parameter 1 : (String) "PROPAGATIONCOEFFICIENT_ExtraSmall"
' Parameter 2 : (String) "Default value"
' Parameter 3 : (String) "Unlocked"
' Parameter 4 : (Boolean) False
'--------------------------------------------------

long1350 = settingRepository1.GetAttr("PROPAGATIONCOEFFICIENT_Nanometric")
'--------------------------------------------------
' Parameter 1 : (String) "PROPAGATIONCOEFFICIENT_Nanometric"
' Returned value : (Variant) (Long) 1
'--------------------------------------------------

Dim bSTR2699
bSTR2699 = ""
Dim bSTR2700
bSTR2700 = ""
Dim boolean1350
settingRepository1.GetAttrInfo "PROPAGATIONCOEFFICIENT_Nanometric", bSTR2699, bSTR2700, boolean1350
'--------------------------------------------------
' Parameter 1 : (String) "PROPAGATIONCOEFFICIENT_Nanometric"
' Parameter 2 : (String) "Default value"
' Parameter 3 : (String) "Unlocked"
' Parameter 4 : (Boolean) False
'--------------------------------------------------

long1351 = settingRepository1.GetAttr("SPECIFICVOLUME")
'--------------------------------------------------
' Parameter 1 : (String) "SPECIFICVOLUME"
' Returned value : (Variant) (Long) 1
'--------------------------------------------------

Dim bSTR2701
bSTR2701 = ""
Dim bSTR2702
bSTR2702 = ""
Dim boolean1351
settingRepository1.GetAttrInfo "SPECIFICVOLUME", bSTR2701, bSTR2702, boolean1351
'--------------------------------------------------
' Parameter 1 : (String) "SPECIFICVOLUME"
' Parameter 2 : (String) "Default value"
' Parameter 3 : (String) "Unlocked"
' Parameter 4 : (Boolean) False
'--------------------------------------------------

long1352 = settingRepository1.GetAttr("SPECIFICVOLUME_Large")
'--------------------------------------------------
' Parameter 1 : (String) "SPECIFICVOLUME_Large"
' Returned value : (Variant) (Long) 1
'--------------------------------------------------

Dim bSTR2703
bSTR2703 = ""
Dim bSTR2704
bSTR2704 = ""
Dim boolean1352
settingRepository1.GetAttrInfo "SPECIFICVOLUME_Large", bSTR2703, bSTR2704, boolean1352
'--------------------------------------------------
' Parameter 1 : (String) "SPECIFICVOLUME_Large"
' Parameter 2 : (String) "Default value"
' Parameter 3 : (String) "Unlocked"
' Parameter 4 : (Boolean) False
'--------------------------------------------------

long1353 = settingRepository1.GetAttr("SPECIFICVOLUME_ExtraLarge")
'--------------------------------------------------
' Parameter 1 : (String) "SPECIFICVOLUME_ExtraLarge"
' Returned value : (Variant) (Long) 1
'--------------------------------------------------

Dim bSTR2705
bSTR2705 = ""
Dim bSTR2706
bSTR2706 = ""
Dim boolean1353
settingRepository1.GetAttrInfo "SPECIFICVOLUME_ExtraLarge", bSTR2705, bSTR2706, boolean1353
'--------------------------------------------------
' Parameter 1 : (String) "SPECIFICVOLUME_ExtraLarge"
' Parameter 2 : (String) "Default value"
' Parameter 3 : (String) "Unlocked"
' Parameter 4 : (Boolean) False
'--------------------------------------------------

long1354 = settingRepository1.GetAttr("SPECIFICVOLUME_Small")
'--------------------------------------------------
' Parameter 1 : (String) "SPECIFICVOLUME_Small"
' Returned value : (Variant) (Long) 1
'--------------------------------------------------

Dim bSTR2707
bSTR2707 = ""
Dim bSTR2708
bSTR2708 = ""
Dim boolean1354
settingRepository1.GetAttrInfo "SPECIFICVOLUME_Small", bSTR2707, bSTR2708, boolean1354
'--------------------------------------------------
' Parameter 1 : (String) "SPECIFICVOLUME_Small"
' Parameter 2 : (String) "Default value"
' Parameter 3 : (String) "Unlocked"
' Parameter 4 : (Boolean) False
'--------------------------------------------------

long1355 = settingRepository1.GetAttr("SPECIFICVOLUME_ExtraSmall")
'--------------------------------------------------
' Parameter 1 : (String) "SPECIFICVOLUME_ExtraSmall"
' Returned value : (Variant) (Long) 1
'--------------------------------------------------

Dim bSTR2709
bSTR2709 = ""
Dim bSTR2710
bSTR2710 = ""
Dim boolean1355
settingRepository1.GetAttrInfo "SPECIFICVOLUME_ExtraSmall", bSTR2709, bSTR2710, boolean1355
'--------------------------------------------------
' Parameter 1 : (String) "SPECIFICVOLUME_ExtraSmall"
' Parameter 2 : (String) "Default value"
' Parameter 3 : (String) "Unlocked"
' Parameter 4 : (Boolean) False
'--------------------------------------------------

long1356 = settingRepository1.GetAttr("SPECIFICVOLUME_Nanometric")
'--------------------------------------------------
' Parameter 1 : (String) "SPECIFICVOLUME_Nanometric"
' Returned value : (Variant) (Long) 1
'--------------------------------------------------

Dim bSTR2711
bSTR2711 = ""
Dim bSTR2712
bSTR2712 = ""
Dim boolean1356
settingRepository1.GetAttrInfo "SPECIFICVOLUME_Nanometric", bSTR2711, bSTR2712, boolean1356
'--------------------------------------------------
' Parameter 1 : (String) "SPECIFICVOLUME_Nanometric"
' Parameter 2 : (String) "Default value"
' Parameter 3 : (String) "Unlocked"
' Parameter 4 : (Boolean) False
'--------------------------------------------------

long1357 = settingRepository1.GetAttr("ANGULARMOMENTUM")
'--------------------------------------------------
' Parameter 1 : (String) "ANGULARMOMENTUM"
' Returned value : (Variant) (Long) 1
'--------------------------------------------------

Dim bSTR2713
bSTR2713 = ""
Dim bSTR2714
bSTR2714 = ""
Dim boolean1357
settingRepository1.GetAttrInfo "ANGULARMOMENTUM", bSTR2713, bSTR2714, boolean1357
'--------------------------------------------------
' Parameter 1 : (String) "ANGULARMOMENTUM"
' Parameter 2 : (String) "Default value"
' Parameter 3 : (String) "Unlocked"
' Parameter 4 : (Boolean) False
'--------------------------------------------------

long1358 = settingRepository1.GetAttr("ANGULARMOMENTUM_Large")
'--------------------------------------------------
' Parameter 1 : (String) "ANGULARMOMENTUM_Large"
' Returned value : (Variant) (Long) 1
'--------------------------------------------------

Dim bSTR2715
bSTR2715 = ""
Dim bSTR2716
bSTR2716 = ""
Dim boolean1358
settingRepository1.GetAttrInfo "ANGULARMOMENTUM_Large", bSTR2715, bSTR2716, boolean1358
'--------------------------------------------------
' Parameter 1 : (String) "ANGULARMOMENTUM_Large"
' Parameter 2 : (String) "Default value"
' Parameter 3 : (String) "Unlocked"
' Parameter 4 : (Boolean) False
'--------------------------------------------------

long1359 = settingRepository1.GetAttr("ANGULARMOMENTUM_ExtraLarge")
'--------------------------------------------------
' Parameter 1 : (String) "ANGULARMOMENTUM_ExtraLarge"
' Returned value : (Variant) (Long) 1
'--------------------------------------------------

Dim bSTR2717
bSTR2717 = ""
Dim bSTR2718
bSTR2718 = ""
Dim boolean1359
settingRepository1.GetAttrInfo "ANGULARMOMENTUM_ExtraLarge", bSTR2717, bSTR2718, boolean1359
'--------------------------------------------------
' Parameter 1 : (String) "ANGULARMOMENTUM_ExtraLarge"
' Parameter 2 : (String) "Default value"
' Parameter 3 : (String) "Unlocked"
' Parameter 4 : (Boolean) False
'--------------------------------------------------

long1360 = settingRepository1.GetAttr("ANGULARMOMENTUM_Small")
'--------------------------------------------------
' Parameter 1 : (String) "ANGULARMOMENTUM_Small"
' Returned value : (Variant) (Long) 1
'--------------------------------------------------

Dim bSTR2719
bSTR2719 = ""
Dim bSTR2720
bSTR2720 = ""
Dim boolean1360
settingRepository1.GetAttrInfo "ANGULARMOMENTUM_Small", bSTR2719, bSTR2720, boolean1360
'--------------------------------------------------
' Parameter 1 : (String) "ANGULARMOMENTUM_Small"
' Parameter 2 : (String) "Default value"
' Parameter 3 : (String) "Unlocked"
' Parameter 4 : (Boolean) False
'--------------------------------------------------

long1361 = settingRepository1.GetAttr("ANGULARMOMENTUM_ExtraSmall")
'--------------------------------------------------
' Parameter 1 : (String) "ANGULARMOMENTUM_ExtraSmall"
' Returned value : (Variant) (Long) 1
'--------------------------------------------------

Dim bSTR2721
bSTR2721 = ""
Dim bSTR2722
bSTR2722 = ""
Dim boolean1361
settingRepository1.GetAttrInfo "ANGULARMOMENTUM_ExtraSmall", bSTR2721, bSTR2722, boolean1361
'--------------------------------------------------
' Parameter 1 : (String) "ANGULARMOMENTUM_ExtraSmall"
' Parameter 2 : (String) "Default value"
' Parameter 3 : (String) "Unlocked"
' Parameter 4 : (Boolean) False
'--------------------------------------------------

long1362 = settingRepository1.GetAttr("ANGULARMOMENTUM_Nanometric")
'--------------------------------------------------
' Parameter 1 : (String) "ANGULARMOMENTUM_Nanometric"
' Returned value : (Variant) (Long) 1
'--------------------------------------------------

Dim bSTR2723
bSTR2723 = ""
Dim bSTR2724
bSTR2724 = ""
Dim boolean1362
settingRepository1.GetAttrInfo "ANGULARMOMENTUM_Nanometric", bSTR2723, bSTR2724, boolean1362
'--------------------------------------------------
' Parameter 1 : (String) "ANGULARMOMENTUM_Nanometric"
' Parameter 2 : (String) "Default value"
' Parameter 3 : (String) "Unlocked"
' Parameter 4 : (Boolean) False
'--------------------------------------------------

long1363 = settingRepository1.GetAttr("ELECTRICALTORQUECONSTANT")
'--------------------------------------------------
' Parameter 1 : (String) "ELECTRICALTORQUECONSTANT"
' Returned value : (Variant) (Long) 1
'--------------------------------------------------

Dim bSTR2725
bSTR2725 = ""
Dim bSTR2726
bSTR2726 = ""
Dim boolean1363
settingRepository1.GetAttrInfo "ELECTRICALTORQUECONSTANT", bSTR2725, bSTR2726, boolean1363
'--------------------------------------------------
' Parameter 1 : (String) "ELECTRICALTORQUECONSTANT"
' Parameter 2 : (String) "Default value"
' Parameter 3 : (String) "Unlocked"
' Parameter 4 : (Boolean) False
'--------------------------------------------------

long1364 = settingRepository1.GetAttr("ELECTRICALTORQUECONSTANT_Large")
'--------------------------------------------------
' Parameter 1 : (String) "ELECTRICALTORQUECONSTANT_Large"
' Returned value : (Variant) (Long) 1
'--------------------------------------------------

Dim bSTR2727
bSTR2727 = ""
Dim bSTR2728
bSTR2728 = ""
Dim boolean1364
settingRepository1.GetAttrInfo "ELECTRICALTORQUECONSTANT_Large", bSTR2727, bSTR2728, boolean1364
'--------------------------------------------------
' Parameter 1 : (String) "ELECTRICALTORQUECONSTANT_Large"
' Parameter 2 : (String) "Default value"
' Parameter 3 : (String) "Unlocked"
' Parameter 4 : (Boolean) False
'--------------------------------------------------

long1365 = settingRepository1.GetAttr("ELECTRICALTORQUECONSTANT_ExtraLarge")
'--------------------------------------------------
' Parameter 1 : (String) "ELECTRICALTORQUECONSTANT_ExtraLarge"
' Returned value : (Variant) (Long) 1
'--------------------------------------------------

Dim bSTR2729
bSTR2729 = ""
Dim bSTR2730
bSTR2730 = ""
Dim boolean1365
settingRepository1.GetAttrInfo "ELECTRICALTORQUECONSTANT_ExtraLarge", bSTR2729, bSTR2730, boolean1365
'--------------------------------------------------
' Parameter 1 : (String) "ELECTRICALTORQUECONSTANT_ExtraLarge"
' Parameter 2 : (String) "Default value"
' Parameter 3 : (String) "Unlocked"
' Parameter 4 : (Boolean) False
'--------------------------------------------------

long1366 = settingRepository1.GetAttr("ELECTRICALTORQUECONSTANT_Small")
'--------------------------------------------------
' Parameter 1 : (String) "ELECTRICALTORQUECONSTANT_Small"
' Returned value : (Variant) (Long) 1
'--------------------------------------------------

Dim bSTR2731
bSTR2731 = ""
Dim bSTR2732
bSTR2732 = ""
Dim boolean1366
settingRepository1.GetAttrInfo "ELECTRICALTORQUECONSTANT_Small", bSTR2731, bSTR2732, boolean1366
'--------------------------------------------------
' Parameter 1 : (String) "ELECTRICALTORQUECONSTANT_Small"
' Parameter 2 : (String) "Default value"
' Parameter 3 : (String) "Unlocked"
' Parameter 4 : (Boolean) False
'--------------------------------------------------

long1367 = settingRepository1.GetAttr("ELECTRICALTORQUECONSTANT_ExtraSmall")
'--------------------------------------------------
' Parameter 1 : (String) "ELECTRICALTORQUECONSTANT_ExtraSmall"
' Returned value : (Variant) (Long) 1
'--------------------------------------------------

Dim bSTR2733
bSTR2733 = ""
Dim bSTR2734
bSTR2734 = ""
Dim boolean1367
settingRepository1.GetAttrInfo "ELECTRICALTORQUECONSTANT_ExtraSmall", bSTR2733, bSTR2734, boolean1367
'--------------------------------------------------
' Parameter 1 : (String) "ELECTRICALTORQUECONSTANT_ExtraSmall"
' Parameter 2 : (String) "Default value"
' Parameter 3 : (String) "Unlocked"
' Parameter 4 : (Boolean) False
'--------------------------------------------------

long1368 = settingRepository1.GetAttr("ELECTRICALTORQUECONSTANT_Nanometric")
'--------------------------------------------------
' Parameter 1 : (String) "ELECTRICALTORQUECONSTANT_Nanometric"
' Returned value : (Variant) (Long) 1
'--------------------------------------------------

Dim bSTR2735
bSTR2735 = ""
Dim bSTR2736
bSTR2736 = ""
Dim boolean1368
settingRepository1.GetAttrInfo "ELECTRICALTORQUECONSTANT_Nanometric", bSTR2735, bSTR2736, boolean1368
'--------------------------------------------------
' Parameter 1 : (String) "ELECTRICALTORQUECONSTANT_Nanometric"
' Parameter 2 : (String) "Default value"
' Parameter 3 : (String) "Unlocked"
' Parameter 4 : (Boolean) False
'--------------------------------------------------

long1369 = settingRepository1.GetAttr("SECTIONMODULUS")
'--------------------------------------------------
' Parameter 1 : (String) "SECTIONMODULUS"
' Returned value : (Variant) (Long) 1
'--------------------------------------------------

Dim bSTR2737
bSTR2737 = ""
Dim bSTR2738
bSTR2738 = ""
Dim boolean1369
settingRepository1.GetAttrInfo "SECTIONMODULUS", bSTR2737, bSTR2738, boolean1369
'--------------------------------------------------
' Parameter 1 : (String) "SECTIONMODULUS"
' Parameter 2 : (String) "Default value"
' Parameter 3 : (String) "Unlocked"
' Parameter 4 : (Boolean) False
'--------------------------------------------------

long1370 = settingRepository1.GetAttr("SECTIONMODULUS_Large")
'--------------------------------------------------
' Parameter 1 : (String) "SECTIONMODULUS_Large"
' Returned value : (Variant) (Long) 1
'--------------------------------------------------

Dim bSTR2739
bSTR2739 = ""
Dim bSTR2740
bSTR2740 = ""
Dim boolean1370
settingRepository1.GetAttrInfo "SECTIONMODULUS_Large", bSTR2739, bSTR2740, boolean1370
'--------------------------------------------------
' Parameter 1 : (String) "SECTIONMODULUS_Large"
' Parameter 2 : (String) "Default value"
' Parameter 3 : (String) "Unlocked"
' Parameter 4 : (Boolean) False
'--------------------------------------------------

long1371 = settingRepository1.GetAttr("SECTIONMODULUS_ExtraLarge")
'--------------------------------------------------
' Parameter 1 : (String) "SECTIONMODULUS_ExtraLarge"
' Returned value : (Variant) (Long) 1
'--------------------------------------------------

Dim bSTR2741
bSTR2741 = ""
Dim bSTR2742
bSTR2742 = ""
Dim boolean1371
settingRepository1.GetAttrInfo "SECTIONMODULUS_ExtraLarge", bSTR2741, bSTR2742, boolean1371
'--------------------------------------------------
' Parameter 1 : (String) "SECTIONMODULUS_ExtraLarge"
' Parameter 2 : (String) "Default value"
' Parameter 3 : (String) "Unlocked"
' Parameter 4 : (Boolean) False
'--------------------------------------------------

long1372 = settingRepository1.GetAttr("SECTIONMODULUS_Small")
'--------------------------------------------------
' Parameter 1 : (String) "SECTIONMODULUS_Small"
' Returned value : (Variant) (Long) 1
'--------------------------------------------------

Dim bSTR2743
bSTR2743 = ""
Dim bSTR2744
bSTR2744 = ""
Dim boolean1372
settingRepository1.GetAttrInfo "SECTIONMODULUS_Small", bSTR2743, bSTR2744, boolean1372
'--------------------------------------------------
' Parameter 1 : (String) "SECTIONMODULUS_Small"
' Parameter 2 : (String) "Default value"
' Parameter 3 : (String) "Unlocked"
' Parameter 4 : (Boolean) False
'--------------------------------------------------

long1373 = settingRepository1.GetAttr("SECTIONMODULUS_ExtraSmall")
'--------------------------------------------------
' Parameter 1 : (String) "SECTIONMODULUS_ExtraSmall"
' Returned value : (Variant) (Long) 1
'--------------------------------------------------

Dim bSTR2745
bSTR2745 = ""
Dim bSTR2746
bSTR2746 = ""
Dim boolean1373
settingRepository1.GetAttrInfo "SECTIONMODULUS_ExtraSmall", bSTR2745, bSTR2746, boolean1373
'--------------------------------------------------
' Parameter 1 : (String) "SECTIONMODULUS_ExtraSmall"
' Parameter 2 : (String) "Default value"
' Parameter 3 : (String) "Unlocked"
' Parameter 4 : (Boolean) False
'--------------------------------------------------

long1374 = settingRepository1.GetAttr("SECTIONMODULUS_Nanometric")
'--------------------------------------------------
' Parameter 1 : (String) "SECTIONMODULUS_Nanometric"
' Returned value : (Variant) (Long) 1
'--------------------------------------------------

Dim bSTR2747
bSTR2747 = ""
Dim bSTR2748
bSTR2748 = ""
Dim boolean1374
settingRepository1.GetAttrInfo "SECTIONMODULUS_Nanometric", bSTR2747, bSTR2748, boolean1374
'--------------------------------------------------
' Parameter 1 : (String) "SECTIONMODULUS_Nanometric"
' Parameter 2 : (String) "Default value"
' Parameter 3 : (String) "Unlocked"
' Parameter 4 : (Boolean) False
'--------------------------------------------------

long1375 = settingRepository1.GetAttr("SURFACETENSION")
'--------------------------------------------------
' Parameter 1 : (String) "SURFACETENSION"
' Returned value : (Variant) (Long) 1
'--------------------------------------------------

Dim bSTR2749
bSTR2749 = ""
Dim bSTR2750
bSTR2750 = ""
Dim boolean1375
settingRepository1.GetAttrInfo "SURFACETENSION", bSTR2749, bSTR2750, boolean1375
'--------------------------------------------------
' Parameter 1 : (String) "SURFACETENSION"
' Parameter 2 : (String) "Default value"
' Parameter 3 : (String) "Unlocked"
' Parameter 4 : (Boolean) False
'--------------------------------------------------

long1376 = settingRepository1.GetAttr("SURFACETENSION_Large")
'--------------------------------------------------
' Parameter 1 : (String) "SURFACETENSION_Large"
' Returned value : (Variant) (Long) 1
'--------------------------------------------------

Dim bSTR2751
bSTR2751 = ""
Dim bSTR2752
bSTR2752 = ""
Dim boolean1376
settingRepository1.GetAttrInfo "SURFACETENSION_Large", bSTR2751, bSTR2752, boolean1376
'--------------------------------------------------
' Parameter 1 : (String) "SURFACETENSION_Large"
' Parameter 2 : (String) "Default value"
' Parameter 3 : (String) "Unlocked"
' Parameter 4 : (Boolean) False
'--------------------------------------------------

long1377 = settingRepository1.GetAttr("SURFACETENSION_ExtraLarge")
'--------------------------------------------------
' Parameter 1 : (String) "SURFACETENSION_ExtraLarge"
' Returned value : (Variant) (Long) 1
'--------------------------------------------------

Dim bSTR2753
bSTR2753 = ""
Dim bSTR2754
bSTR2754 = ""
Dim boolean1377
settingRepository1.GetAttrInfo "SURFACETENSION_ExtraLarge", bSTR2753, bSTR2754, boolean1377
'--------------------------------------------------
' Parameter 1 : (String) "SURFACETENSION_ExtraLarge"
' Parameter 2 : (String) "Default value"
' Parameter 3 : (String) "Unlocked"
' Parameter 4 : (Boolean) False
'--------------------------------------------------

long1378 = settingRepository1.GetAttr("SURFACETENSION_Small")
'--------------------------------------------------
' Parameter 1 : (String) "SURFACETENSION_Small"
' Returned value : (Variant) (Long) 1
'--------------------------------------------------

Dim bSTR2755
bSTR2755 = ""
Dim bSTR2756
bSTR2756 = ""
Dim boolean1378
settingRepository1.GetAttrInfo "SURFACETENSION_Small", bSTR2755, bSTR2756, boolean1378
'--------------------------------------------------
' Parameter 1 : (String) "SURFACETENSION_Small"
' Parameter 2 : (String) "Default value"
' Parameter 3 : (String) "Unlocked"
' Parameter 4 : (Boolean) False
'--------------------------------------------------

long1379 = settingRepository1.GetAttr("SURFACETENSION_ExtraSmall")
'--------------------------------------------------
' Parameter 1 : (String) "SURFACETENSION_ExtraSmall"
' Returned value : (Variant) (Long) 1
'--------------------------------------------------

Dim bSTR2757
bSTR2757 = ""
Dim bSTR2758
bSTR2758 = ""
Dim boolean1379
settingRepository1.GetAttrInfo "SURFACETENSION_ExtraSmall", bSTR2757, bSTR2758, boolean1379
'--------------------------------------------------
' Parameter 1 : (String) "SURFACETENSION_ExtraSmall"
' Parameter 2 : (String) "Default value"
' Parameter 3 : (String) "Unlocked"
' Parameter 4 : (Boolean) False
'--------------------------------------------------

long1380 = settingRepository1.GetAttr("SURFACETENSION_Nanometric")
'--------------------------------------------------
' Parameter 1 : (String) "SURFACETENSION_Nanometric"
' Returned value : (Variant) (Long) 1
'--------------------------------------------------

Dim bSTR2759
bSTR2759 = ""
Dim bSTR2760
bSTR2760 = ""
Dim boolean1380
settingRepository1.GetAttrInfo "SURFACETENSION_Nanometric", bSTR2759, bSTR2760, boolean1380
'--------------------------------------------------
' Parameter 1 : (String) "SURFACETENSION_Nanometric"
' Parameter 2 : (String) "Default value"
' Parameter 3 : (String) "Unlocked"
' Parameter 4 : (Boolean) False
'--------------------------------------------------

long1381 = settingRepository1.GetAttr("ENERGYDENSITY")
'--------------------------------------------------
' Parameter 1 : (String) "ENERGYDENSITY"
' Returned value : (Variant) (Long) 1
'--------------------------------------------------

Dim bSTR2761
bSTR2761 = ""
Dim bSTR2762
bSTR2762 = ""
Dim boolean1381
settingRepository1.GetAttrInfo "ENERGYDENSITY", bSTR2761, bSTR2762, boolean1381
'--------------------------------------------------
' Parameter 1 : (String) "ENERGYDENSITY"
' Parameter 2 : (String) "Default value"
' Parameter 3 : (String) "Unlocked"
' Parameter 4 : (Boolean) False
'--------------------------------------------------

long1382 = settingRepository1.GetAttr("ENERGYDENSITY_Large")
'--------------------------------------------------
' Parameter 1 : (String) "ENERGYDENSITY_Large"
' Returned value : (Variant) (Long) 1
'--------------------------------------------------

Dim bSTR2763
bSTR2763 = ""
Dim bSTR2764
bSTR2764 = ""
Dim boolean1382
settingRepository1.GetAttrInfo "ENERGYDENSITY_Large", bSTR2763, bSTR2764, boolean1382
'--------------------------------------------------
' Parameter 1 : (String) "ENERGYDENSITY_Large"
' Parameter 2 : (String) "Default value"
' Parameter 3 : (String) "Unlocked"
' Parameter 4 : (Boolean) False
'--------------------------------------------------

long1383 = settingRepository1.GetAttr("ENERGYDENSITY_ExtraLarge")
'--------------------------------------------------
' Parameter 1 : (String) "ENERGYDENSITY_ExtraLarge"
' Returned value : (Variant) (Long) 1
'--------------------------------------------------

Dim bSTR2765
bSTR2765 = ""
Dim bSTR2766
bSTR2766 = ""
Dim boolean1383
settingRepository1.GetAttrInfo "ENERGYDENSITY_ExtraLarge", bSTR2765, bSTR2766, boolean1383
'--------------------------------------------------
' Parameter 1 : (String) "ENERGYDENSITY_ExtraLarge"
' Parameter 2 : (String) "Default value"
' Parameter 3 : (String) "Unlocked"
' Parameter 4 : (Boolean) False
'--------------------------------------------------

long1384 = settingRepository1.GetAttr("ENERGYDENSITY_Small")
'--------------------------------------------------
' Parameter 1 : (String) "ENERGYDENSITY_Small"
' Returned value : (Variant) (Long) 1
'--------------------------------------------------

Dim bSTR2767
bSTR2767 = ""
Dim bSTR2768
bSTR2768 = ""
Dim boolean1384
settingRepository1.GetAttrInfo "ENERGYDENSITY_Small", bSTR2767, bSTR2768, boolean1384
'--------------------------------------------------
' Parameter 1 : (String) "ENERGYDENSITY_Small"
' Parameter 2 : (String) "Default value"
' Parameter 3 : (String) "Unlocked"
' Parameter 4 : (Boolean) False
'--------------------------------------------------

long1385 = settingRepository1.GetAttr("ENERGYDENSITY_ExtraSmall")
'--------------------------------------------------
' Parameter 1 : (String) "ENERGYDENSITY_ExtraSmall"
' Returned value : (Variant) (Long) 1
'--------------------------------------------------

Dim bSTR2769
bSTR2769 = ""
Dim bSTR2770
bSTR2770 = ""
Dim boolean1385
settingRepository1.GetAttrInfo "ENERGYDENSITY_ExtraSmall", bSTR2769, bSTR2770, boolean1385
'--------------------------------------------------
' Parameter 1 : (String) "ENERGYDENSITY_ExtraSmall"
' Parameter 2 : (String) "Default value"
' Parameter 3 : (String) "Unlocked"
' Parameter 4 : (Boolean) False
'--------------------------------------------------

long1386 = settingRepository1.GetAttr("ENERGYDENSITY_Nanometric")
'--------------------------------------------------
' Parameter 1 : (String) "ENERGYDENSITY_Nanometric"
' Returned value : (Variant) (Long) 1
'--------------------------------------------------

Dim bSTR2771
bSTR2771 = ""
Dim bSTR2772
bSTR2772 = ""
Dim boolean1386
settingRepository1.GetAttrInfo "ENERGYDENSITY_Nanometric", bSTR2771, bSTR2772, boolean1386
'--------------------------------------------------
' Parameter 1 : (String) "ENERGYDENSITY_Nanometric"
' Parameter 2 : (String) "Default value"
' Parameter 3 : (String) "Unlocked"
' Parameter 4 : (Boolean) False
'--------------------------------------------------

long1387 = settingRepository1.GetAttr("ANGULARMOMENTUMFLUX")
'--------------------------------------------------
' Parameter 1 : (String) "ANGULARMOMENTUMFLUX"
' Returned value : (Variant) (Long) 1
'--------------------------------------------------

Dim bSTR2773
bSTR2773 = ""
Dim bSTR2774
bSTR2774 = ""
Dim boolean1387
settingRepository1.GetAttrInfo "ANGULARMOMENTUMFLUX", bSTR2773, bSTR2774, boolean1387
'--------------------------------------------------
' Parameter 1 : (String) "ANGULARMOMENTUMFLUX"
' Parameter 2 : (String) "Default value"
' Parameter 3 : (String) "Unlocked"
' Parameter 4 : (Boolean) False
'--------------------------------------------------

long1388 = settingRepository1.GetAttr("ANGULARMOMENTUMFLUX_Large")
'--------------------------------------------------
' Parameter 1 : (String) "ANGULARMOMENTUMFLUX_Large"
' Returned value : (Variant) (Long) 1
'--------------------------------------------------

Dim bSTR2775
bSTR2775 = ""
Dim bSTR2776
bSTR2776 = ""
Dim boolean1388
settingRepository1.GetAttrInfo "ANGULARMOMENTUMFLUX_Large", bSTR2775, bSTR2776, boolean1388
'--------------------------------------------------
' Parameter 1 : (String) "ANGULARMOMENTUMFLUX_Large"
' Parameter 2 : (String) "Default value"
' Parameter 3 : (String) "Unlocked"
' Parameter 4 : (Boolean) False
'--------------------------------------------------

long1389 = settingRepository1.GetAttr("ANGULARMOMENTUMFLUX_ExtraLarge")
'--------------------------------------------------
' Parameter 1 : (String) "ANGULARMOMENTUMFLUX_ExtraLarge"
' Returned value : (Variant) (Long) 1
'--------------------------------------------------

Dim bSTR2777
bSTR2777 = ""
Dim bSTR2778
bSTR2778 = ""
Dim boolean1389
settingRepository1.GetAttrInfo "ANGULARMOMENTUMFLUX_ExtraLarge", bSTR2777, bSTR2778, boolean1389
'--------------------------------------------------
' Parameter 1 : (String) "ANGULARMOMENTUMFLUX_ExtraLarge"
' Parameter 2 : (String) "Default value"
' Parameter 3 : (String) "Unlocked"
' Parameter 4 : (Boolean) False
'--------------------------------------------------

long1390 = settingRepository1.GetAttr("ANGULARMOMENTUMFLUX_Small")
'--------------------------------------------------
' Parameter 1 : (String) "ANGULARMOMENTUMFLUX_Small"
' Returned value : (Variant) (Long) 1
'--------------------------------------------------

Dim bSTR2779
bSTR2779 = ""
Dim bSTR2780
bSTR2780 = ""
Dim boolean1390
settingRepository1.GetAttrInfo "ANGULARMOMENTUMFLUX_Small", bSTR2779, bSTR2780, boolean1390
'--------------------------------------------------
' Parameter 1 : (String) "ANGULARMOMENTUMFLUX_Small"
' Parameter 2 : (String) "Default value"
' Parameter 3 : (String) "Unlocked"
' Parameter 4 : (Boolean) False
'--------------------------------------------------

long1391 = settingRepository1.GetAttr("ANGULARMOMENTUMFLUX_ExtraSmall")
'--------------------------------------------------
' Parameter 1 : (String) "ANGULARMOMENTUMFLUX_ExtraSmall"
' Returned value : (Variant) (Long) 1
'--------------------------------------------------

Dim bSTR2781
bSTR2781 = ""
Dim bSTR2782
bSTR2782 = ""
Dim boolean1391
settingRepository1.GetAttrInfo "ANGULARMOMENTUMFLUX_ExtraSmall", bSTR2781, bSTR2782, boolean1391
'--------------------------------------------------
' Parameter 1 : (String) "ANGULARMOMENTUMFLUX_ExtraSmall"
' Parameter 2 : (String) "Default value"
' Parameter 3 : (String) "Unlocked"
' Parameter 4 : (Boolean) False
'--------------------------------------------------

long1392 = settingRepository1.GetAttr("ANGULARMOMENTUMFLUX_Nanometric")
'--------------------------------------------------
' Parameter 1 : (String) "ANGULARMOMENTUMFLUX_Nanometric"
' Returned value : (Variant) (Long) 1
'--------------------------------------------------

Dim bSTR2783
bSTR2783 = ""
Dim bSTR2784
bSTR2784 = ""
Dim boolean1392
settingRepository1.GetAttrInfo "ANGULARMOMENTUMFLUX_Nanometric", bSTR2783, bSTR2784, boolean1392
'--------------------------------------------------
' Parameter 1 : (String) "ANGULARMOMENTUMFLUX_Nanometric"
' Parameter 2 : (String) "Default value"
' Parameter 3 : (String) "Unlocked"
' Parameter 4 : (Boolean) False
'--------------------------------------------------

long1393 = settingRepository1.GetAttr("TEMPERATUREDIFFERENCE")
'--------------------------------------------------
' Parameter 1 : (String) "TEMPERATUREDIFFERENCE"
' Returned value : (Variant) (Long) 1
'--------------------------------------------------

Dim bSTR2785
bSTR2785 = ""
Dim bSTR2786
bSTR2786 = ""
Dim boolean1393
settingRepository1.GetAttrInfo "TEMPERATUREDIFFERENCE", bSTR2785, bSTR2786, boolean1393
'--------------------------------------------------
' Parameter 1 : (String) "TEMPERATUREDIFFERENCE"
' Parameter 2 : (String) "Default value"
' Parameter 3 : (String) "Unlocked"
' Parameter 4 : (Boolean) False
'--------------------------------------------------

long1394 = settingRepository1.GetAttr("TEMPERATUREDIFFERENCE_Large")
'--------------------------------------------------
' Parameter 1 : (String) "TEMPERATUREDIFFERENCE_Large"
' Returned value : (Variant) (Long) 1
'--------------------------------------------------

Dim bSTR2787
bSTR2787 = ""
Dim bSTR2788
bSTR2788 = ""
Dim boolean1394
settingRepository1.GetAttrInfo "TEMPERATUREDIFFERENCE_Large", bSTR2787, bSTR2788, boolean1394
'--------------------------------------------------
' Parameter 1 : (String) "TEMPERATUREDIFFERENCE_Large"
' Parameter 2 : (String) "Default value"
' Parameter 3 : (String) "Unlocked"
' Parameter 4 : (Boolean) False
'--------------------------------------------------

long1395 = settingRepository1.GetAttr("TEMPERATUREDIFFERENCE_ExtraLarge")
'--------------------------------------------------
' Parameter 1 : (String) "TEMPERATUREDIFFERENCE_ExtraLarge"
' Returned value : (Variant) (Long) 1
'--------------------------------------------------

Dim bSTR2789
bSTR2789 = ""
Dim bSTR2790
bSTR2790 = ""
Dim boolean1395
settingRepository1.GetAttrInfo "TEMPERATUREDIFFERENCE_ExtraLarge", bSTR2789, bSTR2790, boolean1395
'--------------------------------------------------
' Parameter 1 : (String) "TEMPERATUREDIFFERENCE_ExtraLarge"
' Parameter 2 : (String) "Default value"
' Parameter 3 : (String) "Unlocked"
' Parameter 4 : (Boolean) False
'--------------------------------------------------

long1396 = settingRepository1.GetAttr("TEMPERATUREDIFFERENCE_Small")
'--------------------------------------------------
' Parameter 1 : (String) "TEMPERATUREDIFFERENCE_Small"
' Returned value : (Variant) (Long) 1
'--------------------------------------------------

Dim bSTR2791
bSTR2791 = ""
Dim bSTR2792
bSTR2792 = ""
Dim boolean1396
settingRepository1.GetAttrInfo "TEMPERATUREDIFFERENCE_Small", bSTR2791, bSTR2792, boolean1396
'--------------------------------------------------
' Parameter 1 : (String) "TEMPERATUREDIFFERENCE_Small"
' Parameter 2 : (String) "Default value"
' Parameter 3 : (String) "Unlocked"
' Parameter 4 : (Boolean) False
'--------------------------------------------------

long1397 = settingRepository1.GetAttr("TEMPERATUREDIFFERENCE_ExtraSmall")
'--------------------------------------------------
' Parameter 1 : (String) "TEMPERATUREDIFFERENCE_ExtraSmall"
' Returned value : (Variant) (Long) 1
'--------------------------------------------------

Dim bSTR2793
bSTR2793 = ""
Dim bSTR2794
bSTR2794 = ""
Dim boolean1397
settingRepository1.GetAttrInfo "TEMPERATUREDIFFERENCE_ExtraSmall", bSTR2793, bSTR2794, boolean1397
'--------------------------------------------------
' Parameter 1 : (String) "TEMPERATUREDIFFERENCE_ExtraSmall"
' Parameter 2 : (String) "Default value"
' Parameter 3 : (String) "Unlocked"
' Parameter 4 : (Boolean) False
'--------------------------------------------------

long1398 = settingRepository1.GetAttr("TEMPERATUREDIFFERENCE_Nanometric")
'--------------------------------------------------
' Parameter 1 : (String) "TEMPERATUREDIFFERENCE_Nanometric"
' Returned value : (Variant) (Long) 1
'--------------------------------------------------

Dim bSTR2795
bSTR2795 = ""
Dim bSTR2796
bSTR2796 = ""
Dim boolean1398
settingRepository1.GetAttrInfo "TEMPERATUREDIFFERENCE_Nanometric", bSTR2795, bSTR2796, boolean1398
'--------------------------------------------------
' Parameter 1 : (String) "TEMPERATUREDIFFERENCE_Nanometric"
' Parameter 2 : (String) "Default value"
' Parameter 3 : (String) "Unlocked"
' Parameter 4 : (Boolean) False
'--------------------------------------------------

long1399 = settingRepository1.GetAttr("TEMPERATURESLOPE")
'--------------------------------------------------
' Parameter 1 : (String) "TEMPERATURESLOPE"
' Returned value : (Variant) (Long) 1
'--------------------------------------------------

Dim bSTR2797
bSTR2797 = ""
Dim bSTR2798
bSTR2798 = ""
Dim boolean1399
settingRepository1.GetAttrInfo "TEMPERATURESLOPE", bSTR2797, bSTR2798, boolean1399
'--------------------------------------------------
' Parameter 1 : (String) "TEMPERATURESLOPE"
' Parameter 2 : (String) "Default value"
' Parameter 3 : (String) "Unlocked"
' Parameter 4 : (Boolean) False
'--------------------------------------------------

long1400 = settingRepository1.GetAttr("TEMPERATURESLOPE_Large")
'--------------------------------------------------
' Parameter 1 : (String) "TEMPERATURESLOPE_Large"
' Returned value : (Variant) (Long) 1
'--------------------------------------------------

Dim bSTR2799
bSTR2799 = ""
Dim bSTR2800
bSTR2800 = ""
Dim boolean1400
settingRepository1.GetAttrInfo "TEMPERATURESLOPE_Large", bSTR2799, bSTR2800, boolean1400
'--------------------------------------------------
' Parameter 1 : (String) "TEMPERATURESLOPE_Large"
' Parameter 2 : (String) "Default value"
' Parameter 3 : (String) "Unlocked"
' Parameter 4 : (Boolean) False
'--------------------------------------------------

long1401 = settingRepository1.GetAttr("TEMPERATURESLOPE_ExtraLarge")
'--------------------------------------------------
' Parameter 1 : (String) "TEMPERATURESLOPE_ExtraLarge"
' Returned value : (Variant) (Long) 1
'--------------------------------------------------

Dim bSTR2801
bSTR2801 = ""
Dim bSTR2802
bSTR2802 = ""
Dim boolean1401
settingRepository1.GetAttrInfo "TEMPERATURESLOPE_ExtraLarge", bSTR2801, bSTR2802, boolean1401
'--------------------------------------------------
' Parameter 1 : (String) "TEMPERATURESLOPE_ExtraLarge"
' Parameter 2 : (String) "Default value"
' Parameter 3 : (String) "Unlocked"
' Parameter 4 : (Boolean) False
'--------------------------------------------------

long1402 = settingRepository1.GetAttr("TEMPERATURESLOPE_Small")
'--------------------------------------------------
' Parameter 1 : (String) "TEMPERATURESLOPE_Small"
' Returned value : (Variant) (Long) 1
'--------------------------------------------------

Dim bSTR2803
bSTR2803 = ""
Dim bSTR2804
bSTR2804 = ""
Dim boolean1402
settingRepository1.GetAttrInfo "TEMPERATURESLOPE_Small", bSTR2803, bSTR2804, boolean1402
'--------------------------------------------------
' Parameter 1 : (String) "TEMPERATURESLOPE_Small"
' Parameter 2 : (String) "Default value"
' Parameter 3 : (String) "Unlocked"
' Parameter 4 : (Boolean) False
'--------------------------------------------------

long1403 = settingRepository1.GetAttr("TEMPERATURESLOPE_ExtraSmall")
'--------------------------------------------------
' Parameter 1 : (String) "TEMPERATURESLOPE_ExtraSmall"
' Returned value : (Variant) (Long) 1
'--------------------------------------------------

Dim bSTR2805
bSTR2805 = ""
Dim bSTR2806
bSTR2806 = ""
Dim boolean1403
settingRepository1.GetAttrInfo "TEMPERATURESLOPE_ExtraSmall", bSTR2805, bSTR2806, boolean1403
'--------------------------------------------------
' Parameter 1 : (String) "TEMPERATURESLOPE_ExtraSmall"
' Parameter 2 : (String) "Default value"
' Parameter 3 : (String) "Unlocked"
' Parameter 4 : (Boolean) False
'--------------------------------------------------

long1404 = settingRepository1.GetAttr("TEMPERATURESLOPE_Nanometric")
'--------------------------------------------------
' Parameter 1 : (String) "TEMPERATURESLOPE_Nanometric"
' Returned value : (Variant) (Long) 1
'--------------------------------------------------

Dim bSTR2807
bSTR2807 = ""
Dim bSTR2808
bSTR2808 = ""
Dim boolean1404
settingRepository1.GetAttrInfo "TEMPERATURESLOPE_Nanometric", bSTR2807, bSTR2808, boolean1404
'--------------------------------------------------
' Parameter 1 : (String) "TEMPERATURESLOPE_Nanometric"
' Parameter 2 : (String) "Default value"
' Parameter 3 : (String) "Unlocked"
' Parameter 4 : (Boolean) False
'--------------------------------------------------

long1405 = settingRepository1.GetAttr("QUADRATICTEMPERATURECOEFFICIENT")
'--------------------------------------------------
' Parameter 1 : (String) "QUADRATICTEMPERATURECOEFFICIENT"
' Returned value : (Variant) (Long) 1
'--------------------------------------------------

Dim bSTR2809
bSTR2809 = ""
Dim bSTR2810
bSTR2810 = ""
Dim boolean1405
settingRepository1.GetAttrInfo "QUADRATICTEMPERATURECOEFFICIENT", bSTR2809, bSTR2810, boolean1405
'--------------------------------------------------
' Parameter 1 : (String) "QUADRATICTEMPERATURECOEFFICIENT"
' Parameter 2 : (String) "Default value"
' Parameter 3 : (String) "Unlocked"
' Parameter 4 : (Boolean) False
'--------------------------------------------------

long1406 = settingRepository1.GetAttr("QUADRATICTEMPERATURECOEFFICIENT_Large")
'--------------------------------------------------
' Parameter 1 : (String) "QUADRATICTEMPERATURECOEFFICIENT_Large"
' Returned value : (Variant) (Long) 1
'--------------------------------------------------

Dim bSTR2811
bSTR2811 = ""
Dim bSTR2812
bSTR2812 = ""
Dim boolean1406
settingRepository1.GetAttrInfo "QUADRATICTEMPERATURECOEFFICIENT_Large", bSTR2811, bSTR2812, boolean1406
'--------------------------------------------------
' Parameter 1 : (String) "QUADRATICTEMPERATURECOEFFICIENT_Large"
' Parameter 2 : (String) "Default value"
' Parameter 3 : (String) "Unlocked"
' Parameter 4 : (Boolean) False
'--------------------------------------------------

long1407 = settingRepository1.GetAttr("QUADRATICTEMPERATURECOEFFICIENT_ExtraLarge")
'--------------------------------------------------
' Parameter 1 : (String) "QUADRATICTEMPERATURECOEFFICIENT_ExtraLarge"
' Returned value : (Variant) (Long) 1
'--------------------------------------------------

Dim bSTR2813
bSTR2813 = ""
Dim bSTR2814
bSTR2814 = ""
Dim boolean1407
settingRepository1.GetAttrInfo "QUADRATICTEMPERATURECOEFFICIENT_ExtraLarge", bSTR2813, bSTR2814, boolean1407
'--------------------------------------------------
' Parameter 1 : (String) "QUADRATICTEMPERATURECOEFFICIENT_ExtraLarge"
' Parameter 2 : (String) "Default value"
' Parameter 3 : (String) "Unlocked"
' Parameter 4 : (Boolean) False
'--------------------------------------------------

long1408 = settingRepository1.GetAttr("QUADRATICTEMPERATURECOEFFICIENT_Small")
'--------------------------------------------------
' Parameter 1 : (String) "QUADRATICTEMPERATURECOEFFICIENT_Small"
' Returned value : (Variant) (Long) 1
'--------------------------------------------------

Dim bSTR2815
bSTR2815 = ""
Dim bSTR2816
bSTR2816 = ""
Dim boolean1408
settingRepository1.GetAttrInfo "QUADRATICTEMPERATURECOEFFICIENT_Small", bSTR2815, bSTR2816, boolean1408
'--------------------------------------------------
' Parameter 1 : (String) "QUADRATICTEMPERATURECOEFFICIENT_Small"
' Parameter 2 : (String) "Default value"
' Parameter 3 : (String) "Unlocked"
' Parameter 4 : (Boolean) False
'--------------------------------------------------

long1409 = settingRepository1.GetAttr("QUADRATICTEMPERATURECOEFFICIENT_ExtraSmall")
'--------------------------------------------------
' Parameter 1 : (String) "QUADRATICTEMPERATURECOEFFICIENT_ExtraSmall"
' Returned value : (Variant) (Long) 1
'--------------------------------------------------

Dim bSTR2817
bSTR2817 = ""
Dim bSTR2818
bSTR2818 = ""
Dim boolean1409
settingRepository1.GetAttrInfo "QUADRATICTEMPERATURECOEFFICIENT_ExtraSmall", bSTR2817, bSTR2818, boolean1409
'--------------------------------------------------
' Parameter 1 : (String) "QUADRATICTEMPERATURECOEFFICIENT_ExtraSmall"
' Parameter 2 : (String) "Default value"
' Parameter 3 : (String) "Unlocked"
' Parameter 4 : (Boolean) False
'--------------------------------------------------

long1410 = settingRepository1.GetAttr("QUADRATICTEMPERATURECOEFFICIENT_Nanometric")
'--------------------------------------------------
' Parameter 1 : (String) "QUADRATICTEMPERATURECOEFFICIENT_Nanometric"
' Returned value : (Variant) (Long) 1
'--------------------------------------------------

Dim bSTR2819
bSTR2819 = ""
Dim bSTR2820
bSTR2820 = ""
Dim boolean1410
settingRepository1.GetAttrInfo "QUADRATICTEMPERATURECOEFFICIENT_Nanometric", bSTR2819, bSTR2820, boolean1410
'--------------------------------------------------
' Parameter 1 : (String) "QUADRATICTEMPERATURECOEFFICIENT_Nanometric"
' Parameter 2 : (String) "Default value"
' Parameter 3 : (String) "Unlocked"
' Parameter 4 : (Boolean) False
'--------------------------------------------------

long1411 = settingRepository1.GetAttr("PRESSURECOEFFICIENT")
'--------------------------------------------------
' Parameter 1 : (String) "PRESSURECOEFFICIENT"
' Returned value : (Variant) (Long) 1
'--------------------------------------------------

Dim bSTR2821
bSTR2821 = ""
Dim bSTR2822
bSTR2822 = ""
Dim boolean1411
settingRepository1.GetAttrInfo "PRESSURECOEFFICIENT", bSTR2821, bSTR2822, boolean1411
'--------------------------------------------------
' Parameter 1 : (String) "PRESSURECOEFFICIENT"
' Parameter 2 : (String) "Default value"
' Parameter 3 : (String) "Unlocked"
' Parameter 4 : (Boolean) False
'--------------------------------------------------

long1412 = settingRepository1.GetAttr("PRESSURECOEFFICIENT_Large")
'--------------------------------------------------
' Parameter 1 : (String) "PRESSURECOEFFICIENT_Large"
' Returned value : (Variant) (Long) 1
'--------------------------------------------------

Dim bSTR2823
bSTR2823 = ""
Dim bSTR2824
bSTR2824 = ""
Dim boolean1412
settingRepository1.GetAttrInfo "PRESSURECOEFFICIENT_Large", bSTR2823, bSTR2824, boolean1412
'--------------------------------------------------
' Parameter 1 : (String) "PRESSURECOEFFICIENT_Large"
' Parameter 2 : (String) "Default value"
' Parameter 3 : (String) "Unlocked"
' Parameter 4 : (Boolean) False
'--------------------------------------------------

long1413 = settingRepository1.GetAttr("PRESSURECOEFFICIENT_ExtraLarge")
'--------------------------------------------------
' Parameter 1 : (String) "PRESSURECOEFFICIENT_ExtraLarge"
' Returned value : (Variant) (Long) 1
'--------------------------------------------------

Dim bSTR2825
bSTR2825 = ""
Dim bSTR2826
bSTR2826 = ""
Dim boolean1413
settingRepository1.GetAttrInfo "PRESSURECOEFFICIENT_ExtraLarge", bSTR2825, bSTR2826, boolean1413
'--------------------------------------------------
' Parameter 1 : (String) "PRESSURECOEFFICIENT_ExtraLarge"
' Parameter 2 : (String) "Default value"
' Parameter 3 : (String) "Unlocked"
' Parameter 4 : (Boolean) False
'--------------------------------------------------

long1414 = settingRepository1.GetAttr("PRESSURECOEFFICIENT_Small")
'--------------------------------------------------
' Parameter 1 : (String) "PRESSURECOEFFICIENT_Small"
' Returned value : (Variant) (Long) 1
'--------------------------------------------------

Dim bSTR2827
bSTR2827 = ""
Dim bSTR2828
bSTR2828 = ""
Dim boolean1414
settingRepository1.GetAttrInfo "PRESSURECOEFFICIENT_Small", bSTR2827, bSTR2828, boolean1414
'--------------------------------------------------
' Parameter 1 : (String) "PRESSURECOEFFICIENT_Small"
' Parameter 2 : (String) "Default value"
' Parameter 3 : (String) "Unlocked"
' Parameter 4 : (Boolean) False
'--------------------------------------------------

long1415 = settingRepository1.GetAttr("PRESSURECOEFFICIENT_ExtraSmall")
'--------------------------------------------------
' Parameter 1 : (String) "PRESSURECOEFFICIENT_ExtraSmall"
' Returned value : (Variant) (Long) 1
'--------------------------------------------------

Dim bSTR2829
bSTR2829 = ""
Dim bSTR2830
bSTR2830 = ""
Dim boolean1415
settingRepository1.GetAttrInfo "PRESSURECOEFFICIENT_ExtraSmall", bSTR2829, bSTR2830, boolean1415
'--------------------------------------------------
' Parameter 1 : (String) "PRESSURECOEFFICIENT_ExtraSmall"
' Parameter 2 : (String) "Default value"
' Parameter 3 : (String) "Unlocked"
' Parameter 4 : (Boolean) False
'--------------------------------------------------

long1416 = settingRepository1.GetAttr("PRESSURECOEFFICIENT_Nanometric")
'--------------------------------------------------
' Parameter 1 : (String) "PRESSURECOEFFICIENT_Nanometric"
' Returned value : (Variant) (Long) 1
'--------------------------------------------------

Dim bSTR2831
bSTR2831 = ""
Dim bSTR2832
bSTR2832 = ""
Dim boolean1416
settingRepository1.GetAttrInfo "PRESSURECOEFFICIENT_Nanometric", bSTR2831, bSTR2832, boolean1416
'--------------------------------------------------
' Parameter 1 : (String) "PRESSURECOEFFICIENT_Nanometric"
' Parameter 2 : (String) "Default value"
' Parameter 3 : (String) "Unlocked"
' Parameter 4 : (Boolean) False
'--------------------------------------------------

long1417 = settingRepository1.GetAttr("COMPRESSIBILITY")
'--------------------------------------------------
' Parameter 1 : (String) "COMPRESSIBILITY"
' Returned value : (Variant) (Long) 1
'--------------------------------------------------

Dim bSTR2833
bSTR2833 = ""
Dim bSTR2834
bSTR2834 = ""
Dim boolean1417
settingRepository1.GetAttrInfo "COMPRESSIBILITY", bSTR2833, bSTR2834, boolean1417
'--------------------------------------------------
' Parameter 1 : (String) "COMPRESSIBILITY"
' Parameter 2 : (String) "Default value"
' Parameter 3 : (String) "Unlocked"
' Parameter 4 : (Boolean) False
'--------------------------------------------------

long1418 = settingRepository1.GetAttr("COMPRESSIBILITY_Large")
'--------------------------------------------------
' Parameter 1 : (String) "COMPRESSIBILITY_Large"
' Returned value : (Variant) (Long) 1
'--------------------------------------------------

Dim bSTR2835
bSTR2835 = ""
Dim bSTR2836
bSTR2836 = ""
Dim boolean1418
settingRepository1.GetAttrInfo "COMPRESSIBILITY_Large", bSTR2835, bSTR2836, boolean1418
'--------------------------------------------------
' Parameter 1 : (String) "COMPRESSIBILITY_Large"
' Parameter 2 : (String) "Default value"
' Parameter 3 : (String) "Unlocked"
' Parameter 4 : (Boolean) False
'--------------------------------------------------

long1419 = settingRepository1.GetAttr("COMPRESSIBILITY_ExtraLarge")
'--------------------------------------------------
' Parameter 1 : (String) "COMPRESSIBILITY_ExtraLarge"
' Returned value : (Variant) (Long) 1
'--------------------------------------------------

Dim bSTR2837
bSTR2837 = ""
Dim bSTR2838
bSTR2838 = ""
Dim boolean1419
settingRepository1.GetAttrInfo "COMPRESSIBILITY_ExtraLarge", bSTR2837, bSTR2838, boolean1419
'--------------------------------------------------
' Parameter 1 : (String) "COMPRESSIBILITY_ExtraLarge"
' Parameter 2 : (String) "Default value"
' Parameter 3 : (String) "Unlocked"
' Parameter 4 : (Boolean) False
'--------------------------------------------------

long1420 = settingRepository1.GetAttr("COMPRESSIBILITY_Small")
'--------------------------------------------------
' Parameter 1 : (String) "COMPRESSIBILITY_Small"
' Returned value : (Variant) (Long) 1
'--------------------------------------------------

Dim bSTR2839
bSTR2839 = ""
Dim bSTR2840
bSTR2840 = ""
Dim boolean1420
settingRepository1.GetAttrInfo "COMPRESSIBILITY_Small", bSTR2839, bSTR2840, boolean1420
'--------------------------------------------------
' Parameter 1 : (String) "COMPRESSIBILITY_Small"
' Parameter 2 : (String) "Default value"
' Parameter 3 : (String) "Unlocked"
' Parameter 4 : (Boolean) False
'--------------------------------------------------

long1421 = settingRepository1.GetAttr("COMPRESSIBILITY_ExtraSmall")
'--------------------------------------------------
' Parameter 1 : (String) "COMPRESSIBILITY_ExtraSmall"
' Returned value : (Variant) (Long) 1
'--------------------------------------------------

Dim bSTR2841
bSTR2841 = ""
Dim bSTR2842
bSTR2842 = ""
Dim boolean1421
settingRepository1.GetAttrInfo "COMPRESSIBILITY_ExtraSmall", bSTR2841, bSTR2842, boolean1421
'--------------------------------------------------
' Parameter 1 : (String) "COMPRESSIBILITY_ExtraSmall"
' Parameter 2 : (String) "Default value"
' Parameter 3 : (String) "Unlocked"
' Parameter 4 : (Boolean) False
'--------------------------------------------------

long1422 = settingRepository1.GetAttr("COMPRESSIBILITY_Nanometric")
'--------------------------------------------------
' Parameter 1 : (String) "COMPRESSIBILITY_Nanometric"
' Returned value : (Variant) (Long) 1
'--------------------------------------------------

Dim bSTR2843
bSTR2843 = ""
Dim bSTR2844
bSTR2844 = ""
Dim boolean1422
settingRepository1.GetAttrInfo "COMPRESSIBILITY_Nanometric", bSTR2843, bSTR2844, boolean1422
'--------------------------------------------------
' Parameter 1 : (String) "COMPRESSIBILITY_Nanometric"
' Parameter 2 : (String) "Default value"
' Parameter 3 : (String) "Unlocked"
' Parameter 4 : (Boolean) False
'--------------------------------------------------

long1423 = settingRepository1.GetAttr("DENSITYOFHEATFLOWRATE")
'--------------------------------------------------
' Parameter 1 : (String) "DENSITYOFHEATFLOWRATE"
' Returned value : (Variant) (Long) 1
'--------------------------------------------------

Dim bSTR2845
bSTR2845 = ""
Dim bSTR2846
bSTR2846 = ""
Dim boolean1423
settingRepository1.GetAttrInfo "DENSITYOFHEATFLOWRATE", bSTR2845, bSTR2846, boolean1423
'--------------------------------------------------
' Parameter 1 : (String) "DENSITYOFHEATFLOWRATE"
' Parameter 2 : (String) "Default value"
' Parameter 3 : (String) "Unlocked"
' Parameter 4 : (Boolean) False
'--------------------------------------------------

long1424 = settingRepository1.GetAttr("DENSITYOFHEATFLOWRATE_Large")
'--------------------------------------------------
' Parameter 1 : (String) "DENSITYOFHEATFLOWRATE_Large"
' Returned value : (Variant) (Long) 1
'--------------------------------------------------

Dim bSTR2847
bSTR2847 = ""
Dim bSTR2848
bSTR2848 = ""
Dim boolean1424
settingRepository1.GetAttrInfo "DENSITYOFHEATFLOWRATE_Large", bSTR2847, bSTR2848, boolean1424
'--------------------------------------------------
' Parameter 1 : (String) "DENSITYOFHEATFLOWRATE_Large"
' Parameter 2 : (String) "Default value"
' Parameter 3 : (String) "Unlocked"
' Parameter 4 : (Boolean) False
'--------------------------------------------------

long1425 = settingRepository1.GetAttr("DENSITYOFHEATFLOWRATE_ExtraLarge")
'--------------------------------------------------
' Parameter 1 : (String) "DENSITYOFHEATFLOWRATE_ExtraLarge"
' Returned value : (Variant) (Long) 1
'--------------------------------------------------

Dim bSTR2849
bSTR2849 = ""
Dim bSTR2850
bSTR2850 = ""
Dim boolean1425
settingRepository1.GetAttrInfo "DENSITYOFHEATFLOWRATE_ExtraLarge", bSTR2849, bSTR2850, boolean1425
'--------------------------------------------------
' Parameter 1 : (String) "DENSITYOFHEATFLOWRATE_ExtraLarge"
' Parameter 2 : (String) "Default value"
' Parameter 3 : (String) "Unlocked"
' Parameter 4 : (Boolean) False
'--------------------------------------------------

long1426 = settingRepository1.GetAttr("DENSITYOFHEATFLOWRATE_Small")
'--------------------------------------------------
' Parameter 1 : (String) "DENSITYOFHEATFLOWRATE_Small"
' Returned value : (Variant) (Long) 1
'--------------------------------------------------

Dim bSTR2851
bSTR2851 = ""
Dim bSTR2852
bSTR2852 = ""
Dim boolean1426
settingRepository1.GetAttrInfo "DENSITYOFHEATFLOWRATE_Small", bSTR2851, bSTR2852, boolean1426
'--------------------------------------------------
' Parameter 1 : (String) "DENSITYOFHEATFLOWRATE_Small"
' Parameter 2 : (String) "Default value"
' Parameter 3 : (String) "Unlocked"
' Parameter 4 : (Boolean) False
'--------------------------------------------------

long1427 = settingRepository1.GetAttr("DENSITYOFHEATFLOWRATE_ExtraSmall")
'--------------------------------------------------
' Parameter 1 : (String) "DENSITYOFHEATFLOWRATE_ExtraSmall"
' Returned value : (Variant) (Long) 1
'--------------------------------------------------

Dim bSTR2853
bSTR2853 = ""
Dim bSTR2854
bSTR2854 = ""
Dim boolean1427
settingRepository1.GetAttrInfo "DENSITYOFHEATFLOWRATE_ExtraSmall", bSTR2853, bSTR2854, boolean1427
'--------------------------------------------------
' Parameter 1 : (String) "DENSITYOFHEATFLOWRATE_ExtraSmall"
' Parameter 2 : (String) "Default value"
' Parameter 3 : (String) "Unlocked"
' Parameter 4 : (Boolean) False
'--------------------------------------------------

long1428 = settingRepository1.GetAttr("DENSITYOFHEATFLOWRATE_Nanometric")
'--------------------------------------------------
' Parameter 1 : (String) "DENSITYOFHEATFLOWRATE_Nanometric"
' Returned value : (Variant) (Long) 1
'--------------------------------------------------

Dim bSTR2855
bSTR2855 = ""
Dim bSTR2856
bSTR2856 = ""
Dim boolean1428
settingRepository1.GetAttrInfo "DENSITYOFHEATFLOWRATE_Nanometric", bSTR2855, bSTR2856, boolean1428
'--------------------------------------------------
' Parameter 1 : (String) "DENSITYOFHEATFLOWRATE_Nanometric"
' Parameter 2 : (String) "Default value"
' Parameter 3 : (String) "Unlocked"
' Parameter 4 : (Boolean) False
'--------------------------------------------------

long1429 = settingRepository1.GetAttr("THERMALINSULANCE")
'--------------------------------------------------
' Parameter 1 : (String) "THERMALINSULANCE"
' Returned value : (Variant) (Long) 1
'--------------------------------------------------

Dim bSTR2857
bSTR2857 = ""
Dim bSTR2858
bSTR2858 = ""
Dim boolean1429
settingRepository1.GetAttrInfo "THERMALINSULANCE", bSTR2857, bSTR2858, boolean1429
'--------------------------------------------------
' Parameter 1 : (String) "THERMALINSULANCE"
' Parameter 2 : (String) "Default value"
' Parameter 3 : (String) "Unlocked"
' Parameter 4 : (Boolean) False
'--------------------------------------------------

long1430 = settingRepository1.GetAttr("THERMALINSULANCE_Large")
'--------------------------------------------------
' Parameter 1 : (String) "THERMALINSULANCE_Large"
' Returned value : (Variant) (Long) 1
'--------------------------------------------------

Dim bSTR2859
bSTR2859 = ""
Dim bSTR2860
bSTR2860 = ""
Dim boolean1430
settingRepository1.GetAttrInfo "THERMALINSULANCE_Large", bSTR2859, bSTR2860, boolean1430
'--------------------------------------------------
' Parameter 1 : (String) "THERMALINSULANCE_Large"
' Parameter 2 : (String) "Default value"
' Parameter 3 : (String) "Unlocked"
' Parameter 4 : (Boolean) False
'--------------------------------------------------

long1431 = settingRepository1.GetAttr("THERMALINSULANCE_ExtraLarge")
'--------------------------------------------------
' Parameter 1 : (String) "THERMALINSULANCE_ExtraLarge"
' Returned value : (Variant) (Long) 1
'--------------------------------------------------

Dim bSTR2861
bSTR2861 = ""
Dim bSTR2862
bSTR2862 = ""
Dim boolean1431
settingRepository1.GetAttrInfo "THERMALINSULANCE_ExtraLarge", bSTR2861, bSTR2862, boolean1431
'--------------------------------------------------
' Parameter 1 : (String) "THERMALINSULANCE_ExtraLarge"
' Parameter 2 : (String) "Default value"
' Parameter 3 : (String) "Unlocked"
' Parameter 4 : (Boolean) False
'--------------------------------------------------

long1432 = settingRepository1.GetAttr("THERMALINSULANCE_Small")
'--------------------------------------------------
' Parameter 1 : (String) "THERMALINSULANCE_Small"
' Returned value : (Variant) (Long) 1
'--------------------------------------------------

Dim bSTR2863
bSTR2863 = ""
Dim bSTR2864
bSTR2864 = ""
Dim boolean1432
settingRepository1.GetAttrInfo "THERMALINSULANCE_Small", bSTR2863, bSTR2864, boolean1432
'--------------------------------------------------
' Parameter 1 : (String) "THERMALINSULANCE_Small"
' Parameter 2 : (String) "Default value"
' Parameter 3 : (String) "Unlocked"
' Parameter 4 : (Boolean) False
'--------------------------------------------------

long1433 = settingRepository1.GetAttr("THERMALINSULANCE_ExtraSmall")
'--------------------------------------------------
' Parameter 1 : (String) "THERMALINSULANCE_ExtraSmall"
' Returned value : (Variant) (Long) 1
'--------------------------------------------------

Dim bSTR2865
bSTR2865 = ""
Dim bSTR2866
bSTR2866 = ""
Dim boolean1433
settingRepository1.GetAttrInfo "THERMALINSULANCE_ExtraSmall", bSTR2865, bSTR2866, boolean1433
'--------------------------------------------------
' Parameter 1 : (String) "THERMALINSULANCE_ExtraSmall"
' Parameter 2 : (String) "Default value"
' Parameter 3 : (String) "Unlocked"
' Parameter 4 : (Boolean) False
'--------------------------------------------------

long1434 = settingRepository1.GetAttr("THERMALINSULANCE_Nanometric")
'--------------------------------------------------
' Parameter 1 : (String) "THERMALINSULANCE_Nanometric"
' Returned value : (Variant) (Long) 1
'--------------------------------------------------

Dim bSTR2867
bSTR2867 = ""
Dim bSTR2868
bSTR2868 = ""
Dim boolean1434
settingRepository1.GetAttrInfo "THERMALINSULANCE_Nanometric", bSTR2867, bSTR2868, boolean1434
'--------------------------------------------------
' Parameter 1 : (String) "THERMALINSULANCE_Nanometric"
' Parameter 2 : (String) "Default value"
' Parameter 3 : (String) "Unlocked"
' Parameter 4 : (Boolean) False
'--------------------------------------------------

long1435 = settingRepository1.GetAttr("THERMALRESISTANCE")
'--------------------------------------------------
' Parameter 1 : (String) "THERMALRESISTANCE"
' Returned value : (Variant) (Long) 1
'--------------------------------------------------

Dim bSTR2869
bSTR2869 = ""
Dim bSTR2870
bSTR2870 = ""
Dim boolean1435
settingRepository1.GetAttrInfo "THERMALRESISTANCE", bSTR2869, bSTR2870, boolean1435
'--------------------------------------------------
' Parameter 1 : (String) "THERMALRESISTANCE"
' Parameter 2 : (String) "Default value"
' Parameter 3 : (String) "Unlocked"
' Parameter 4 : (Boolean) False
'--------------------------------------------------

long1436 = settingRepository1.GetAttr("THERMALRESISTANCE_Large")
'--------------------------------------------------
' Parameter 1 : (String) "THERMALRESISTANCE_Large"
' Returned value : (Variant) (Long) 1
'--------------------------------------------------

Dim bSTR2871
bSTR2871 = ""
Dim bSTR2872
bSTR2872 = ""
Dim boolean1436
settingRepository1.GetAttrInfo "THERMALRESISTANCE_Large", bSTR2871, bSTR2872, boolean1436
'--------------------------------------------------
' Parameter 1 : (String) "THERMALRESISTANCE_Large"
' Parameter 2 : (String) "Default value"
' Parameter 3 : (String) "Unlocked"
' Parameter 4 : (Boolean) False
'--------------------------------------------------

long1437 = settingRepository1.GetAttr("THERMALRESISTANCE_ExtraLarge")
'--------------------------------------------------
' Parameter 1 : (String) "THERMALRESISTANCE_ExtraLarge"
' Returned value : (Variant) (Long) 1
'--------------------------------------------------

Dim bSTR2873
bSTR2873 = ""
Dim bSTR2874
bSTR2874 = ""
Dim boolean1437
settingRepository1.GetAttrInfo "THERMALRESISTANCE_ExtraLarge", bSTR2873, bSTR2874, boolean1437
'--------------------------------------------------
' Parameter 1 : (String) "THERMALRESISTANCE_ExtraLarge"
' Parameter 2 : (String) "Default value"
' Parameter 3 : (String) "Unlocked"
' Parameter 4 : (Boolean) False
'--------------------------------------------------

long1438 = settingRepository1.GetAttr("THERMALRESISTANCE_Small")
'--------------------------------------------------
' Parameter 1 : (String) "THERMALRESISTANCE_Small"
' Returned value : (Variant) (Long) 1
'--------------------------------------------------

Dim bSTR2875
bSTR2875 = ""
Dim bSTR2876
bSTR2876 = ""
Dim boolean1438
settingRepository1.GetAttrInfo "THERMALRESISTANCE_Small", bSTR2875, bSTR2876, boolean1438
'--------------------------------------------------
' Parameter 1 : (String) "THERMALRESISTANCE_Small"
' Parameter 2 : (String) "Default value"
' Parameter 3 : (String) "Unlocked"
' Parameter 4 : (Boolean) False
'--------------------------------------------------

long1439 = settingRepository1.GetAttr("THERMALRESISTANCE_ExtraSmall")
'--------------------------------------------------
' Parameter 1 : (String) "THERMALRESISTANCE_ExtraSmall"
' Returned value : (Variant) (Long) 1
'--------------------------------------------------

Dim bSTR2877
bSTR2877 = ""
Dim bSTR2878
bSTR2878 = ""
Dim boolean1439
settingRepository1.GetAttrInfo "THERMALRESISTANCE_ExtraSmall", bSTR2877, bSTR2878, boolean1439
'--------------------------------------------------
' Parameter 1 : (String) "THERMALRESISTANCE_ExtraSmall"
' Parameter 2 : (String) "Default value"
' Parameter 3 : (String) "Unlocked"
' Parameter 4 : (Boolean) False
'--------------------------------------------------

long1440 = settingRepository1.GetAttr("THERMALRESISTANCE_Nanometric")
'--------------------------------------------------
' Parameter 1 : (String) "THERMALRESISTANCE_Nanometric"
' Returned value : (Variant) (Long) 1
'--------------------------------------------------

Dim bSTR2879
bSTR2879 = ""
Dim bSTR2880
bSTR2880 = ""
Dim boolean1440
settingRepository1.GetAttrInfo "THERMALRESISTANCE_Nanometric", bSTR2879, bSTR2880, boolean1440
'--------------------------------------------------
' Parameter 1 : (String) "THERMALRESISTANCE_Nanometric"
' Parameter 2 : (String) "Default value"
' Parameter 3 : (String) "Unlocked"
' Parameter 4 : (Boolean) False
'--------------------------------------------------

long1441 = settingRepository1.GetAttr("THERMALCONDUCTANCE")
'--------------------------------------------------
' Parameter 1 : (String) "THERMALCONDUCTANCE"
' Returned value : (Variant) (Long) 1
'--------------------------------------------------

Dim bSTR2881
bSTR2881 = ""
Dim bSTR2882
bSTR2882 = ""
Dim boolean1441
settingRepository1.GetAttrInfo "THERMALCONDUCTANCE", bSTR2881, bSTR2882, boolean1441
'--------------------------------------------------
' Parameter 1 : (String) "THERMALCONDUCTANCE"
' Parameter 2 : (String) "Default value"
' Parameter 3 : (String) "Unlocked"
' Parameter 4 : (Boolean) False
'--------------------------------------------------

long1442 = settingRepository1.GetAttr("THERMALCONDUCTANCE_Large")
'--------------------------------------------------
' Parameter 1 : (String) "THERMALCONDUCTANCE_Large"
' Returned value : (Variant) (Long) 1
'--------------------------------------------------

Dim bSTR2883
bSTR2883 = ""
Dim bSTR2884
bSTR2884 = ""
Dim boolean1442
settingRepository1.GetAttrInfo "THERMALCONDUCTANCE_Large", bSTR2883, bSTR2884, boolean1442
'--------------------------------------------------
' Parameter 1 : (String) "THERMALCONDUCTANCE_Large"
' Parameter 2 : (String) "Default value"
' Parameter 3 : (String) "Unlocked"
' Parameter 4 : (Boolean) False
'--------------------------------------------------

long1443 = settingRepository1.GetAttr("THERMALCONDUCTANCE_ExtraLarge")
'--------------------------------------------------
' Parameter 1 : (String) "THERMALCONDUCTANCE_ExtraLarge"
' Returned value : (Variant) (Long) 1
'--------------------------------------------------

Dim bSTR2885
bSTR2885 = ""
Dim bSTR2886
bSTR2886 = ""
Dim boolean1443
settingRepository1.GetAttrInfo "THERMALCONDUCTANCE_ExtraLarge", bSTR2885, bSTR2886, boolean1443
'--------------------------------------------------
' Parameter 1 : (String) "THERMALCONDUCTANCE_ExtraLarge"
' Parameter 2 : (String) "Default value"
' Parameter 3 : (String) "Unlocked"
' Parameter 4 : (Boolean) False
'--------------------------------------------------

long1444 = settingRepository1.GetAttr("THERMALCONDUCTANCE_Small")
'--------------------------------------------------
' Parameter 1 : (String) "THERMALCONDUCTANCE_Small"
' Returned value : (Variant) (Long) 1
'--------------------------------------------------

Dim bSTR2887
bSTR2887 = ""
Dim bSTR2888
bSTR2888 = ""
Dim boolean1444
settingRepository1.GetAttrInfo "THERMALCONDUCTANCE_Small", bSTR2887, bSTR2888, boolean1444
'--------------------------------------------------
' Parameter 1 : (String) "THERMALCONDUCTANCE_Small"
' Parameter 2 : (String) "Default value"
' Parameter 3 : (String) "Unlocked"
' Parameter 4 : (Boolean) False
'--------------------------------------------------

long1445 = settingRepository1.GetAttr("THERMALCONDUCTANCE_ExtraSmall")
'--------------------------------------------------
' Parameter 1 : (String) "THERMALCONDUCTANCE_ExtraSmall"
' Returned value : (Variant) (Long) 1
'--------------------------------------------------

Dim bSTR2889
bSTR2889 = ""
Dim bSTR2890
bSTR2890 = ""
Dim boolean1445
settingRepository1.GetAttrInfo "THERMALCONDUCTANCE_ExtraSmall", bSTR2889, bSTR2890, boolean1445
'--------------------------------------------------
' Parameter 1 : (String) "THERMALCONDUCTANCE_ExtraSmall"
' Parameter 2 : (String) "Default value"
' Parameter 3 : (String) "Unlocked"
' Parameter 4 : (Boolean) False
'--------------------------------------------------

long1446 = settingRepository1.GetAttr("THERMALCONDUCTANCE_Nanometric")
'--------------------------------------------------
' Parameter 1 : (String) "THERMALCONDUCTANCE_Nanometric"
' Returned value : (Variant) (Long) 1
'--------------------------------------------------

Dim bSTR2891
bSTR2891 = ""
Dim bSTR2892
bSTR2892 = ""
Dim boolean1446
settingRepository1.GetAttrInfo "THERMALCONDUCTANCE_Nanometric", bSTR2891, bSTR2892, boolean1446
'--------------------------------------------------
' Parameter 1 : (String) "THERMALCONDUCTANCE_Nanometric"
' Parameter 2 : (String) "Default value"
' Parameter 3 : (String) "Unlocked"
' Parameter 4 : (Boolean) False
'--------------------------------------------------

long1447 = settingRepository1.GetAttr("THERMALDIFFUSIVITY")
'--------------------------------------------------
' Parameter 1 : (String) "THERMALDIFFUSIVITY"
' Returned value : (Variant) (Long) 1
'--------------------------------------------------

Dim bSTR2893
bSTR2893 = ""
Dim bSTR2894
bSTR2894 = ""
Dim boolean1447
settingRepository1.GetAttrInfo "THERMALDIFFUSIVITY", bSTR2893, bSTR2894, boolean1447
'--------------------------------------------------
' Parameter 1 : (String) "THERMALDIFFUSIVITY"
' Parameter 2 : (String) "Default value"
' Parameter 3 : (String) "Unlocked"
' Parameter 4 : (Boolean) False
'--------------------------------------------------

long1448 = settingRepository1.GetAttr("THERMALDIFFUSIVITY_Large")
'--------------------------------------------------
' Parameter 1 : (String) "THERMALDIFFUSIVITY_Large"
' Returned value : (Variant) (Long) 1
'--------------------------------------------------

Dim bSTR2895
bSTR2895 = ""
Dim bSTR2896
bSTR2896 = ""
Dim boolean1448
settingRepository1.GetAttrInfo "THERMALDIFFUSIVITY_Large", bSTR2895, bSTR2896, boolean1448
'--------------------------------------------------
' Parameter 1 : (String) "THERMALDIFFUSIVITY_Large"
' Parameter 2 : (String) "Default value"
' Parameter 3 : (String) "Unlocked"
' Parameter 4 : (Boolean) False
'--------------------------------------------------

long1449 = settingRepository1.GetAttr("THERMALDIFFUSIVITY_ExtraLarge")
'--------------------------------------------------
' Parameter 1 : (String) "THERMALDIFFUSIVITY_ExtraLarge"
' Returned value : (Variant) (Long) 1
'--------------------------------------------------

Dim bSTR2897
bSTR2897 = ""
Dim bSTR2898
bSTR2898 = ""
Dim boolean1449
settingRepository1.GetAttrInfo "THERMALDIFFUSIVITY_ExtraLarge", bSTR2897, bSTR2898, boolean1449
'--------------------------------------------------
' Parameter 1 : (String) "THERMALDIFFUSIVITY_ExtraLarge"
' Parameter 2 : (String) "Default value"
' Parameter 3 : (String) "Unlocked"
' Parameter 4 : (Boolean) False
'--------------------------------------------------

long1450 = settingRepository1.GetAttr("THERMALDIFFUSIVITY_Small")
'--------------------------------------------------
' Parameter 1 : (String) "THERMALDIFFUSIVITY_Small"
' Returned value : (Variant) (Long) 1
'--------------------------------------------------

Dim bSTR2899
bSTR2899 = ""
Dim bSTR2900
bSTR2900 = ""
Dim boolean1450
settingRepository1.GetAttrInfo "THERMALDIFFUSIVITY_Small", bSTR2899, bSTR2900, boolean1450
'--------------------------------------------------
' Parameter 1 : (String) "THERMALDIFFUSIVITY_Small"
' Parameter 2 : (String) "Default value"
' Parameter 3 : (String) "Unlocked"
' Parameter 4 : (Boolean) False
'--------------------------------------------------

long1451 = settingRepository1.GetAttr("THERMALDIFFUSIVITY_ExtraSmall")
'--------------------------------------------------
' Parameter 1 : (String) "THERMALDIFFUSIVITY_ExtraSmall"
' Returned value : (Variant) (Long) 1
'--------------------------------------------------

Dim bSTR2901
bSTR2901 = ""
Dim bSTR2902
bSTR2902 = ""
Dim boolean1451
settingRepository1.GetAttrInfo "THERMALDIFFUSIVITY_ExtraSmall", bSTR2901, bSTR2902, boolean1451
'--------------------------------------------------
' Parameter 1 : (String) "THERMALDIFFUSIVITY_ExtraSmall"
' Parameter 2 : (String) "Default value"
' Parameter 3 : (String) "Unlocked"
' Parameter 4 : (Boolean) False
'--------------------------------------------------

long1452 = settingRepository1.GetAttr("THERMALDIFFUSIVITY_Nanometric")
'--------------------------------------------------
' Parameter 1 : (String) "THERMALDIFFUSIVITY_Nanometric"
' Returned value : (Variant) (Long) 1
'--------------------------------------------------

Dim bSTR2903
bSTR2903 = ""
Dim bSTR2904
bSTR2904 = ""
Dim boolean1452
settingRepository1.GetAttrInfo "THERMALDIFFUSIVITY_Nanometric", bSTR2903, bSTR2904, boolean1452
'--------------------------------------------------
' Parameter 1 : (String) "THERMALDIFFUSIVITY_Nanometric"
' Parameter 2 : (String) "Default value"
' Parameter 3 : (String) "Unlocked"
' Parameter 4 : (Boolean) False
'--------------------------------------------------

long1453 = settingRepository1.GetAttr("HEATCAPACITY_SI")
'--------------------------------------------------
' Parameter 1 : (String) "HEATCAPACITY_SI"
' Returned value : (Variant) (Long) 1
'--------------------------------------------------

Dim bSTR2905
bSTR2905 = ""
Dim bSTR2906
bSTR2906 = ""
Dim boolean1453
settingRepository1.GetAttrInfo "HEATCAPACITY_SI", bSTR2905, bSTR2906, boolean1453
'--------------------------------------------------
' Parameter 1 : (String) "HEATCAPACITY_SI"
' Parameter 2 : (String) "Default value"
' Parameter 3 : (String) "Unlocked"
' Parameter 4 : (Boolean) False
'--------------------------------------------------

long1454 = settingRepository1.GetAttr("HEATCAPACITY_SI_Large")
'--------------------------------------------------
' Parameter 1 : (String) "HEATCAPACITY_SI_Large"
' Returned value : (Variant) (Long) 1
'--------------------------------------------------

Dim bSTR2907
bSTR2907 = ""
Dim bSTR2908
bSTR2908 = ""
Dim boolean1454
settingRepository1.GetAttrInfo "HEATCAPACITY_SI_Large", bSTR2907, bSTR2908, boolean1454
'--------------------------------------------------
' Parameter 1 : (String) "HEATCAPACITY_SI_Large"
' Parameter 2 : (String) "Default value"
' Parameter 3 : (String) "Unlocked"
' Parameter 4 : (Boolean) False
'--------------------------------------------------

long1455 = settingRepository1.GetAttr("HEATCAPACITY_SI_ExtraLarge")
'--------------------------------------------------
' Parameter 1 : (String) "HEATCAPACITY_SI_ExtraLarge"
' Returned value : (Variant) (Long) 1
'--------------------------------------------------

Dim bSTR2909
bSTR2909 = ""
Dim bSTR2910
bSTR2910 = ""
Dim boolean1455
settingRepository1.GetAttrInfo "HEATCAPACITY_SI_ExtraLarge", bSTR2909, bSTR2910, boolean1455
'--------------------------------------------------
' Parameter 1 : (String) "HEATCAPACITY_SI_ExtraLarge"
' Parameter 2 : (String) "Default value"
' Parameter 3 : (String) "Unlocked"
' Parameter 4 : (Boolean) False
'--------------------------------------------------

long1456 = settingRepository1.GetAttr("HEATCAPACITY_SI_Small")
'--------------------------------------------------
' Parameter 1 : (String) "HEATCAPACITY_SI_Small"
' Returned value : (Variant) (Long) 1
'--------------------------------------------------

Dim bSTR2911
bSTR2911 = ""
Dim bSTR2912
bSTR2912 = ""
Dim boolean1456
settingRepository1.GetAttrInfo "HEATCAPACITY_SI_Small", bSTR2911, bSTR2912, boolean1456
'--------------------------------------------------
' Parameter 1 : (String) "HEATCAPACITY_SI_Small"
' Parameter 2 : (String) "Default value"
' Parameter 3 : (String) "Unlocked"
' Parameter 4 : (Boolean) False
'--------------------------------------------------

long1457 = settingRepository1.GetAttr("HEATCAPACITY_SI_ExtraSmall")
'--------------------------------------------------
' Parameter 1 : (String) "HEATCAPACITY_SI_ExtraSmall"
' Returned value : (Variant) (Long) 1
'--------------------------------------------------

Dim bSTR2913
bSTR2913 = ""
Dim bSTR2914
bSTR2914 = ""
Dim boolean1457
settingRepository1.GetAttrInfo "HEATCAPACITY_SI_ExtraSmall", bSTR2913, bSTR2914, boolean1457
'--------------------------------------------------
' Parameter 1 : (String) "HEATCAPACITY_SI_ExtraSmall"
' Parameter 2 : (String) "Default value"
' Parameter 3 : (String) "Unlocked"
' Parameter 4 : (Boolean) False
'--------------------------------------------------

long1458 = settingRepository1.GetAttr("HEATCAPACITY_SI_Nanometric")
'--------------------------------------------------
' Parameter 1 : (String) "HEATCAPACITY_SI_Nanometric"
' Returned value : (Variant) (Long) 1
'--------------------------------------------------

Dim bSTR2915
bSTR2915 = ""
Dim bSTR2916
bSTR2916 = ""
Dim boolean1458
settingRepository1.GetAttrInfo "HEATCAPACITY_SI_Nanometric", bSTR2915, bSTR2916, boolean1458
'--------------------------------------------------
' Parameter 1 : (String) "HEATCAPACITY_SI_Nanometric"
' Parameter 2 : (String) "Default value"
' Parameter 3 : (String) "Unlocked"
' Parameter 4 : (Boolean) False
'--------------------------------------------------

long1459 = settingRepository1.GetAttr("ENTROPY_SI")
'--------------------------------------------------
' Parameter 1 : (String) "ENTROPY_SI"
' Returned value : (Variant) (Long) 1
'--------------------------------------------------

Dim bSTR2917
bSTR2917 = ""
Dim bSTR2918
bSTR2918 = ""
Dim boolean1459
settingRepository1.GetAttrInfo "ENTROPY_SI", bSTR2917, bSTR2918, boolean1459
'--------------------------------------------------
' Parameter 1 : (String) "ENTROPY_SI"
' Parameter 2 : (String) "Default value"
' Parameter 3 : (String) "Unlocked"
' Parameter 4 : (Boolean) False
'--------------------------------------------------

long1460 = settingRepository1.GetAttr("ENTROPY_SI_Large")
'--------------------------------------------------
' Parameter 1 : (String) "ENTROPY_SI_Large"
' Returned value : (Variant) (Long) 1
'--------------------------------------------------

Dim bSTR2919
bSTR2919 = ""
Dim bSTR2920
bSTR2920 = ""
Dim boolean1460
settingRepository1.GetAttrInfo "ENTROPY_SI_Large", bSTR2919, bSTR2920, boolean1460
'--------------------------------------------------
' Parameter 1 : (String) "ENTROPY_SI_Large"
' Parameter 2 : (String) "Default value"
' Parameter 3 : (String) "Unlocked"
' Parameter 4 : (Boolean) False
'--------------------------------------------------

long1461 = settingRepository1.GetAttr("ENTROPY_SI_ExtraLarge")
'--------------------------------------------------
' Parameter 1 : (String) "ENTROPY_SI_ExtraLarge"
' Returned value : (Variant) (Long) 1
'--------------------------------------------------

Dim bSTR2921
bSTR2921 = ""
Dim bSTR2922
bSTR2922 = ""
Dim boolean1461
settingRepository1.GetAttrInfo "ENTROPY_SI_ExtraLarge", bSTR2921, bSTR2922, boolean1461
'--------------------------------------------------
' Parameter 1 : (String) "ENTROPY_SI_ExtraLarge"
' Parameter 2 : (String) "Default value"
' Parameter 3 : (String) "Unlocked"
' Parameter 4 : (Boolean) False
'--------------------------------------------------

long1462 = settingRepository1.GetAttr("ENTROPY_SI_Small")
'--------------------------------------------------
' Parameter 1 : (String) "ENTROPY_SI_Small"
' Returned value : (Variant) (Long) 1
'--------------------------------------------------

Dim bSTR2923
bSTR2923 = ""
Dim bSTR2924
bSTR2924 = ""
Dim boolean1462
settingRepository1.GetAttrInfo "ENTROPY_SI_Small", bSTR2923, bSTR2924, boolean1462
'--------------------------------------------------
' Parameter 1 : (String) "ENTROPY_SI_Small"
' Parameter 2 : (String) "Default value"
' Parameter 3 : (String) "Unlocked"
' Parameter 4 : (Boolean) False
'--------------------------------------------------

long1463 = settingRepository1.GetAttr("ENTROPY_SI_ExtraSmall")
'--------------------------------------------------
' Parameter 1 : (String) "ENTROPY_SI_ExtraSmall"
' Returned value : (Variant) (Long) 1
'--------------------------------------------------

Dim bSTR2925
bSTR2925 = ""
Dim bSTR2926
bSTR2926 = ""
Dim boolean1463
settingRepository1.GetAttrInfo "ENTROPY_SI_ExtraSmall", bSTR2925, bSTR2926, boolean1463
'--------------------------------------------------
' Parameter 1 : (String) "ENTROPY_SI_ExtraSmall"
' Parameter 2 : (String) "Default value"
' Parameter 3 : (String) "Unlocked"
' Parameter 4 : (Boolean) False
'--------------------------------------------------

long1464 = settingRepository1.GetAttr("ENTROPY_SI_Nanometric")
'--------------------------------------------------
' Parameter 1 : (String) "ENTROPY_SI_Nanometric"
' Returned value : (Variant) (Long) 1
'--------------------------------------------------

Dim bSTR2927
bSTR2927 = ""
Dim bSTR2928
bSTR2928 = ""
Dim boolean1464
settingRepository1.GetAttrInfo "ENTROPY_SI_Nanometric", bSTR2927, bSTR2928, boolean1464
'--------------------------------------------------
' Parameter 1 : (String) "ENTROPY_SI_Nanometric"
' Parameter 2 : (String) "Default value"
' Parameter 3 : (String) "Unlocked"
' Parameter 4 : (Boolean) False
'--------------------------------------------------

long1465 = settingRepository1.GetAttr("ENTROPYFLOWRATE")
'--------------------------------------------------
' Parameter 1 : (String) "ENTROPYFLOWRATE"
' Returned value : (Variant) (Long) 1
'--------------------------------------------------

Dim bSTR2929
bSTR2929 = ""
Dim bSTR2930
bSTR2930 = ""
Dim boolean1465
settingRepository1.GetAttrInfo "ENTROPYFLOWRATE", bSTR2929, bSTR2930, boolean1465
'--------------------------------------------------
' Parameter 1 : (String) "ENTROPYFLOWRATE"
' Parameter 2 : (String) "Default value"
' Parameter 3 : (String) "Unlocked"
' Parameter 4 : (Boolean) False
'--------------------------------------------------

long1466 = settingRepository1.GetAttr("ENTROPYFLOWRATE_Large")
'--------------------------------------------------
' Parameter 1 : (String) "ENTROPYFLOWRATE_Large"
' Returned value : (Variant) (Long) 1
'--------------------------------------------------

Dim bSTR2931
bSTR2931 = ""
Dim bSTR2932
bSTR2932 = ""
Dim boolean1466
settingRepository1.GetAttrInfo "ENTROPYFLOWRATE_Large", bSTR2931, bSTR2932, boolean1466
'--------------------------------------------------
' Parameter 1 : (String) "ENTROPYFLOWRATE_Large"
' Parameter 2 : (String) "Default value"
' Parameter 3 : (String) "Unlocked"
' Parameter 4 : (Boolean) False
'--------------------------------------------------

long1467 = settingRepository1.GetAttr("ENTROPYFLOWRATE_ExtraLarge")
'--------------------------------------------------
' Parameter 1 : (String) "ENTROPYFLOWRATE_ExtraLarge"
' Returned value : (Variant) (Long) 1
'--------------------------------------------------

Dim bSTR2933
bSTR2933 = ""
Dim bSTR2934
bSTR2934 = ""
Dim boolean1467
settingRepository1.GetAttrInfo "ENTROPYFLOWRATE_ExtraLarge", bSTR2933, bSTR2934, boolean1467
'--------------------------------------------------
' Parameter 1 : (String) "ENTROPYFLOWRATE_ExtraLarge"
' Parameter 2 : (String) "Default value"
' Parameter 3 : (String) "Unlocked"
' Parameter 4 : (Boolean) False
'--------------------------------------------------

long1468 = settingRepository1.GetAttr("ENTROPYFLOWRATE_Small")
'--------------------------------------------------
' Parameter 1 : (String) "ENTROPYFLOWRATE_Small"
' Returned value : (Variant) (Long) 1
'--------------------------------------------------

Dim bSTR2935
bSTR2935 = ""
Dim bSTR2936
bSTR2936 = ""
Dim boolean1468
settingRepository1.GetAttrInfo "ENTROPYFLOWRATE_Small", bSTR2935, bSTR2936, boolean1468
'--------------------------------------------------
' Parameter 1 : (String) "ENTROPYFLOWRATE_Small"
' Parameter 2 : (String) "Default value"
' Parameter 3 : (String) "Unlocked"
' Parameter 4 : (Boolean) False
'--------------------------------------------------

long1469 = settingRepository1.GetAttr("ENTROPYFLOWRATE_ExtraSmall")
'--------------------------------------------------
' Parameter 1 : (String) "ENTROPYFLOWRATE_ExtraSmall"
' Returned value : (Variant) (Long) 1
'--------------------------------------------------

Dim bSTR2937
bSTR2937 = ""
Dim bSTR2938
bSTR2938 = ""
Dim boolean1469
settingRepository1.GetAttrInfo "ENTROPYFLOWRATE_ExtraSmall", bSTR2937, bSTR2938, boolean1469
'--------------------------------------------------
' Parameter 1 : (String) "ENTROPYFLOWRATE_ExtraSmall"
' Parameter 2 : (String) "Default value"
' Parameter 3 : (String) "Unlocked"
' Parameter 4 : (Boolean) False
'--------------------------------------------------

long1470 = settingRepository1.GetAttr("ENTROPYFLOWRATE_Nanometric")
'--------------------------------------------------
' Parameter 1 : (String) "ENTROPYFLOWRATE_Nanometric"
' Returned value : (Variant) (Long) 1
'--------------------------------------------------

Dim bSTR2939
bSTR2939 = ""
Dim bSTR2940
bSTR2940 = ""
Dim boolean1470
settingRepository1.GetAttrInfo "ENTROPYFLOWRATE_Nanometric", bSTR2939, bSTR2940, boolean1470
'--------------------------------------------------
' Parameter 1 : (String) "ENTROPYFLOWRATE_Nanometric"
' Parameter 2 : (String) "Default value"
' Parameter 3 : (String) "Unlocked"
' Parameter 4 : (Boolean) False
'--------------------------------------------------

long1471 = settingRepository1.GetAttr("SPECIFICENERGY")
'--------------------------------------------------
' Parameter 1 : (String) "SPECIFICENERGY"
' Returned value : (Variant) (Long) 1
'--------------------------------------------------

Dim bSTR2941
bSTR2941 = ""
Dim bSTR2942
bSTR2942 = ""
Dim boolean1471
settingRepository1.GetAttrInfo "SPECIFICENERGY", bSTR2941, bSTR2942, boolean1471
'--------------------------------------------------
' Parameter 1 : (String) "SPECIFICENERGY"
' Parameter 2 : (String) "Default value"
' Parameter 3 : (String) "Unlocked"
' Parameter 4 : (Boolean) False
'--------------------------------------------------

long1472 = settingRepository1.GetAttr("SPECIFICENERGY_Large")
'--------------------------------------------------
' Parameter 1 : (String) "SPECIFICENERGY_Large"
' Returned value : (Variant) (Long) 1
'--------------------------------------------------

Dim bSTR2943
bSTR2943 = ""
Dim bSTR2944
bSTR2944 = ""
Dim boolean1472
settingRepository1.GetAttrInfo "SPECIFICENERGY_Large", bSTR2943, bSTR2944, boolean1472
'--------------------------------------------------
' Parameter 1 : (String) "SPECIFICENERGY_Large"
' Parameter 2 : (String) "Default value"
' Parameter 3 : (String) "Unlocked"
' Parameter 4 : (Boolean) False
'--------------------------------------------------

long1473 = settingRepository1.GetAttr("SPECIFICENERGY_ExtraLarge")
'--------------------------------------------------
' Parameter 1 : (String) "SPECIFICENERGY_ExtraLarge"
' Returned value : (Variant) (Long) 1
'--------------------------------------------------

Dim bSTR2945
bSTR2945 = ""
Dim bSTR2946
bSTR2946 = ""
Dim boolean1473
settingRepository1.GetAttrInfo "SPECIFICENERGY_ExtraLarge", bSTR2945, bSTR2946, boolean1473
'--------------------------------------------------
' Parameter 1 : (String) "SPECIFICENERGY_ExtraLarge"
' Parameter 2 : (String) "Default value"
' Parameter 3 : (String) "Unlocked"
' Parameter 4 : (Boolean) False
'--------------------------------------------------

long1474 = settingRepository1.GetAttr("SPECIFICENERGY_Small")
'--------------------------------------------------
' Parameter 1 : (String) "SPECIFICENERGY_Small"
' Returned value : (Variant) (Long) 1
'--------------------------------------------------

Dim bSTR2947
bSTR2947 = ""
Dim bSTR2948
bSTR2948 = ""
Dim boolean1474
settingRepository1.GetAttrInfo "SPECIFICENERGY_Small", bSTR2947, bSTR2948, boolean1474
'--------------------------------------------------
' Parameter 1 : (String) "SPECIFICENERGY_Small"
' Parameter 2 : (String) "Default value"
' Parameter 3 : (String) "Unlocked"
' Parameter 4 : (Boolean) False
'--------------------------------------------------

long1475 = settingRepository1.GetAttr("SPECIFICENERGY_ExtraSmall")
'--------------------------------------------------
' Parameter 1 : (String) "SPECIFICENERGY_ExtraSmall"
' Returned value : (Variant) (Long) 1
'--------------------------------------------------

Dim bSTR2949
bSTR2949 = ""
Dim bSTR2950
bSTR2950 = ""
Dim boolean1475
settingRepository1.GetAttrInfo "SPECIFICENERGY_ExtraSmall", bSTR2949, bSTR2950, boolean1475
'--------------------------------------------------
' Parameter 1 : (String) "SPECIFICENERGY_ExtraSmall"
' Parameter 2 : (String) "Default value"
' Parameter 3 : (String) "Unlocked"
' Parameter 4 : (Boolean) False
'--------------------------------------------------

long1476 = settingRepository1.GetAttr("SPECIFICENERGY_Nanometric")
'--------------------------------------------------
' Parameter 1 : (String) "SPECIFICENERGY_Nanometric"
' Returned value : (Variant) (Long) 1
'--------------------------------------------------

Dim bSTR2951
bSTR2951 = ""
Dim bSTR2952
bSTR2952 = ""
Dim boolean1476
settingRepository1.GetAttrInfo "SPECIFICENERGY_Nanometric", bSTR2951, bSTR2952, boolean1476
'--------------------------------------------------
' Parameter 1 : (String) "SPECIFICENERGY_Nanometric"
' Parameter 2 : (String) "Default value"
' Parameter 3 : (String) "Unlocked"
' Parameter 4 : (Boolean) False
'--------------------------------------------------

long1477 = settingRepository1.GetAttr("DERDENSITYBYENTHALPY")
'--------------------------------------------------
' Parameter 1 : (String) "DERDENSITYBYENTHALPY"
' Returned value : (Variant) (Long) 1
'--------------------------------------------------

Dim bSTR2953
bSTR2953 = ""
Dim bSTR2954
bSTR2954 = ""
Dim boolean1477
settingRepository1.GetAttrInfo "DERDENSITYBYENTHALPY", bSTR2953, bSTR2954, boolean1477
'--------------------------------------------------
' Parameter 1 : (String) "DERDENSITYBYENTHALPY"
' Parameter 2 : (String) "Default value"
' Parameter 3 : (String) "Unlocked"
' Parameter 4 : (Boolean) False
'--------------------------------------------------

long1478 = settingRepository1.GetAttr("DERDENSITYBYENTHALPY_Large")
'--------------------------------------------------
' Parameter 1 : (String) "DERDENSITYBYENTHALPY_Large"
' Returned value : (Variant) (Long) 1
'--------------------------------------------------

Dim bSTR2955
bSTR2955 = ""
Dim bSTR2956
bSTR2956 = ""
Dim boolean1478
settingRepository1.GetAttrInfo "DERDENSITYBYENTHALPY_Large", bSTR2955, bSTR2956, boolean1478
'--------------------------------------------------
' Parameter 1 : (String) "DERDENSITYBYENTHALPY_Large"
' Parameter 2 : (String) "Default value"
' Parameter 3 : (String) "Unlocked"
' Parameter 4 : (Boolean) False
'--------------------------------------------------

long1479 = settingRepository1.GetAttr("DERDENSITYBYENTHALPY_ExtraLarge")
'--------------------------------------------------
' Parameter 1 : (String) "DERDENSITYBYENTHALPY_ExtraLarge"
' Returned value : (Variant) (Long) 1
'--------------------------------------------------

Dim bSTR2957
bSTR2957 = ""
Dim bSTR2958
bSTR2958 = ""
Dim boolean1479
settingRepository1.GetAttrInfo "DERDENSITYBYENTHALPY_ExtraLarge", bSTR2957, bSTR2958, boolean1479
'--------------------------------------------------
' Parameter 1 : (String) "DERDENSITYBYENTHALPY_ExtraLarge"
' Parameter 2 : (String) "Default value"
' Parameter 3 : (String) "Unlocked"
' Parameter 4 : (Boolean) False
'--------------------------------------------------

long1480 = settingRepository1.GetAttr("DERDENSITYBYENTHALPY_Small")
'--------------------------------------------------
' Parameter 1 : (String) "DERDENSITYBYENTHALPY_Small"
' Returned value : (Variant) (Long) 1
'--------------------------------------------------

Dim bSTR2959
bSTR2959 = ""
Dim bSTR2960
bSTR2960 = ""
Dim boolean1480
settingRepository1.GetAttrInfo "DERDENSITYBYENTHALPY_Small", bSTR2959, bSTR2960, boolean1480
'--------------------------------------------------
' Parameter 1 : (String) "DERDENSITYBYENTHALPY_Small"
' Parameter 2 : (String) "Default value"
' Parameter 3 : (String) "Unlocked"
' Parameter 4 : (Boolean) False
'--------------------------------------------------

long1481 = settingRepository1.GetAttr("DERDENSITYBYENTHALPY_ExtraSmall")
'--------------------------------------------------
' Parameter 1 : (String) "DERDENSITYBYENTHALPY_ExtraSmall"
' Returned value : (Variant) (Long) 1
'--------------------------------------------------

Dim bSTR2961
bSTR2961 = ""
Dim bSTR2962
bSTR2962 = ""
Dim boolean1481
settingRepository1.GetAttrInfo "DERDENSITYBYENTHALPY_ExtraSmall", bSTR2961, bSTR2962, boolean1481
'--------------------------------------------------
' Parameter 1 : (String) "DERDENSITYBYENTHALPY_ExtraSmall"
' Parameter 2 : (String) "Default value"
' Parameter 3 : (String) "Unlocked"
' Parameter 4 : (Boolean) False
'--------------------------------------------------

long1482 = settingRepository1.GetAttr("DERDENSITYBYENTHALPY_Nanometric")
'--------------------------------------------------
' Parameter 1 : (String) "DERDENSITYBYENTHALPY_Nanometric"
' Returned value : (Variant) (Long) 1
'--------------------------------------------------

Dim bSTR2963
bSTR2963 = ""
Dim bSTR2964
bSTR2964 = ""
Dim boolean1482
settingRepository1.GetAttrInfo "DERDENSITYBYENTHALPY_Nanometric", bSTR2963, bSTR2964, boolean1482
'--------------------------------------------------
' Parameter 1 : (String) "DERDENSITYBYENTHALPY_Nanometric"
' Parameter 2 : (String) "Default value"
' Parameter 3 : (String) "Unlocked"
' Parameter 4 : (Boolean) False
'--------------------------------------------------

long1483 = settingRepository1.GetAttr("DERDENSITYBYPRESSURE")
'--------------------------------------------------
' Parameter 1 : (String) "DERDENSITYBYPRESSURE"
' Returned value : (Variant) (Long) 1
'--------------------------------------------------

Dim bSTR2965
bSTR2965 = ""
Dim bSTR2966
bSTR2966 = ""
Dim boolean1483
settingRepository1.GetAttrInfo "DERDENSITYBYPRESSURE", bSTR2965, bSTR2966, boolean1483
'--------------------------------------------------
' Parameter 1 : (String) "DERDENSITYBYPRESSURE"
' Parameter 2 : (String) "Default value"
' Parameter 3 : (String) "Unlocked"
' Parameter 4 : (Boolean) False
'--------------------------------------------------

long1484 = settingRepository1.GetAttr("DERDENSITYBYPRESSURE_Large")
'--------------------------------------------------
' Parameter 1 : (String) "DERDENSITYBYPRESSURE_Large"
' Returned value : (Variant) (Long) 1
'--------------------------------------------------

Dim bSTR2967
bSTR2967 = ""
Dim bSTR2968
bSTR2968 = ""
Dim boolean1484
settingRepository1.GetAttrInfo "DERDENSITYBYPRESSURE_Large", bSTR2967, bSTR2968, boolean1484
'--------------------------------------------------
' Parameter 1 : (String) "DERDENSITYBYPRESSURE_Large"
' Parameter 2 : (String) "Default value"
' Parameter 3 : (String) "Unlocked"
' Parameter 4 : (Boolean) False
'--------------------------------------------------

long1485 = settingRepository1.GetAttr("DERDENSITYBYPRESSURE_ExtraLarge")
'--------------------------------------------------
' Parameter 1 : (String) "DERDENSITYBYPRESSURE_ExtraLarge"
' Returned value : (Variant) (Long) 1
'--------------------------------------------------

Dim bSTR2969
bSTR2969 = ""
Dim bSTR2970
bSTR2970 = ""
Dim boolean1485
settingRepository1.GetAttrInfo "DERDENSITYBYPRESSURE_ExtraLarge", bSTR2969, bSTR2970, boolean1485
'--------------------------------------------------
' Parameter 1 : (String) "DERDENSITYBYPRESSURE_ExtraLarge"
' Parameter 2 : (String) "Default value"
' Parameter 3 : (String) "Unlocked"
' Parameter 4 : (Boolean) False
'--------------------------------------------------

long1486 = settingRepository1.GetAttr("DERDENSITYBYPRESSURE_Small")
'--------------------------------------------------
' Parameter 1 : (String) "DERDENSITYBYPRESSURE_Small"
' Returned value : (Variant) (Long) 1
'--------------------------------------------------

Dim bSTR2971
bSTR2971 = ""
Dim bSTR2972
bSTR2972 = ""
Dim boolean1486
settingRepository1.GetAttrInfo "DERDENSITYBYPRESSURE_Small", bSTR2971, bSTR2972, boolean1486
'--------------------------------------------------
' Parameter 1 : (String) "DERDENSITYBYPRESSURE_Small"
' Parameter 2 : (String) "Default value"
' Parameter 3 : (String) "Unlocked"
' Parameter 4 : (Boolean) False
'--------------------------------------------------

long1487 = settingRepository1.GetAttr("DERDENSITYBYPRESSURE_ExtraSmall")
'--------------------------------------------------
' Parameter 1 : (String) "DERDENSITYBYPRESSURE_ExtraSmall"
' Returned value : (Variant) (Long) 1
'--------------------------------------------------

Dim bSTR2973
bSTR2973 = ""
Dim bSTR2974
bSTR2974 = ""
Dim boolean1487
settingRepository1.GetAttrInfo "DERDENSITYBYPRESSURE_ExtraSmall", bSTR2973, bSTR2974, boolean1487
'--------------------------------------------------
' Parameter 1 : (String) "DERDENSITYBYPRESSURE_ExtraSmall"
' Parameter 2 : (String) "Default value"
' Parameter 3 : (String) "Unlocked"
' Parameter 4 : (Boolean) False
'--------------------------------------------------

long1488 = settingRepository1.GetAttr("DERDENSITYBYPRESSURE_Nanometric")
'--------------------------------------------------
' Parameter 1 : (String) "DERDENSITYBYPRESSURE_Nanometric"
' Returned value : (Variant) (Long) 1
'--------------------------------------------------

Dim bSTR2975
bSTR2975 = ""
Dim bSTR2976
bSTR2976 = ""
Dim boolean1488
settingRepository1.GetAttrInfo "DERDENSITYBYPRESSURE_Nanometric", bSTR2975, bSTR2976, boolean1488
'--------------------------------------------------
' Parameter 1 : (String) "DERDENSITYBYPRESSURE_Nanometric"
' Parameter 2 : (String) "Default value"
' Parameter 3 : (String) "Unlocked"
' Parameter 4 : (Boolean) False
'--------------------------------------------------

long1489 = settingRepository1.GetAttr("DERDENSITYBYTEMPERATURE")
'--------------------------------------------------
' Parameter 1 : (String) "DERDENSITYBYTEMPERATURE"
' Returned value : (Variant) (Long) 1
'--------------------------------------------------

Dim bSTR2977
bSTR2977 = ""
Dim bSTR2978
bSTR2978 = ""
Dim boolean1489
settingRepository1.GetAttrInfo "DERDENSITYBYTEMPERATURE", bSTR2977, bSTR2978, boolean1489
'--------------------------------------------------
' Parameter 1 : (String) "DERDENSITYBYTEMPERATURE"
' Parameter 2 : (String) "Default value"
' Parameter 3 : (String) "Unlocked"
' Parameter 4 : (Boolean) False
'--------------------------------------------------

long1490 = settingRepository1.GetAttr("DERDENSITYBYTEMPERATURE_Large")
'--------------------------------------------------
' Parameter 1 : (String) "DERDENSITYBYTEMPERATURE_Large"
' Returned value : (Variant) (Long) 1
'--------------------------------------------------

Dim bSTR2979
bSTR2979 = ""
Dim bSTR2980
bSTR2980 = ""
Dim boolean1490
settingRepository1.GetAttrInfo "DERDENSITYBYTEMPERATURE_Large", bSTR2979, bSTR2980, boolean1490
'--------------------------------------------------
' Parameter 1 : (String) "DERDENSITYBYTEMPERATURE_Large"
' Parameter 2 : (String) "Default value"
' Parameter 3 : (String) "Unlocked"
' Parameter 4 : (Boolean) False
'--------------------------------------------------

long1491 = settingRepository1.GetAttr("DERDENSITYBYTEMPERATURE_ExtraLarge")
'--------------------------------------------------
' Parameter 1 : (String) "DERDENSITYBYTEMPERATURE_ExtraLarge"
' Returned value : (Variant) (Long) 1
'--------------------------------------------------

Dim bSTR2981
bSTR2981 = ""
Dim bSTR2982
bSTR2982 = ""
Dim boolean1491
settingRepository1.GetAttrInfo "DERDENSITYBYTEMPERATURE_ExtraLarge", bSTR2981, bSTR2982, boolean1491
'--------------------------------------------------
' Parameter 1 : (String) "DERDENSITYBYTEMPERATURE_ExtraLarge"
' Parameter 2 : (String) "Default value"
' Parameter 3 : (String) "Unlocked"
' Parameter 4 : (Boolean) False
'--------------------------------------------------

long1492 = settingRepository1.GetAttr("DERDENSITYBYTEMPERATURE_Small")
'--------------------------------------------------
' Parameter 1 : (String) "DERDENSITYBYTEMPERATURE_Small"
' Returned value : (Variant) (Long) 1
'--------------------------------------------------

Dim bSTR2983
bSTR2983 = ""
Dim bSTR2984
bSTR2984 = ""
Dim boolean1492
settingRepository1.GetAttrInfo "DERDENSITYBYTEMPERATURE_Small", bSTR2983, bSTR2984, boolean1492
'--------------------------------------------------
' Parameter 1 : (String) "DERDENSITYBYTEMPERATURE_Small"
' Parameter 2 : (String) "Default value"
' Parameter 3 : (String) "Unlocked"
' Parameter 4 : (Boolean) False
'--------------------------------------------------

long1493 = settingRepository1.GetAttr("DERDENSITYBYTEMPERATURE_ExtraSmall")
'--------------------------------------------------
' Parameter 1 : (String) "DERDENSITYBYTEMPERATURE_ExtraSmall"
' Returned value : (Variant) (Long) 1
'--------------------------------------------------

Dim bSTR2985
bSTR2985 = ""
Dim bSTR2986
bSTR2986 = ""
Dim boolean1493
settingRepository1.GetAttrInfo "DERDENSITYBYTEMPERATURE_ExtraSmall", bSTR2985, bSTR2986, boolean1493
'--------------------------------------------------
' Parameter 1 : (String) "DERDENSITYBYTEMPERATURE_ExtraSmall"
' Parameter 2 : (String) "Default value"
' Parameter 3 : (String) "Unlocked"
' Parameter 4 : (Boolean) False
'--------------------------------------------------

long1494 = settingRepository1.GetAttr("DERDENSITYBYTEMPERATURE_Nanometric")
'--------------------------------------------------
' Parameter 1 : (String) "DERDENSITYBYTEMPERATURE_Nanometric"
' Returned value : (Variant) (Long) 1
'--------------------------------------------------

Dim bSTR2987
bSTR2987 = ""
Dim bSTR2988
bSTR2988 = ""
Dim boolean1494
settingRepository1.GetAttrInfo "DERDENSITYBYTEMPERATURE_Nanometric", bSTR2987, bSTR2988, boolean1494
'--------------------------------------------------
' Parameter 1 : (String) "DERDENSITYBYTEMPERATURE_Nanometric"
' Parameter 2 : (String) "Default value"
' Parameter 3 : (String) "Unlocked"
' Parameter 4 : (Boolean) False
'--------------------------------------------------

long1495 = settingRepository1.GetAttr("DERENTHALPYBYPRESSURE")
'--------------------------------------------------
' Parameter 1 : (String) "DERENTHALPYBYPRESSURE"
' Returned value : (Variant) (Long) 1
'--------------------------------------------------

Dim bSTR2989
bSTR2989 = ""
Dim bSTR2990
bSTR2990 = ""
Dim boolean1495
settingRepository1.GetAttrInfo "DERENTHALPYBYPRESSURE", bSTR2989, bSTR2990, boolean1495
'--------------------------------------------------
' Parameter 1 : (String) "DERENTHALPYBYPRESSURE"
' Parameter 2 : (String) "Default value"
' Parameter 3 : (String) "Unlocked"
' Parameter 4 : (Boolean) False
'--------------------------------------------------

long1496 = settingRepository1.GetAttr("DERENTHALPYBYPRESSURE_Large")
'--------------------------------------------------
' Parameter 1 : (String) "DERENTHALPYBYPRESSURE_Large"
' Returned value : (Variant) (Long) 1
'--------------------------------------------------

Dim bSTR2991
bSTR2991 = ""
Dim bSTR2992
bSTR2992 = ""
Dim boolean1496
settingRepository1.GetAttrInfo "DERENTHALPYBYPRESSURE_Large", bSTR2991, bSTR2992, boolean1496
'--------------------------------------------------
' Parameter 1 : (String) "DERENTHALPYBYPRESSURE_Large"
' Parameter 2 : (String) "Default value"
' Parameter 3 : (String) "Unlocked"
' Parameter 4 : (Boolean) False
'--------------------------------------------------

long1497 = settingRepository1.GetAttr("DERENTHALPYBYPRESSURE_ExtraLarge")
'--------------------------------------------------
' Parameter 1 : (String) "DERENTHALPYBYPRESSURE_ExtraLarge"
' Returned value : (Variant) (Long) 1
'--------------------------------------------------

Dim bSTR2993
bSTR2993 = ""
Dim bSTR2994
bSTR2994 = ""
Dim boolean1497
settingRepository1.GetAttrInfo "DERENTHALPYBYPRESSURE_ExtraLarge", bSTR2993, bSTR2994, boolean1497
'--------------------------------------------------
' Parameter 1 : (String) "DERENTHALPYBYPRESSURE_ExtraLarge"
' Parameter 2 : (String) "Default value"
' Parameter 3 : (String) "Unlocked"
' Parameter 4 : (Boolean) False
'--------------------------------------------------

long1498 = settingRepository1.GetAttr("DERENTHALPYBYPRESSURE_Small")
'--------------------------------------------------
' Parameter 1 : (String) "DERENTHALPYBYPRESSURE_Small"
' Returned value : (Variant) (Long) 1
'--------------------------------------------------

Dim bSTR2995
bSTR2995 = ""
Dim bSTR2996
bSTR2996 = ""
Dim boolean1498
settingRepository1.GetAttrInfo "DERENTHALPYBYPRESSURE_Small", bSTR2995, bSTR2996, boolean1498
'--------------------------------------------------
' Parameter 1 : (String) "DERENTHALPYBYPRESSURE_Small"
' Parameter 2 : (String) "Default value"
' Parameter 3 : (String) "Unlocked"
' Parameter 4 : (Boolean) False
'--------------------------------------------------

long1499 = settingRepository1.GetAttr("DERENTHALPYBYPRESSURE_ExtraSmall")
'--------------------------------------------------
' Parameter 1 : (String) "DERENTHALPYBYPRESSURE_ExtraSmall"
' Returned value : (Variant) (Long) 1
'--------------------------------------------------

Dim bSTR2997
bSTR2997 = ""
Dim bSTR2998
bSTR2998 = ""
Dim boolean1499
settingRepository1.GetAttrInfo "DERENTHALPYBYPRESSURE_ExtraSmall", bSTR2997, bSTR2998, boolean1499
'--------------------------------------------------
' Parameter 1 : (String) "DERENTHALPYBYPRESSURE_ExtraSmall"
' Parameter 2 : (String) "Default value"
' Parameter 3 : (String) "Unlocked"
' Parameter 4 : (Boolean) False
'--------------------------------------------------

long1500 = settingRepository1.GetAttr("DERENTHALPYBYPRESSURE_Nanometric")
'--------------------------------------------------
' Parameter 1 : (String) "DERENTHALPYBYPRESSURE_Nanometric"
' Returned value : (Variant) (Long) 1
'--------------------------------------------------

Dim bSTR2999
bSTR2999 = ""
Dim bSTR3000
bSTR3000 = ""
Dim boolean1500
settingRepository1.GetAttrInfo "DERENTHALPYBYPRESSURE_Nanometric", bSTR2999, bSTR3000, boolean1500
'--------------------------------------------------
' Parameter 1 : (String) "DERENTHALPYBYPRESSURE_Nanometric"
' Parameter 2 : (String) "Default value"
' Parameter 3 : (String) "Unlocked"
' Parameter 4 : (Boolean) False
'--------------------------------------------------

long1501 = settingRepository1.GetAttr("DERENERGYBYDENSITY")
'--------------------------------------------------
' Parameter 1 : (String) "DERENERGYBYDENSITY"
' Returned value : (Variant) (Long) 1
'--------------------------------------------------

Dim bSTR3001
bSTR3001 = ""
Dim bSTR3002
bSTR3002 = ""
Dim boolean1501
settingRepository1.GetAttrInfo "DERENERGYBYDENSITY", bSTR3001, bSTR3002, boolean1501
'--------------------------------------------------
' Parameter 1 : (String) "DERENERGYBYDENSITY"
' Parameter 2 : (String) "Default value"
' Parameter 3 : (String) "Unlocked"
' Parameter 4 : (Boolean) False
'--------------------------------------------------

long1502 = settingRepository1.GetAttr("DERENERGYBYDENSITY_Large")
'--------------------------------------------------
' Parameter 1 : (String) "DERENERGYBYDENSITY_Large"
' Returned value : (Variant) (Long) 1
'--------------------------------------------------

Dim bSTR3003
bSTR3003 = ""
Dim bSTR3004
bSTR3004 = ""
Dim boolean1502
settingRepository1.GetAttrInfo "DERENERGYBYDENSITY_Large", bSTR3003, bSTR3004, boolean1502
'--------------------------------------------------
' Parameter 1 : (String) "DERENERGYBYDENSITY_Large"
' Parameter 2 : (String) "Default value"
' Parameter 3 : (String) "Unlocked"
' Parameter 4 : (Boolean) False
'--------------------------------------------------

long1503 = settingRepository1.GetAttr("DERENERGYBYDENSITY_ExtraLarge")
'--------------------------------------------------
' Parameter 1 : (String) "DERENERGYBYDENSITY_ExtraLarge"
' Returned value : (Variant) (Long) 1
'--------------------------------------------------

Dim bSTR3005
bSTR3005 = ""
Dim bSTR3006
bSTR3006 = ""
Dim boolean1503
settingRepository1.GetAttrInfo "DERENERGYBYDENSITY_ExtraLarge", bSTR3005, bSTR3006, boolean1503
'--------------------------------------------------
' Parameter 1 : (String) "DERENERGYBYDENSITY_ExtraLarge"
' Parameter 2 : (String) "Default value"
' Parameter 3 : (String) "Unlocked"
' Parameter 4 : (Boolean) False
'--------------------------------------------------

long1504 = settingRepository1.GetAttr("DERENERGYBYDENSITY_Small")
'--------------------------------------------------
' Parameter 1 : (String) "DERENERGYBYDENSITY_Small"
' Returned value : (Variant) (Long) 1
'--------------------------------------------------

Dim bSTR3007
bSTR3007 = ""
Dim bSTR3008
bSTR3008 = ""
Dim boolean1504
settingRepository1.GetAttrInfo "DERENERGYBYDENSITY_Small", bSTR3007, bSTR3008, boolean1504
'--------------------------------------------------
' Parameter 1 : (String) "DERENERGYBYDENSITY_Small"
' Parameter 2 : (String) "Default value"
' Parameter 3 : (String) "Unlocked"
' Parameter 4 : (Boolean) False
'--------------------------------------------------

long1505 = settingRepository1.GetAttr("DERENERGYBYDENSITY_ExtraSmall")
'--------------------------------------------------
' Parameter 1 : (String) "DERENERGYBYDENSITY_ExtraSmall"
' Returned value : (Variant) (Long) 1
'--------------------------------------------------

Dim bSTR3009
bSTR3009 = ""
Dim bSTR3010
bSTR3010 = ""
Dim boolean1505
settingRepository1.GetAttrInfo "DERENERGYBYDENSITY_ExtraSmall", bSTR3009, bSTR3010, boolean1505
'--------------------------------------------------
' Parameter 1 : (String) "DERENERGYBYDENSITY_ExtraSmall"
' Parameter 2 : (String) "Default value"
' Parameter 3 : (String) "Unlocked"
' Parameter 4 : (Boolean) False
'--------------------------------------------------

long1506 = settingRepository1.GetAttr("DERENERGYBYDENSITY_Nanometric")
'--------------------------------------------------
' Parameter 1 : (String) "DERENERGYBYDENSITY_Nanometric"
' Returned value : (Variant) (Long) 1
'--------------------------------------------------

Dim bSTR3011
bSTR3011 = ""
Dim bSTR3012
bSTR3012 = ""
Dim boolean1506
settingRepository1.GetAttrInfo "DERENERGYBYDENSITY_Nanometric", bSTR3011, bSTR3012, boolean1506
'--------------------------------------------------
' Parameter 1 : (String) "DERENERGYBYDENSITY_Nanometric"
' Parameter 2 : (String) "Default value"
' Parameter 3 : (String) "Unlocked"
' Parameter 4 : (Boolean) False
'--------------------------------------------------

long1507 = settingRepository1.GetAttr("DERENERGYBYPRESSURE")
'--------------------------------------------------
' Parameter 1 : (String) "DERENERGYBYPRESSURE"
' Returned value : (Variant) (Long) 1
'--------------------------------------------------

Dim bSTR3013
bSTR3013 = ""
Dim bSTR3014
bSTR3014 = ""
Dim boolean1507
settingRepository1.GetAttrInfo "DERENERGYBYPRESSURE", bSTR3013, bSTR3014, boolean1507
'--------------------------------------------------
' Parameter 1 : (String) "DERENERGYBYPRESSURE"
' Parameter 2 : (String) "Default value"
' Parameter 3 : (String) "Unlocked"
' Parameter 4 : (Boolean) False
'--------------------------------------------------

long1508 = settingRepository1.GetAttr("DERENERGYBYPRESSURE_Large")
'--------------------------------------------------
' Parameter 1 : (String) "DERENERGYBYPRESSURE_Large"
' Returned value : (Variant) (Long) 1
'--------------------------------------------------

Dim bSTR3015
bSTR3015 = ""
Dim bSTR3016
bSTR3016 = ""
Dim boolean1508
settingRepository1.GetAttrInfo "DERENERGYBYPRESSURE_Large", bSTR3015, bSTR3016, boolean1508
'--------------------------------------------------
' Parameter 1 : (String) "DERENERGYBYPRESSURE_Large"
' Parameter 2 : (String) "Default value"
' Parameter 3 : (String) "Unlocked"
' Parameter 4 : (Boolean) False
'--------------------------------------------------

long1509 = settingRepository1.GetAttr("DERENERGYBYPRESSURE_ExtraLarge")
'--------------------------------------------------
' Parameter 1 : (String) "DERENERGYBYPRESSURE_ExtraLarge"
' Returned value : (Variant) (Long) 1
'--------------------------------------------------

Dim bSTR3017
bSTR3017 = ""
Dim bSTR3018
bSTR3018 = ""
Dim boolean1509
settingRepository1.GetAttrInfo "DERENERGYBYPRESSURE_ExtraLarge", bSTR3017, bSTR3018, boolean1509
'--------------------------------------------------
' Parameter 1 : (String) "DERENERGYBYPRESSURE_ExtraLarge"
' Parameter 2 : (String) "Default value"
' Parameter 3 : (String) "Unlocked"
' Parameter 4 : (Boolean) False
'--------------------------------------------------

long1510 = settingRepository1.GetAttr("DERENERGYBYPRESSURE_Small")
'--------------------------------------------------
' Parameter 1 : (String) "DERENERGYBYPRESSURE_Small"
' Returned value : (Variant) (Long) 1
'--------------------------------------------------

Dim bSTR3019
bSTR3019 = ""
Dim bSTR3020
bSTR3020 = ""
Dim boolean1510
settingRepository1.GetAttrInfo "DERENERGYBYPRESSURE_Small", bSTR3019, bSTR3020, boolean1510
'--------------------------------------------------
' Parameter 1 : (String) "DERENERGYBYPRESSURE_Small"
' Parameter 2 : (String) "Default value"
' Parameter 3 : (String) "Unlocked"
' Parameter 4 : (Boolean) False
'--------------------------------------------------

long1511 = settingRepository1.GetAttr("DERENERGYBYPRESSURE_ExtraSmall")
'--------------------------------------------------
' Parameter 1 : (String) "DERENERGYBYPRESSURE_ExtraSmall"
' Returned value : (Variant) (Long) 1
'--------------------------------------------------

Dim bSTR3021
bSTR3021 = ""
Dim bSTR3022
bSTR3022 = ""
Dim boolean1511
settingRepository1.GetAttrInfo "DERENERGYBYPRESSURE_ExtraSmall", bSTR3021, bSTR3022, boolean1511
'--------------------------------------------------
' Parameter 1 : (String) "DERENERGYBYPRESSURE_ExtraSmall"
' Parameter 2 : (String) "Default value"
' Parameter 3 : (String) "Unlocked"
' Parameter 4 : (Boolean) False
'--------------------------------------------------

long1512 = settingRepository1.GetAttr("DERENERGYBYPRESSURE_Nanometric")
'--------------------------------------------------
' Parameter 1 : (String) "DERENERGYBYPRESSURE_Nanometric"
' Returned value : (Variant) (Long) 1
'--------------------------------------------------

Dim bSTR3023
bSTR3023 = ""
Dim bSTR3024
bSTR3024 = ""
Dim boolean1512
settingRepository1.GetAttrInfo "DERENERGYBYPRESSURE_Nanometric", bSTR3023, bSTR3024, boolean1512
'--------------------------------------------------
' Parameter 1 : (String) "DERENERGYBYPRESSURE_Nanometric"
' Parameter 2 : (String) "Default value"
' Parameter 3 : (String) "Unlocked"
' Parameter 4 : (Boolean) False
'--------------------------------------------------

long1513 = settingRepository1.GetAttr("CURRENTSLOPE")
'--------------------------------------------------
' Parameter 1 : (String) "CURRENTSLOPE"
' Returned value : (Variant) (Long) 1
'--------------------------------------------------

Dim bSTR3025
bSTR3025 = ""
Dim bSTR3026
bSTR3026 = ""
Dim boolean1513
settingRepository1.GetAttrInfo "CURRENTSLOPE", bSTR3025, bSTR3026, boolean1513
'--------------------------------------------------
' Parameter 1 : (String) "CURRENTSLOPE"
' Parameter 2 : (String) "Default value"
' Parameter 3 : (String) "Unlocked"
' Parameter 4 : (Boolean) False
'--------------------------------------------------

long1514 = settingRepository1.GetAttr("CURRENTSLOPE_Large")
'--------------------------------------------------
' Parameter 1 : (String) "CURRENTSLOPE_Large"
' Returned value : (Variant) (Long) 1
'--------------------------------------------------

Dim bSTR3027
bSTR3027 = ""
Dim bSTR3028
bSTR3028 = ""
Dim boolean1514
settingRepository1.GetAttrInfo "CURRENTSLOPE_Large", bSTR3027, bSTR3028, boolean1514
'--------------------------------------------------
' Parameter 1 : (String) "CURRENTSLOPE_Large"
' Parameter 2 : (String) "Default value"
' Parameter 3 : (String) "Unlocked"
' Parameter 4 : (Boolean) False
'--------------------------------------------------

long1515 = settingRepository1.GetAttr("CURRENTSLOPE_ExtraLarge")
'--------------------------------------------------
' Parameter 1 : (String) "CURRENTSLOPE_ExtraLarge"
' Returned value : (Variant) (Long) 1
'--------------------------------------------------

Dim bSTR3029
bSTR3029 = ""
Dim bSTR3030
bSTR3030 = ""
Dim boolean1515
settingRepository1.GetAttrInfo "CURRENTSLOPE_ExtraLarge", bSTR3029, bSTR3030, boolean1515
'--------------------------------------------------
' Parameter 1 : (String) "CURRENTSLOPE_ExtraLarge"
' Parameter 2 : (String) "Default value"
' Parameter 3 : (String) "Unlocked"
' Parameter 4 : (Boolean) False
'--------------------------------------------------

long1516 = settingRepository1.GetAttr("CURRENTSLOPE_Small")
'--------------------------------------------------
' Parameter 1 : (String) "CURRENTSLOPE_Small"
' Returned value : (Variant) (Long) 1
'--------------------------------------------------

Dim bSTR3031
bSTR3031 = ""
Dim bSTR3032
bSTR3032 = ""
Dim boolean1516
settingRepository1.GetAttrInfo "CURRENTSLOPE_Small", bSTR3031, bSTR3032, boolean1516
'--------------------------------------------------
' Parameter 1 : (String) "CURRENTSLOPE_Small"
' Parameter 2 : (String) "Default value"
' Parameter 3 : (String) "Unlocked"
' Parameter 4 : (Boolean) False
'--------------------------------------------------

long1517 = settingRepository1.GetAttr("CURRENTSLOPE_ExtraSmall")
'--------------------------------------------------
' Parameter 1 : (String) "CURRENTSLOPE_ExtraSmall"
' Returned value : (Variant) (Long) 1
'--------------------------------------------------

Dim bSTR3033
bSTR3033 = ""
Dim bSTR3034
bSTR3034 = ""
Dim boolean1517
settingRepository1.GetAttrInfo "CURRENTSLOPE_ExtraSmall", bSTR3033, bSTR3034, boolean1517
'--------------------------------------------------
' Parameter 1 : (String) "CURRENTSLOPE_ExtraSmall"
' Parameter 2 : (String) "Default value"
' Parameter 3 : (String) "Unlocked"
' Parameter 4 : (Boolean) False
'--------------------------------------------------

long1518 = settingRepository1.GetAttr("CURRENTSLOPE_Nanometric")
'--------------------------------------------------
' Parameter 1 : (String) "CURRENTSLOPE_Nanometric"
' Returned value : (Variant) (Long) 1
'--------------------------------------------------

Dim bSTR3035
bSTR3035 = ""
Dim bSTR3036
bSTR3036 = ""
Dim boolean1518
settingRepository1.GetAttrInfo "CURRENTSLOPE_Nanometric", bSTR3035, bSTR3036, boolean1518
'--------------------------------------------------
' Parameter 1 : (String) "CURRENTSLOPE_Nanometric"
' Parameter 2 : (String) "Default value"
' Parameter 3 : (String) "Unlocked"
' Parameter 4 : (Boolean) False
'--------------------------------------------------

long1519 = settingRepository1.GetAttr("ELECTRICCHARGE")
'--------------------------------------------------
' Parameter 1 : (String) "ELECTRICCHARGE"
' Returned value : (Variant) (Long) 1
'--------------------------------------------------

Dim bSTR3037
bSTR3037 = ""
Dim bSTR3038
bSTR3038 = ""
Dim boolean1519
settingRepository1.GetAttrInfo "ELECTRICCHARGE", bSTR3037, bSTR3038, boolean1519
'--------------------------------------------------
' Parameter 1 : (String) "ELECTRICCHARGE"
' Parameter 2 : (String) "Default value"
' Parameter 3 : (String) "Unlocked"
' Parameter 4 : (Boolean) False
'--------------------------------------------------

long1520 = settingRepository1.GetAttr("ELECTRICCHARGE_Large")
'--------------------------------------------------
' Parameter 1 : (String) "ELECTRICCHARGE_Large"
' Returned value : (Variant) (Long) 1
'--------------------------------------------------

Dim bSTR3039
bSTR3039 = ""
Dim bSTR3040
bSTR3040 = ""
Dim boolean1520
settingRepository1.GetAttrInfo "ELECTRICCHARGE_Large", bSTR3039, bSTR3040, boolean1520
'--------------------------------------------------
' Parameter 1 : (String) "ELECTRICCHARGE_Large"
' Parameter 2 : (String) "Default value"
' Parameter 3 : (String) "Unlocked"
' Parameter 4 : (Boolean) False
'--------------------------------------------------

long1521 = settingRepository1.GetAttr("ELECTRICCHARGE_ExtraLarge")
'--------------------------------------------------
' Parameter 1 : (String) "ELECTRICCHARGE_ExtraLarge"
' Returned value : (Variant) (Long) 1
'--------------------------------------------------

Dim bSTR3041
bSTR3041 = ""
Dim bSTR3042
bSTR3042 = ""
Dim boolean1521
settingRepository1.GetAttrInfo "ELECTRICCHARGE_ExtraLarge", bSTR3041, bSTR3042, boolean1521
'--------------------------------------------------
' Parameter 1 : (String) "ELECTRICCHARGE_ExtraLarge"
' Parameter 2 : (String) "Default value"
' Parameter 3 : (String) "Unlocked"
' Parameter 4 : (Boolean) False
'--------------------------------------------------

long1522 = settingRepository1.GetAttr("ELECTRICCHARGE_Small")
'--------------------------------------------------
' Parameter 1 : (String) "ELECTRICCHARGE_Small"
' Returned value : (Variant) (Long) 1
'--------------------------------------------------

Dim bSTR3043
bSTR3043 = ""
Dim bSTR3044
bSTR3044 = ""
Dim boolean1522
settingRepository1.GetAttrInfo "ELECTRICCHARGE_Small", bSTR3043, bSTR3044, boolean1522
'--------------------------------------------------
' Parameter 1 : (String) "ELECTRICCHARGE_Small"
' Parameter 2 : (String) "Default value"
' Parameter 3 : (String) "Unlocked"
' Parameter 4 : (Boolean) False
'--------------------------------------------------

long1523 = settingRepository1.GetAttr("ELECTRICCHARGE_ExtraSmall")
'--------------------------------------------------
' Parameter 1 : (String) "ELECTRICCHARGE_ExtraSmall"
' Returned value : (Variant) (Long) 1
'--------------------------------------------------

Dim bSTR3045
bSTR3045 = ""
Dim bSTR3046
bSTR3046 = ""
Dim boolean1523
settingRepository1.GetAttrInfo "ELECTRICCHARGE_ExtraSmall", bSTR3045, bSTR3046, boolean1523
'--------------------------------------------------
' Parameter 1 : (String) "ELECTRICCHARGE_ExtraSmall"
' Parameter 2 : (String) "Default value"
' Parameter 3 : (String) "Unlocked"
' Parameter 4 : (Boolean) False
'--------------------------------------------------

long1524 = settingRepository1.GetAttr("ELECTRICCHARGE_Nanometric")
'--------------------------------------------------
' Parameter 1 : (String) "ELECTRICCHARGE_Nanometric"
' Returned value : (Variant) (Long) 1
'--------------------------------------------------

Dim bSTR3047
bSTR3047 = ""
Dim bSTR3048
bSTR3048 = ""
Dim boolean1524
settingRepository1.GetAttrInfo "ELECTRICCHARGE_Nanometric", bSTR3047, bSTR3048, boolean1524
'--------------------------------------------------
' Parameter 1 : (String) "ELECTRICCHARGE_Nanometric"
' Parameter 2 : (String) "Default value"
' Parameter 3 : (String) "Unlocked"
' Parameter 4 : (Boolean) False
'--------------------------------------------------

long1525 = settingRepository1.GetAttr("VOLUMEDENSITYOFCHARGE")
'--------------------------------------------------
' Parameter 1 : (String) "VOLUMEDENSITYOFCHARGE"
' Returned value : (Variant) (Long) 1
'--------------------------------------------------

Dim bSTR3049
bSTR3049 = ""
Dim bSTR3050
bSTR3050 = ""
Dim boolean1525
settingRepository1.GetAttrInfo "VOLUMEDENSITYOFCHARGE", bSTR3049, bSTR3050, boolean1525
'--------------------------------------------------
' Parameter 1 : (String) "VOLUMEDENSITYOFCHARGE"
' Parameter 2 : (String) "Default value"
' Parameter 3 : (String) "Unlocked"
' Parameter 4 : (Boolean) False
'--------------------------------------------------

long1526 = settingRepository1.GetAttr("VOLUMEDENSITYOFCHARGE_Large")
'--------------------------------------------------
' Parameter 1 : (String) "VOLUMEDENSITYOFCHARGE_Large"
' Returned value : (Variant) (Long) 1
'--------------------------------------------------

Dim bSTR3051
bSTR3051 = ""
Dim bSTR3052
bSTR3052 = ""
Dim boolean1526
settingRepository1.GetAttrInfo "VOLUMEDENSITYOFCHARGE_Large", bSTR3051, bSTR3052, boolean1526
'--------------------------------------------------
' Parameter 1 : (String) "VOLUMEDENSITYOFCHARGE_Large"
' Parameter 2 : (String) "Default value"
' Parameter 3 : (String) "Unlocked"
' Parameter 4 : (Boolean) False
'--------------------------------------------------

long1527 = settingRepository1.GetAttr("VOLUMEDENSITYOFCHARGE_ExtraLarge")
'--------------------------------------------------
' Parameter 1 : (String) "VOLUMEDENSITYOFCHARGE_ExtraLarge"
' Returned value : (Variant) (Long) 1
'--------------------------------------------------

Dim bSTR3053
bSTR3053 = ""
Dim bSTR3054
bSTR3054 = ""
Dim boolean1527
settingRepository1.GetAttrInfo "VOLUMEDENSITYOFCHARGE_ExtraLarge", bSTR3053, bSTR3054, boolean1527
'--------------------------------------------------
' Parameter 1 : (String) "VOLUMEDENSITYOFCHARGE_ExtraLarge"
' Parameter 2 : (String) "Default value"
' Parameter 3 : (String) "Unlocked"
' Parameter 4 : (Boolean) False
'--------------------------------------------------

long1528 = settingRepository1.GetAttr("VOLUMEDENSITYOFCHARGE_Small")
'--------------------------------------------------
' Parameter 1 : (String) "VOLUMEDENSITYOFCHARGE_Small"
' Returned value : (Variant) (Long) 1
'--------------------------------------------------

Dim bSTR3055
bSTR3055 = ""
Dim bSTR3056
bSTR3056 = ""
Dim boolean1528
settingRepository1.GetAttrInfo "VOLUMEDENSITYOFCHARGE_Small", bSTR3055, bSTR3056, boolean1528
'--------------------------------------------------
' Parameter 1 : (String) "VOLUMEDENSITYOFCHARGE_Small"
' Parameter 2 : (String) "Default value"
' Parameter 3 : (String) "Unlocked"
' Parameter 4 : (Boolean) False
'--------------------------------------------------

long1529 = settingRepository1.GetAttr("VOLUMEDENSITYOFCHARGE_ExtraSmall")
'--------------------------------------------------
' Parameter 1 : (String) "VOLUMEDENSITYOFCHARGE_ExtraSmall"
' Returned value : (Variant) (Long) 1
'--------------------------------------------------

Dim bSTR3057
bSTR3057 = ""
Dim bSTR3058
bSTR3058 = ""
Dim boolean1529
settingRepository1.GetAttrInfo "VOLUMEDENSITYOFCHARGE_ExtraSmall", bSTR3057, bSTR3058, boolean1529
'--------------------------------------------------
' Parameter 1 : (String) "VOLUMEDENSITYOFCHARGE_ExtraSmall"
' Parameter 2 : (String) "Default value"
' Parameter 3 : (String) "Unlocked"
' Parameter 4 : (Boolean) False
'--------------------------------------------------

long1530 = settingRepository1.GetAttr("VOLUMEDENSITYOFCHARGE_Nanometric")
'--------------------------------------------------
' Parameter 1 : (String) "VOLUMEDENSITYOFCHARGE_Nanometric"
' Returned value : (Variant) (Long) 1
'--------------------------------------------------

Dim bSTR3059
bSTR3059 = ""
Dim bSTR3060
bSTR3060 = ""
Dim boolean1530
settingRepository1.GetAttrInfo "VOLUMEDENSITYOFCHARGE_Nanometric", bSTR3059, bSTR3060, boolean1530
'--------------------------------------------------
' Parameter 1 : (String) "VOLUMEDENSITYOFCHARGE_Nanometric"
' Parameter 2 : (String) "Default value"
' Parameter 3 : (String) "Unlocked"
' Parameter 4 : (Boolean) False
'--------------------------------------------------

long1531 = settingRepository1.GetAttr("SURFACEDENSITYOFCHARGE")
'--------------------------------------------------
' Parameter 1 : (String) "SURFACEDENSITYOFCHARGE"
' Returned value : (Variant) (Long) 1
'--------------------------------------------------

Dim bSTR3061
bSTR3061 = ""
Dim bSTR3062
bSTR3062 = ""
Dim boolean1531
settingRepository1.GetAttrInfo "SURFACEDENSITYOFCHARGE", bSTR3061, bSTR3062, boolean1531
'--------------------------------------------------
' Parameter 1 : (String) "SURFACEDENSITYOFCHARGE"
' Parameter 2 : (String) "Default value"
' Parameter 3 : (String) "Unlocked"
' Parameter 4 : (Boolean) False
'--------------------------------------------------

long1532 = settingRepository1.GetAttr("SURFACEDENSITYOFCHARGE_Large")
'--------------------------------------------------
' Parameter 1 : (String) "SURFACEDENSITYOFCHARGE_Large"
' Returned value : (Variant) (Long) 1
'--------------------------------------------------

Dim bSTR3063
bSTR3063 = ""
Dim bSTR3064
bSTR3064 = ""
Dim boolean1532
settingRepository1.GetAttrInfo "SURFACEDENSITYOFCHARGE_Large", bSTR3063, bSTR3064, boolean1532
'--------------------------------------------------
' Parameter 1 : (String) "SURFACEDENSITYOFCHARGE_Large"
' Parameter 2 : (String) "Default value"
' Parameter 3 : (String) "Unlocked"
' Parameter 4 : (Boolean) False
'--------------------------------------------------

long1533 = settingRepository1.GetAttr("SURFACEDENSITYOFCHARGE_ExtraLarge")
'--------------------------------------------------
' Parameter 1 : (String) "SURFACEDENSITYOFCHARGE_ExtraLarge"
' Returned value : (Variant) (Long) 1
'--------------------------------------------------

Dim bSTR3065
bSTR3065 = ""
Dim bSTR3066
bSTR3066 = ""
Dim boolean1533
settingRepository1.GetAttrInfo "SURFACEDENSITYOFCHARGE_ExtraLarge", bSTR3065, bSTR3066, boolean1533
'--------------------------------------------------
' Parameter 1 : (String) "SURFACEDENSITYOFCHARGE_ExtraLarge"
' Parameter 2 : (String) "Default value"
' Parameter 3 : (String) "Unlocked"
' Parameter 4 : (Boolean) False
'--------------------------------------------------

long1534 = settingRepository1.GetAttr("SURFACEDENSITYOFCHARGE_Small")
'--------------------------------------------------
' Parameter 1 : (String) "SURFACEDENSITYOFCHARGE_Small"
' Returned value : (Variant) (Long) 1
'--------------------------------------------------

Dim bSTR3067
bSTR3067 = ""
Dim bSTR3068
bSTR3068 = ""
Dim boolean1534
settingRepository1.GetAttrInfo "SURFACEDENSITYOFCHARGE_Small", bSTR3067, bSTR3068, boolean1534
'--------------------------------------------------
' Parameter 1 : (String) "SURFACEDENSITYOFCHARGE_Small"
' Parameter 2 : (String) "Default value"
' Parameter 3 : (String) "Unlocked"
' Parameter 4 : (Boolean) False
'--------------------------------------------------

long1535 = settingRepository1.GetAttr("SURFACEDENSITYOFCHARGE_ExtraSmall")
'--------------------------------------------------
' Parameter 1 : (String) "SURFACEDENSITYOFCHARGE_ExtraSmall"
' Returned value : (Variant) (Long) 1
'--------------------------------------------------

Dim bSTR3069
bSTR3069 = ""
Dim bSTR3070
bSTR3070 = ""
Dim boolean1535
settingRepository1.GetAttrInfo "SURFACEDENSITYOFCHARGE_ExtraSmall", bSTR3069, bSTR3070, boolean1535
'--------------------------------------------------
' Parameter 1 : (String) "SURFACEDENSITYOFCHARGE_ExtraSmall"
' Parameter 2 : (String) "Default value"
' Parameter 3 : (String) "Unlocked"
' Parameter 4 : (Boolean) False
'--------------------------------------------------

long1536 = settingRepository1.GetAttr("SURFACEDENSITYOFCHARGE_Nanometric")
'--------------------------------------------------
' Parameter 1 : (String) "SURFACEDENSITYOFCHARGE_Nanometric"
' Returned value : (Variant) (Long) 1
'--------------------------------------------------

Dim bSTR3071
bSTR3071 = ""
Dim bSTR3072
bSTR3072 = ""
Dim boolean1536
settingRepository1.GetAttrInfo "SURFACEDENSITYOFCHARGE_Nanometric", bSTR3071, bSTR3072, boolean1536
'--------------------------------------------------
' Parameter 1 : (String) "SURFACEDENSITYOFCHARGE_Nanometric"
' Parameter 2 : (String) "Default value"
' Parameter 3 : (String) "Unlocked"
' Parameter 4 : (Boolean) False
'--------------------------------------------------

long1537 = settingRepository1.GetAttr("ELECTRICFIELDSTRENGTH")
'--------------------------------------------------
' Parameter 1 : (String) "ELECTRICFIELDSTRENGTH"
' Returned value : (Variant) (Long) 1
'--------------------------------------------------

Dim bSTR3073
bSTR3073 = ""
Dim bSTR3074
bSTR3074 = ""
Dim boolean1537
settingRepository1.GetAttrInfo "ELECTRICFIELDSTRENGTH", bSTR3073, bSTR3074, boolean1537
'--------------------------------------------------
' Parameter 1 : (String) "ELECTRICFIELDSTRENGTH"
' Parameter 2 : (String) "Default value"
' Parameter 3 : (String) "Unlocked"
' Parameter 4 : (Boolean) False
'--------------------------------------------------

long1538 = settingRepository1.GetAttr("ELECTRICFIELDSTRENGTH_Large")
'--------------------------------------------------
' Parameter 1 : (String) "ELECTRICFIELDSTRENGTH_Large"
' Returned value : (Variant) (Long) 1
'--------------------------------------------------

Dim bSTR3075
bSTR3075 = ""
Dim bSTR3076
bSTR3076 = ""
Dim boolean1538
settingRepository1.GetAttrInfo "ELECTRICFIELDSTRENGTH_Large", bSTR3075, bSTR3076, boolean1538
'--------------------------------------------------
' Parameter 1 : (String) "ELECTRICFIELDSTRENGTH_Large"
' Parameter 2 : (String) "Default value"
' Parameter 3 : (String) "Unlocked"
' Parameter 4 : (Boolean) False
'--------------------------------------------------

long1539 = settingRepository1.GetAttr("ELECTRICFIELDSTRENGTH_ExtraLarge")
'--------------------------------------------------
' Parameter 1 : (String) "ELECTRICFIELDSTRENGTH_ExtraLarge"
' Returned value : (Variant) (Long) 1
'--------------------------------------------------

Dim bSTR3077
bSTR3077 = ""
Dim bSTR3078
bSTR3078 = ""
Dim boolean1539
settingRepository1.GetAttrInfo "ELECTRICFIELDSTRENGTH_ExtraLarge", bSTR3077, bSTR3078, boolean1539
'--------------------------------------------------
' Parameter 1 : (String) "ELECTRICFIELDSTRENGTH_ExtraLarge"
' Parameter 2 : (String) "Default value"
' Parameter 3 : (String) "Unlocked"
' Parameter 4 : (Boolean) False
'--------------------------------------------------

long1540 = settingRepository1.GetAttr("ELECTRICFIELDSTRENGTH_Small")
'--------------------------------------------------
' Parameter 1 : (String) "ELECTRICFIELDSTRENGTH_Small"
' Returned value : (Variant) (Long) 1
'--------------------------------------------------

Dim bSTR3079
bSTR3079 = ""
Dim bSTR3080
bSTR3080 = ""
Dim boolean1540
settingRepository1.GetAttrInfo "ELECTRICFIELDSTRENGTH_Small", bSTR3079, bSTR3080, boolean1540
'--------------------------------------------------
' Parameter 1 : (String) "ELECTRICFIELDSTRENGTH_Small"
' Parameter 2 : (String) "Default value"
' Parameter 3 : (String) "Unlocked"
' Parameter 4 : (Boolean) False
'--------------------------------------------------

long1541 = settingRepository1.GetAttr("ELECTRICFIELDSTRENGTH_ExtraSmall")
'--------------------------------------------------
' Parameter 1 : (String) "ELECTRICFIELDSTRENGTH_ExtraSmall"
' Returned value : (Variant) (Long) 1
'--------------------------------------------------

Dim bSTR3081
bSTR3081 = ""
Dim bSTR3082
bSTR3082 = ""
Dim boolean1541
settingRepository1.GetAttrInfo "ELECTRICFIELDSTRENGTH_ExtraSmall", bSTR3081, bSTR3082, boolean1541
'--------------------------------------------------
' Parameter 1 : (String) "ELECTRICFIELDSTRENGTH_ExtraSmall"
' Parameter 2 : (String) "Default value"
' Parameter 3 : (String) "Unlocked"
' Parameter 4 : (Boolean) False
'--------------------------------------------------

long1542 = settingRepository1.GetAttr("ELECTRICFIELDSTRENGTH_Nanometric")
'--------------------------------------------------
' Parameter 1 : (String) "ELECTRICFIELDSTRENGTH_Nanometric"
' Returned value : (Variant) (Long) 1
'--------------------------------------------------

Dim bSTR3083
bSTR3083 = ""
Dim bSTR3084
bSTR3084 = ""
Dim boolean1542
settingRepository1.GetAttrInfo "ELECTRICFIELDSTRENGTH_Nanometric", bSTR3083, bSTR3084, boolean1542
'--------------------------------------------------
' Parameter 1 : (String) "ELECTRICFIELDSTRENGTH_Nanometric"
' Parameter 2 : (String) "Default value"
' Parameter 3 : (String) "Unlocked"
' Parameter 4 : (Boolean) False
'--------------------------------------------------

long1543 = settingRepository1.GetAttr("VOLTAGESLOPE")
'--------------------------------------------------
' Parameter 1 : (String) "VOLTAGESLOPE"
' Returned value : (Variant) (Long) 1
'--------------------------------------------------

Dim bSTR3085
bSTR3085 = ""
Dim bSTR3086
bSTR3086 = ""
Dim boolean1543
settingRepository1.GetAttrInfo "VOLTAGESLOPE", bSTR3085, bSTR3086, boolean1543
'--------------------------------------------------
' Parameter 1 : (String) "VOLTAGESLOPE"
' Parameter 2 : (String) "Default value"
' Parameter 3 : (String) "Unlocked"
' Parameter 4 : (Boolean) False
'--------------------------------------------------

long1544 = settingRepository1.GetAttr("VOLTAGESLOPE_Large")
'--------------------------------------------------
' Parameter 1 : (String) "VOLTAGESLOPE_Large"
' Returned value : (Variant) (Long) 1
'--------------------------------------------------

Dim bSTR3087
bSTR3087 = ""
Dim bSTR3088
bSTR3088 = ""
Dim boolean1544
settingRepository1.GetAttrInfo "VOLTAGESLOPE_Large", bSTR3087, bSTR3088, boolean1544
'--------------------------------------------------
' Parameter 1 : (String) "VOLTAGESLOPE_Large"
' Parameter 2 : (String) "Default value"
' Parameter 3 : (String) "Unlocked"
' Parameter 4 : (Boolean) False
'--------------------------------------------------

long1545 = settingRepository1.GetAttr("VOLTAGESLOPE_ExtraLarge")
'--------------------------------------------------
' Parameter 1 : (String) "VOLTAGESLOPE_ExtraLarge"
' Returned value : (Variant) (Long) 1
'--------------------------------------------------

Dim bSTR3089
bSTR3089 = ""
Dim bSTR3090
bSTR3090 = ""
Dim boolean1545
settingRepository1.GetAttrInfo "VOLTAGESLOPE_ExtraLarge", bSTR3089, bSTR3090, boolean1545
'--------------------------------------------------
' Parameter 1 : (String) "VOLTAGESLOPE_ExtraLarge"
' Parameter 2 : (String) "Default value"
' Parameter 3 : (String) "Unlocked"
' Parameter 4 : (Boolean) False
'--------------------------------------------------

long1546 = settingRepository1.GetAttr("VOLTAGESLOPE_Small")
'--------------------------------------------------
' Parameter 1 : (String) "VOLTAGESLOPE_Small"
' Returned value : (Variant) (Long) 1
'--------------------------------------------------

Dim bSTR3091
bSTR3091 = ""
Dim bSTR3092
bSTR3092 = ""
Dim boolean1546
settingRepository1.GetAttrInfo "VOLTAGESLOPE_Small", bSTR3091, bSTR3092, boolean1546
'--------------------------------------------------
' Parameter 1 : (String) "VOLTAGESLOPE_Small"
' Parameter 2 : (String) "Default value"
' Parameter 3 : (String) "Unlocked"
' Parameter 4 : (Boolean) False
'--------------------------------------------------

long1547 = settingRepository1.GetAttr("VOLTAGESLOPE_ExtraSmall")
'--------------------------------------------------
' Parameter 1 : (String) "VOLTAGESLOPE_ExtraSmall"
' Returned value : (Variant) (Long) 1
'--------------------------------------------------

Dim bSTR3093
bSTR3093 = ""
Dim bSTR3094
bSTR3094 = ""
Dim boolean1547
settingRepository1.GetAttrInfo "VOLTAGESLOPE_ExtraSmall", bSTR3093, bSTR3094, boolean1547
'--------------------------------------------------
' Parameter 1 : (String) "VOLTAGESLOPE_ExtraSmall"
' Parameter 2 : (String) "Default value"
' Parameter 3 : (String) "Unlocked"
' Parameter 4 : (Boolean) False
'--------------------------------------------------

long1548 = settingRepository1.GetAttr("VOLTAGESLOPE_Nanometric")
'--------------------------------------------------
' Parameter 1 : (String) "VOLTAGESLOPE_Nanometric"
' Returned value : (Variant) (Long) 1
'--------------------------------------------------

Dim bSTR3095
bSTR3095 = ""
Dim bSTR3096
bSTR3096 = ""
Dim boolean1548
settingRepository1.GetAttrInfo "VOLTAGESLOPE_Nanometric", bSTR3095, bSTR3096, boolean1548
'--------------------------------------------------
' Parameter 1 : (String) "VOLTAGESLOPE_Nanometric"
' Parameter 2 : (String) "Default value"
' Parameter 3 : (String) "Unlocked"
' Parameter 4 : (Boolean) False
'--------------------------------------------------

long1549 = settingRepository1.GetAttr("ELECTRICFLUXDENSITY")
'--------------------------------------------------
' Parameter 1 : (String) "ELECTRICFLUXDENSITY"
' Returned value : (Variant) (Long) 1
'--------------------------------------------------

Dim bSTR3097
bSTR3097 = ""
Dim bSTR3098
bSTR3098 = ""
Dim boolean1549
settingRepository1.GetAttrInfo "ELECTRICFLUXDENSITY", bSTR3097, bSTR3098, boolean1549
'--------------------------------------------------
' Parameter 1 : (String) "ELECTRICFLUXDENSITY"
' Parameter 2 : (String) "Default value"
' Parameter 3 : (String) "Unlocked"
' Parameter 4 : (Boolean) False
'--------------------------------------------------

long1550 = settingRepository1.GetAttr("ELECTRICFLUXDENSITY_Large")
'--------------------------------------------------
' Parameter 1 : (String) "ELECTRICFLUXDENSITY_Large"
' Returned value : (Variant) (Long) 1
'--------------------------------------------------

Dim bSTR3099
bSTR3099 = ""
Dim bSTR3100
bSTR3100 = ""
Dim boolean1550
settingRepository1.GetAttrInfo "ELECTRICFLUXDENSITY_Large", bSTR3099, bSTR3100, boolean1550
'--------------------------------------------------
' Parameter 1 : (String) "ELECTRICFLUXDENSITY_Large"
' Parameter 2 : (String) "Default value"
' Parameter 3 : (String) "Unlocked"
' Parameter 4 : (Boolean) False
'--------------------------------------------------

long1551 = settingRepository1.GetAttr("ELECTRICFLUXDENSITY_ExtraLarge")
'--------------------------------------------------
' Parameter 1 : (String) "ELECTRICFLUXDENSITY_ExtraLarge"
' Returned value : (Variant) (Long) 1
'--------------------------------------------------

Dim bSTR3101
bSTR3101 = ""
Dim bSTR3102
bSTR3102 = ""
Dim boolean1551
settingRepository1.GetAttrInfo "ELECTRICFLUXDENSITY_ExtraLarge", bSTR3101, bSTR3102, boolean1551
'--------------------------------------------------
' Parameter 1 : (String) "ELECTRICFLUXDENSITY_ExtraLarge"
' Parameter 2 : (String) "Default value"
' Parameter 3 : (String) "Unlocked"
' Parameter 4 : (Boolean) False
'--------------------------------------------------

long1552 = settingRepository1.GetAttr("ELECTRICFLUXDENSITY_Small")
'--------------------------------------------------
' Parameter 1 : (String) "ELECTRICFLUXDENSITY_Small"
' Returned value : (Variant) (Long) 1
'--------------------------------------------------

Dim bSTR3103
bSTR3103 = ""
Dim bSTR3104
bSTR3104 = ""
Dim boolean1552
settingRepository1.GetAttrInfo "ELECTRICFLUXDENSITY_Small", bSTR3103, bSTR3104, boolean1552
'--------------------------------------------------
' Parameter 1 : (String) "ELECTRICFLUXDENSITY_Small"
' Parameter 2 : (String) "Default value"
' Parameter 3 : (String) "Unlocked"
' Parameter 4 : (Boolean) False
'--------------------------------------------------

long1553 = settingRepository1.GetAttr("ELECTRICFLUXDENSITY_ExtraSmall")
'--------------------------------------------------
' Parameter 1 : (String) "ELECTRICFLUXDENSITY_ExtraSmall"
' Returned value : (Variant) (Long) 1
'--------------------------------------------------

Dim bSTR3105
bSTR3105 = ""
Dim bSTR3106
bSTR3106 = ""
Dim boolean1553
settingRepository1.GetAttrInfo "ELECTRICFLUXDENSITY_ExtraSmall", bSTR3105, bSTR3106, boolean1553
'--------------------------------------------------
' Parameter 1 : (String) "ELECTRICFLUXDENSITY_ExtraSmall"
' Parameter 2 : (String) "Default value"
' Parameter 3 : (String) "Unlocked"
' Parameter 4 : (Boolean) False
'--------------------------------------------------

long1554 = settingRepository1.GetAttr("ELECTRICFLUXDENSITY_Nanometric")
'--------------------------------------------------
' Parameter 1 : (String) "ELECTRICFLUXDENSITY_Nanometric"
' Returned value : (Variant) (Long) 1
'--------------------------------------------------

Dim bSTR3107
bSTR3107 = ""
Dim bSTR3108
bSTR3108 = ""
Dim boolean1554
settingRepository1.GetAttrInfo "ELECTRICFLUXDENSITY_Nanometric", bSTR3107, bSTR3108, boolean1554
'--------------------------------------------------
' Parameter 1 : (String) "ELECTRICFLUXDENSITY_Nanometric"
' Parameter 2 : (String) "Default value"
' Parameter 3 : (String) "Unlocked"
' Parameter 4 : (Boolean) False
'--------------------------------------------------

long1555 = settingRepository1.GetAttr("CAPACITANCE")
'--------------------------------------------------
' Parameter 1 : (String) "CAPACITANCE"
' Returned value : (Variant) (Long) 1
'--------------------------------------------------

Dim bSTR3109
bSTR3109 = ""
Dim bSTR3110
bSTR3110 = ""
Dim boolean1555
settingRepository1.GetAttrInfo "CAPACITANCE", bSTR3109, bSTR3110, boolean1555
'--------------------------------------------------
' Parameter 1 : (String) "CAPACITANCE"
' Parameter 2 : (String) "Default value"
' Parameter 3 : (String) "Unlocked"
' Parameter 4 : (Boolean) False
'--------------------------------------------------

long1556 = settingRepository1.GetAttr("CAPACITANCE_Large")
'--------------------------------------------------
' Parameter 1 : (String) "CAPACITANCE_Large"
' Returned value : (Variant) (Long) 1
'--------------------------------------------------

Dim bSTR3111
bSTR3111 = ""
Dim bSTR3112
bSTR3112 = ""
Dim boolean1556
settingRepository1.GetAttrInfo "CAPACITANCE_Large", bSTR3111, bSTR3112, boolean1556
'--------------------------------------------------
' Parameter 1 : (String) "CAPACITANCE_Large"
' Parameter 2 : (String) "Default value"
' Parameter 3 : (String) "Unlocked"
' Parameter 4 : (Boolean) False
'--------------------------------------------------

long1557 = settingRepository1.GetAttr("CAPACITANCE_ExtraLarge")
'--------------------------------------------------
' Parameter 1 : (String) "CAPACITANCE_ExtraLarge"
' Returned value : (Variant) (Long) 1
'--------------------------------------------------

Dim bSTR3113
bSTR3113 = ""
Dim bSTR3114
bSTR3114 = ""
Dim boolean1557
settingRepository1.GetAttrInfo "CAPACITANCE_ExtraLarge", bSTR3113, bSTR3114, boolean1557
'--------------------------------------------------
' Parameter 1 : (String) "CAPACITANCE_ExtraLarge"
' Parameter 2 : (String) "Default value"
' Parameter 3 : (String) "Unlocked"
' Parameter 4 : (Boolean) False
'--------------------------------------------------

long1558 = settingRepository1.GetAttr("CAPACITANCE_Small")
'--------------------------------------------------
' Parameter 1 : (String) "CAPACITANCE_Small"
' Returned value : (Variant) (Long) 1
'--------------------------------------------------

Dim bSTR3115
bSTR3115 = ""
Dim bSTR3116
bSTR3116 = ""
Dim boolean1558
settingRepository1.GetAttrInfo "CAPACITANCE_Small", bSTR3115, bSTR3116, boolean1558
'--------------------------------------------------
' Parameter 1 : (String) "CAPACITANCE_Small"
' Parameter 2 : (String) "Default value"
' Parameter 3 : (String) "Unlocked"
' Parameter 4 : (Boolean) False
'--------------------------------------------------

long1559 = settingRepository1.GetAttr("CAPACITANCE_ExtraSmall")
'--------------------------------------------------
' Parameter 1 : (String) "CAPACITANCE_ExtraSmall"
' Returned value : (Variant) (Long) 1
'--------------------------------------------------

Dim bSTR3117
bSTR3117 = ""
Dim bSTR3118
bSTR3118 = ""
Dim boolean1559
settingRepository1.GetAttrInfo "CAPACITANCE_ExtraSmall", bSTR3117, bSTR3118, boolean1559
'--------------------------------------------------
' Parameter 1 : (String) "CAPACITANCE_ExtraSmall"
' Parameter 2 : (String) "Default value"
' Parameter 3 : (String) "Unlocked"
' Parameter 4 : (Boolean) False
'--------------------------------------------------

long1560 = settingRepository1.GetAttr("CAPACITANCE_Nanometric")
'--------------------------------------------------
' Parameter 1 : (String) "CAPACITANCE_Nanometric"
' Returned value : (Variant) (Long) 1
'--------------------------------------------------

Dim bSTR3119
bSTR3119 = ""
Dim bSTR3120
bSTR3120 = ""
Dim boolean1560
settingRepository1.GetAttrInfo "CAPACITANCE_Nanometric", bSTR3119, bSTR3120, boolean1560
'--------------------------------------------------
' Parameter 1 : (String) "CAPACITANCE_Nanometric"
' Parameter 2 : (String) "Default value"
' Parameter 3 : (String) "Unlocked"
' Parameter 4 : (Boolean) False
'--------------------------------------------------

long1561 = settingRepository1.GetAttr("PERMITTIVITY")
'--------------------------------------------------
' Parameter 1 : (String) "PERMITTIVITY"
' Returned value : (Variant) (Long) 1
'--------------------------------------------------

Dim bSTR3121
bSTR3121 = ""
Dim bSTR3122
bSTR3122 = ""
Dim boolean1561
settingRepository1.GetAttrInfo "PERMITTIVITY", bSTR3121, bSTR3122, boolean1561
'--------------------------------------------------
' Parameter 1 : (String) "PERMITTIVITY"
' Parameter 2 : (String) "Default value"
' Parameter 3 : (String) "Unlocked"
' Parameter 4 : (Boolean) False
'--------------------------------------------------

long1562 = settingRepository1.GetAttr("PERMITTIVITY_Large")
'--------------------------------------------------
' Parameter 1 : (String) "PERMITTIVITY_Large"
' Returned value : (Variant) (Long) 1
'--------------------------------------------------

Dim bSTR3123
bSTR3123 = ""
Dim bSTR3124
bSTR3124 = ""
Dim boolean1562
settingRepository1.GetAttrInfo "PERMITTIVITY_Large", bSTR3123, bSTR3124, boolean1562
'--------------------------------------------------
' Parameter 1 : (String) "PERMITTIVITY_Large"
' Parameter 2 : (String) "Default value"
' Parameter 3 : (String) "Unlocked"
' Parameter 4 : (Boolean) False
'--------------------------------------------------

long1563 = settingRepository1.GetAttr("PERMITTIVITY_ExtraLarge")
'--------------------------------------------------
' Parameter 1 : (String) "PERMITTIVITY_ExtraLarge"
' Returned value : (Variant) (Long) 1
'--------------------------------------------------

Dim bSTR3125
bSTR3125 = ""
Dim bSTR3126
bSTR3126 = ""
Dim boolean1563
settingRepository1.GetAttrInfo "PERMITTIVITY_ExtraLarge", bSTR3125, bSTR3126, boolean1563
'--------------------------------------------------
' Parameter 1 : (String) "PERMITTIVITY_ExtraLarge"
' Parameter 2 : (String) "Default value"
' Parameter 3 : (String) "Unlocked"
' Parameter 4 : (Boolean) False
'--------------------------------------------------

long1564 = settingRepository1.GetAttr("PERMITTIVITY_Small")
'--------------------------------------------------
' Parameter 1 : (String) "PERMITTIVITY_Small"
' Returned value : (Variant) (Long) 1
'--------------------------------------------------

Dim bSTR3127
bSTR3127 = ""
Dim bSTR3128
bSTR3128 = ""
Dim boolean1564
settingRepository1.GetAttrInfo "PERMITTIVITY_Small", bSTR3127, bSTR3128, boolean1564
'--------------------------------------------------
' Parameter 1 : (String) "PERMITTIVITY_Small"
' Parameter 2 : (String) "Default value"
' Parameter 3 : (String) "Unlocked"
' Parameter 4 : (Boolean) False
'--------------------------------------------------

long1565 = settingRepository1.GetAttr("PERMITTIVITY_ExtraSmall")
'--------------------------------------------------
' Parameter 1 : (String) "PERMITTIVITY_ExtraSmall"
' Returned value : (Variant) (Long) 1
'--------------------------------------------------

Dim bSTR3129
bSTR3129 = ""
Dim bSTR3130
bSTR3130 = ""
Dim boolean1565
settingRepository1.GetAttrInfo "PERMITTIVITY_ExtraSmall", bSTR3129, bSTR3130, boolean1565
'--------------------------------------------------
' Parameter 1 : (String) "PERMITTIVITY_ExtraSmall"
' Parameter 2 : (String) "Default value"
' Parameter 3 : (String) "Unlocked"
' Parameter 4 : (Boolean) False
'--------------------------------------------------

long1566 = settingRepository1.GetAttr("PERMITTIVITY_Nanometric")
'--------------------------------------------------
' Parameter 1 : (String) "PERMITTIVITY_Nanometric"
' Returned value : (Variant) (Long) 1
'--------------------------------------------------

Dim bSTR3131
bSTR3131 = ""
Dim bSTR3132
bSTR3132 = ""
Dim boolean1566
settingRepository1.GetAttrInfo "PERMITTIVITY_Nanometric", bSTR3131, bSTR3132, boolean1566
'--------------------------------------------------
' Parameter 1 : (String) "PERMITTIVITY_Nanometric"
' Parameter 2 : (String) "Default value"
' Parameter 3 : (String) "Unlocked"
' Parameter 4 : (Boolean) False
'--------------------------------------------------

long1567 = settingRepository1.GetAttr("ELECTRICPOLARIZATION")
'--------------------------------------------------
' Parameter 1 : (String) "ELECTRICPOLARIZATION"
' Returned value : (Variant) (Long) 1
'--------------------------------------------------

Dim bSTR3133
bSTR3133 = ""
Dim bSTR3134
bSTR3134 = ""
Dim boolean1567
settingRepository1.GetAttrInfo "ELECTRICPOLARIZATION", bSTR3133, bSTR3134, boolean1567
'--------------------------------------------------
' Parameter 1 : (String) "ELECTRICPOLARIZATION"
' Parameter 2 : (String) "Default value"
' Parameter 3 : (String) "Unlocked"
' Parameter 4 : (Boolean) False
'--------------------------------------------------

long1568 = settingRepository1.GetAttr("ELECTRICPOLARIZATION_Large")
'--------------------------------------------------
' Parameter 1 : (String) "ELECTRICPOLARIZATION_Large"
' Returned value : (Variant) (Long) 1
'--------------------------------------------------

Dim bSTR3135
bSTR3135 = ""
Dim bSTR3136
bSTR3136 = ""
Dim boolean1568
settingRepository1.GetAttrInfo "ELECTRICPOLARIZATION_Large", bSTR3135, bSTR3136, boolean1568
'--------------------------------------------------
' Parameter 1 : (String) "ELECTRICPOLARIZATION_Large"
' Parameter 2 : (String) "Default value"
' Parameter 3 : (String) "Unlocked"
' Parameter 4 : (Boolean) False
'--------------------------------------------------

long1569 = settingRepository1.GetAttr("ELECTRICPOLARIZATION_ExtraLarge")
'--------------------------------------------------
' Parameter 1 : (String) "ELECTRICPOLARIZATION_ExtraLarge"
' Returned value : (Variant) (Long) 1
'--------------------------------------------------

Dim bSTR3137
bSTR3137 = ""
Dim bSTR3138
bSTR3138 = ""
Dim boolean1569
settingRepository1.GetAttrInfo "ELECTRICPOLARIZATION_ExtraLarge", bSTR3137, bSTR3138, boolean1569
'--------------------------------------------------
' Parameter 1 : (String) "ELECTRICPOLARIZATION_ExtraLarge"
' Parameter 2 : (String) "Default value"
' Parameter 3 : (String) "Unlocked"
' Parameter 4 : (Boolean) False
'--------------------------------------------------

long1570 = settingRepository1.GetAttr("ELECTRICPOLARIZATION_Small")
'--------------------------------------------------
' Parameter 1 : (String) "ELECTRICPOLARIZATION_Small"
' Returned value : (Variant) (Long) 1
'--------------------------------------------------

Dim bSTR3139
bSTR3139 = ""
Dim bSTR3140
bSTR3140 = ""
Dim boolean1570
settingRepository1.GetAttrInfo "ELECTRICPOLARIZATION_Small", bSTR3139, bSTR3140, boolean1570
'--------------------------------------------------
' Parameter 1 : (String) "ELECTRICPOLARIZATION_Small"
' Parameter 2 : (String) "Default value"
' Parameter 3 : (String) "Unlocked"
' Parameter 4 : (Boolean) False
'--------------------------------------------------

long1571 = settingRepository1.GetAttr("ELECTRICPOLARIZATION_ExtraSmall")
'--------------------------------------------------
' Parameter 1 : (String) "ELECTRICPOLARIZATION_ExtraSmall"
' Returned value : (Variant) (Long) 1
'--------------------------------------------------

Dim bSTR3141
bSTR3141 = ""
Dim bSTR3142
bSTR3142 = ""
Dim boolean1571
settingRepository1.GetAttrInfo "ELECTRICPOLARIZATION_ExtraSmall", bSTR3141, bSTR3142, boolean1571
'--------------------------------------------------
' Parameter 1 : (String) "ELECTRICPOLARIZATION_ExtraSmall"
' Parameter 2 : (String) "Default value"
' Parameter 3 : (String) "Unlocked"
' Parameter 4 : (Boolean) False
'--------------------------------------------------

long1572 = settingRepository1.GetAttr("ELECTRICPOLARIZATION_Nanometric")
'--------------------------------------------------
' Parameter 1 : (String) "ELECTRICPOLARIZATION_Nanometric"
' Returned value : (Variant) (Long) 1
'--------------------------------------------------

Dim bSTR3143
bSTR3143 = ""
Dim bSTR3144
bSTR3144 = ""
Dim boolean1572
settingRepository1.GetAttrInfo "ELECTRICPOLARIZATION_Nanometric", bSTR3143, bSTR3144, boolean1572
'--------------------------------------------------
' Parameter 1 : (String) "ELECTRICPOLARIZATION_Nanometric"
' Parameter 2 : (String) "Default value"
' Parameter 3 : (String) "Unlocked"
' Parameter 4 : (Boolean) False
'--------------------------------------------------

long1573 = settingRepository1.GetAttr("ELECTRIZATION")
'--------------------------------------------------
' Parameter 1 : (String) "ELECTRIZATION"
' Returned value : (Variant) (Long) 1
'--------------------------------------------------

Dim bSTR3145
bSTR3145 = ""
Dim bSTR3146
bSTR3146 = ""
Dim boolean1573
settingRepository1.GetAttrInfo "ELECTRIZATION", bSTR3145, bSTR3146, boolean1573
'--------------------------------------------------
' Parameter 1 : (String) "ELECTRIZATION"
' Parameter 2 : (String) "Default value"
' Parameter 3 : (String) "Unlocked"
' Parameter 4 : (Boolean) False
'--------------------------------------------------

long1574 = settingRepository1.GetAttr("ELECTRIZATION_Large")
'--------------------------------------------------
' Parameter 1 : (String) "ELECTRIZATION_Large"
' Returned value : (Variant) (Long) 1
'--------------------------------------------------

Dim bSTR3147
bSTR3147 = ""
Dim bSTR3148
bSTR3148 = ""
Dim boolean1574
settingRepository1.GetAttrInfo "ELECTRIZATION_Large", bSTR3147, bSTR3148, boolean1574
'--------------------------------------------------
' Parameter 1 : (String) "ELECTRIZATION_Large"
' Parameter 2 : (String) "Default value"
' Parameter 3 : (String) "Unlocked"
' Parameter 4 : (Boolean) False
'--------------------------------------------------

long1575 = settingRepository1.GetAttr("ELECTRIZATION_ExtraLarge")
'--------------------------------------------------
' Parameter 1 : (String) "ELECTRIZATION_ExtraLarge"
' Returned value : (Variant) (Long) 1
'--------------------------------------------------

Dim bSTR3149
bSTR3149 = ""
Dim bSTR3150
bSTR3150 = ""
Dim boolean1575
settingRepository1.GetAttrInfo "ELECTRIZATION_ExtraLarge", bSTR3149, bSTR3150, boolean1575
'--------------------------------------------------
' Parameter 1 : (String) "ELECTRIZATION_ExtraLarge"
' Parameter 2 : (String) "Default value"
' Parameter 3 : (String) "Unlocked"
' Parameter 4 : (Boolean) False
'--------------------------------------------------

long1576 = settingRepository1.GetAttr("ELECTRIZATION_Small")
'--------------------------------------------------
' Parameter 1 : (String) "ELECTRIZATION_Small"
' Returned value : (Variant) (Long) 1
'--------------------------------------------------

Dim bSTR3151
bSTR3151 = ""
Dim bSTR3152
bSTR3152 = ""
Dim boolean1576
settingRepository1.GetAttrInfo "ELECTRIZATION_Small", bSTR3151, bSTR3152, boolean1576
'--------------------------------------------------
' Parameter 1 : (String) "ELECTRIZATION_Small"
' Parameter 2 : (String) "Default value"
' Parameter 3 : (String) "Unlocked"
' Parameter 4 : (Boolean) False
'--------------------------------------------------

long1577 = settingRepository1.GetAttr("ELECTRIZATION_ExtraSmall")
'--------------------------------------------------
' Parameter 1 : (String) "ELECTRIZATION_ExtraSmall"
' Returned value : (Variant) (Long) 1
'--------------------------------------------------

Dim bSTR3153
bSTR3153 = ""
Dim bSTR3154
bSTR3154 = ""
Dim boolean1577
settingRepository1.GetAttrInfo "ELECTRIZATION_ExtraSmall", bSTR3153, bSTR3154, boolean1577
'--------------------------------------------------
' Parameter 1 : (String) "ELECTRIZATION_ExtraSmall"
' Parameter 2 : (String) "Default value"
' Parameter 3 : (String) "Unlocked"
' Parameter 4 : (Boolean) False
'--------------------------------------------------

long1578 = settingRepository1.GetAttr("ELECTRIZATION_Nanometric")
'--------------------------------------------------
' Parameter 1 : (String) "ELECTRIZATION_Nanometric"
' Returned value : (Variant) (Long) 1
'--------------------------------------------------

Dim bSTR3155
bSTR3155 = ""
Dim bSTR3156
bSTR3156 = ""
Dim boolean1578
settingRepository1.GetAttrInfo "ELECTRIZATION_Nanometric", bSTR3155, bSTR3156, boolean1578
'--------------------------------------------------
' Parameter 1 : (String) "ELECTRIZATION_Nanometric"
' Parameter 2 : (String) "Default value"
' Parameter 3 : (String) "Unlocked"
' Parameter 4 : (Boolean) False
'--------------------------------------------------

long1579 = settingRepository1.GetAttr("ELECTRICDIPOLEMOMENT")
'--------------------------------------------------
' Parameter 1 : (String) "ELECTRICDIPOLEMOMENT"
' Returned value : (Variant) (Long) 1
'--------------------------------------------------

Dim bSTR3157
bSTR3157 = ""
Dim bSTR3158
bSTR3158 = ""
Dim boolean1579
settingRepository1.GetAttrInfo "ELECTRICDIPOLEMOMENT", bSTR3157, bSTR3158, boolean1579
'--------------------------------------------------
' Parameter 1 : (String) "ELECTRICDIPOLEMOMENT"
' Parameter 2 : (String) "Default value"
' Parameter 3 : (String) "Unlocked"
' Parameter 4 : (Boolean) False
'--------------------------------------------------

long1580 = settingRepository1.GetAttr("ELECTRICDIPOLEMOMENT_Large")
'--------------------------------------------------
' Parameter 1 : (String) "ELECTRICDIPOLEMOMENT_Large"
' Returned value : (Variant) (Long) 1
'--------------------------------------------------

Dim bSTR3159
bSTR3159 = ""
Dim bSTR3160
bSTR3160 = ""
Dim boolean1580
settingRepository1.GetAttrInfo "ELECTRICDIPOLEMOMENT_Large", bSTR3159, bSTR3160, boolean1580
'--------------------------------------------------
' Parameter 1 : (String) "ELECTRICDIPOLEMOMENT_Large"
' Parameter 2 : (String) "Default value"
' Parameter 3 : (String) "Unlocked"
' Parameter 4 : (Boolean) False
'--------------------------------------------------

long1581 = settingRepository1.GetAttr("ELECTRICDIPOLEMOMENT_ExtraLarge")
'--------------------------------------------------
' Parameter 1 : (String) "ELECTRICDIPOLEMOMENT_ExtraLarge"
' Returned value : (Variant) (Long) 1
'--------------------------------------------------

Dim bSTR3161
bSTR3161 = ""
Dim bSTR3162
bSTR3162 = ""
Dim boolean1581
settingRepository1.GetAttrInfo "ELECTRICDIPOLEMOMENT_ExtraLarge", bSTR3161, bSTR3162, boolean1581
'--------------------------------------------------
' Parameter 1 : (String) "ELECTRICDIPOLEMOMENT_ExtraLarge"
' Parameter 2 : (String) "Default value"
' Parameter 3 : (String) "Unlocked"
' Parameter 4 : (Boolean) False
'--------------------------------------------------

long1582 = settingRepository1.GetAttr("ELECTRICDIPOLEMOMENT_Small")
'--------------------------------------------------
' Parameter 1 : (String) "ELECTRICDIPOLEMOMENT_Small"
' Returned value : (Variant) (Long) 1
'--------------------------------------------------

Dim bSTR3163
bSTR3163 = ""
Dim bSTR3164
bSTR3164 = ""
Dim boolean1582
settingRepository1.GetAttrInfo "ELECTRICDIPOLEMOMENT_Small", bSTR3163, bSTR3164, boolean1582
'--------------------------------------------------
' Parameter 1 : (String) "ELECTRICDIPOLEMOMENT_Small"
' Parameter 2 : (String) "Default value"
' Parameter 3 : (String) "Unlocked"
' Parameter 4 : (Boolean) False
'--------------------------------------------------

long1583 = settingRepository1.GetAttr("ELECTRICDIPOLEMOMENT_ExtraSmall")
'--------------------------------------------------
' Parameter 1 : (String) "ELECTRICDIPOLEMOMENT_ExtraSmall"
' Returned value : (Variant) (Long) 1
'--------------------------------------------------

Dim bSTR3165
bSTR3165 = ""
Dim bSTR3166
bSTR3166 = ""
Dim boolean1583
settingRepository1.GetAttrInfo "ELECTRICDIPOLEMOMENT_ExtraSmall", bSTR3165, bSTR3166, boolean1583
'--------------------------------------------------
' Parameter 1 : (String) "ELECTRICDIPOLEMOMENT_ExtraSmall"
' Parameter 2 : (String) "Default value"
' Parameter 3 : (String) "Unlocked"
' Parameter 4 : (Boolean) False
'--------------------------------------------------

long1584 = settingRepository1.GetAttr("ELECTRICDIPOLEMOMENT_Nanometric")
'--------------------------------------------------
' Parameter 1 : (String) "ELECTRICDIPOLEMOMENT_Nanometric"
' Returned value : (Variant) (Long) 1
'--------------------------------------------------

Dim bSTR3167
bSTR3167 = ""
Dim bSTR3168
bSTR3168 = ""
Dim boolean1584
settingRepository1.GetAttrInfo "ELECTRICDIPOLEMOMENT_Nanometric", bSTR3167, bSTR3168, boolean1584
'--------------------------------------------------
' Parameter 1 : (String) "ELECTRICDIPOLEMOMENT_Nanometric"
' Parameter 2 : (String) "Default value"
' Parameter 3 : (String) "Unlocked"
' Parameter 4 : (Boolean) False
'--------------------------------------------------

long1585 = settingRepository1.GetAttr("LINEARCURRENTDENSITY")
'--------------------------------------------------
' Parameter 1 : (String) "LINEARCURRENTDENSITY"
' Returned value : (Variant) (Long) 1
'--------------------------------------------------

Dim bSTR3169
bSTR3169 = ""
Dim bSTR3170
bSTR3170 = ""
Dim boolean1585
settingRepository1.GetAttrInfo "LINEARCURRENTDENSITY", bSTR3169, bSTR3170, boolean1585
'--------------------------------------------------
' Parameter 1 : (String) "LINEARCURRENTDENSITY"
' Parameter 2 : (String) "Default value"
' Parameter 3 : (String) "Unlocked"
' Parameter 4 : (Boolean) False
'--------------------------------------------------

long1586 = settingRepository1.GetAttr("LINEARCURRENTDENSITY_Large")
'--------------------------------------------------
' Parameter 1 : (String) "LINEARCURRENTDENSITY_Large"
' Returned value : (Variant) (Long) 1
'--------------------------------------------------

Dim bSTR3171
bSTR3171 = ""
Dim bSTR3172
bSTR3172 = ""
Dim boolean1586
settingRepository1.GetAttrInfo "LINEARCURRENTDENSITY_Large", bSTR3171, bSTR3172, boolean1586
'--------------------------------------------------
' Parameter 1 : (String) "LINEARCURRENTDENSITY_Large"
' Parameter 2 : (String) "Default value"
' Parameter 3 : (String) "Unlocked"
' Parameter 4 : (Boolean) False
'--------------------------------------------------

long1587 = settingRepository1.GetAttr("LINEARCURRENTDENSITY_ExtraLarge")
'--------------------------------------------------
' Parameter 1 : (String) "LINEARCURRENTDENSITY_ExtraLarge"
' Returned value : (Variant) (Long) 1
'--------------------------------------------------

Dim bSTR3173
bSTR3173 = ""
Dim bSTR3174
bSTR3174 = ""
Dim boolean1587
settingRepository1.GetAttrInfo "LINEARCURRENTDENSITY_ExtraLarge", bSTR3173, bSTR3174, boolean1587
'--------------------------------------------------
' Parameter 1 : (String) "LINEARCURRENTDENSITY_ExtraLarge"
' Parameter 2 : (String) "Default value"
' Parameter 3 : (String) "Unlocked"
' Parameter 4 : (Boolean) False
'--------------------------------------------------

long1588 = settingRepository1.GetAttr("LINEARCURRENTDENSITY_Small")
'--------------------------------------------------
' Parameter 1 : (String) "LINEARCURRENTDENSITY_Small"
' Returned value : (Variant) (Long) 1
'--------------------------------------------------

Dim bSTR3175
bSTR3175 = ""
Dim bSTR3176
bSTR3176 = ""
Dim boolean1588
settingRepository1.GetAttrInfo "LINEARCURRENTDENSITY_Small", bSTR3175, bSTR3176, boolean1588
'--------------------------------------------------
' Parameter 1 : (String) "LINEARCURRENTDENSITY_Small"
' Parameter 2 : (String) "Default value"
' Parameter 3 : (String) "Unlocked"
' Parameter 4 : (Boolean) False
'--------------------------------------------------

long1589 = settingRepository1.GetAttr("LINEARCURRENTDENSITY_ExtraSmall")
'--------------------------------------------------
' Parameter 1 : (String) "LINEARCURRENTDENSITY_ExtraSmall"
' Returned value : (Variant) (Long) 1
'--------------------------------------------------

Dim bSTR3177
bSTR3177 = ""
Dim bSTR3178
bSTR3178 = ""
Dim boolean1589
settingRepository1.GetAttrInfo "LINEARCURRENTDENSITY_ExtraSmall", bSTR3177, bSTR3178, boolean1589
'--------------------------------------------------
' Parameter 1 : (String) "LINEARCURRENTDENSITY_ExtraSmall"
' Parameter 2 : (String) "Default value"
' Parameter 3 : (String) "Unlocked"
' Parameter 4 : (Boolean) False
'--------------------------------------------------

long1590 = settingRepository1.GetAttr("LINEARCURRENTDENSITY_Nanometric")
'--------------------------------------------------
' Parameter 1 : (String) "LINEARCURRENTDENSITY_Nanometric"
' Returned value : (Variant) (Long) 1
'--------------------------------------------------

Dim bSTR3179
bSTR3179 = ""
Dim bSTR3180
bSTR3180 = ""
Dim boolean1590
settingRepository1.GetAttrInfo "LINEARCURRENTDENSITY_Nanometric", bSTR3179, bSTR3180, boolean1590
'--------------------------------------------------
' Parameter 1 : (String) "LINEARCURRENTDENSITY_Nanometric"
' Parameter 2 : (String) "Default value"
' Parameter 3 : (String) "Unlocked"
' Parameter 4 : (Boolean) False
'--------------------------------------------------

long1591 = settingRepository1.GetAttr("MAGNETICFIELDSTRENGTH")
'--------------------------------------------------
' Parameter 1 : (String) "MAGNETICFIELDSTRENGTH"
' Returned value : (Variant) (Long) 1
'--------------------------------------------------

Dim bSTR3181
bSTR3181 = ""
Dim bSTR3182
bSTR3182 = ""
Dim boolean1591
settingRepository1.GetAttrInfo "MAGNETICFIELDSTRENGTH", bSTR3181, bSTR3182, boolean1591
'--------------------------------------------------
' Parameter 1 : (String) "MAGNETICFIELDSTRENGTH"
' Parameter 2 : (String) "Default value"
' Parameter 3 : (String) "Unlocked"
' Parameter 4 : (Boolean) False
'--------------------------------------------------

long1592 = settingRepository1.GetAttr("MAGNETICFIELDSTRENGTH_Large")
'--------------------------------------------------
' Parameter 1 : (String) "MAGNETICFIELDSTRENGTH_Large"
' Returned value : (Variant) (Long) 1
'--------------------------------------------------

Dim bSTR3183
bSTR3183 = ""
Dim bSTR3184
bSTR3184 = ""
Dim boolean1592
settingRepository1.GetAttrInfo "MAGNETICFIELDSTRENGTH_Large", bSTR3183, bSTR3184, boolean1592
'--------------------------------------------------
' Parameter 1 : (String) "MAGNETICFIELDSTRENGTH_Large"
' Parameter 2 : (String) "Default value"
' Parameter 3 : (String) "Unlocked"
' Parameter 4 : (Boolean) False
'--------------------------------------------------

long1593 = settingRepository1.GetAttr("MAGNETICFIELDSTRENGTH_ExtraLarge")
'--------------------------------------------------
' Parameter 1 : (String) "MAGNETICFIELDSTRENGTH_ExtraLarge"
' Returned value : (Variant) (Long) 1
'--------------------------------------------------

Dim bSTR3185
bSTR3185 = ""
Dim bSTR3186
bSTR3186 = ""
Dim boolean1593
settingRepository1.GetAttrInfo "MAGNETICFIELDSTRENGTH_ExtraLarge", bSTR3185, bSTR3186, boolean1593
'--------------------------------------------------
' Parameter 1 : (String) "MAGNETICFIELDSTRENGTH_ExtraLarge"
' Parameter 2 : (String) "Default value"
' Parameter 3 : (String) "Unlocked"
' Parameter 4 : (Boolean) False
'--------------------------------------------------

long1594 = settingRepository1.GetAttr("MAGNETICFIELDSTRENGTH_Small")
'--------------------------------------------------
' Parameter 1 : (String) "MAGNETICFIELDSTRENGTH_Small"
' Returned value : (Variant) (Long) 1
'--------------------------------------------------

Dim bSTR3187
bSTR3187 = ""
Dim bSTR3188
bSTR3188 = ""
Dim boolean1594
settingRepository1.GetAttrInfo "MAGNETICFIELDSTRENGTH_Small", bSTR3187, bSTR3188, boolean1594
'--------------------------------------------------
' Parameter 1 : (String) "MAGNETICFIELDSTRENGTH_Small"
' Parameter 2 : (String) "Default value"
' Parameter 3 : (String) "Unlocked"
' Parameter 4 : (Boolean) False
'--------------------------------------------------

long1595 = settingRepository1.GetAttr("MAGNETICFIELDSTRENGTH_ExtraSmall")
'--------------------------------------------------
' Parameter 1 : (String) "MAGNETICFIELDSTRENGTH_ExtraSmall"
' Returned value : (Variant) (Long) 1
'--------------------------------------------------

Dim bSTR3189
bSTR3189 = ""
Dim bSTR3190
bSTR3190 = ""
Dim boolean1595
settingRepository1.GetAttrInfo "MAGNETICFIELDSTRENGTH_ExtraSmall", bSTR3189, bSTR3190, boolean1595
'--------------------------------------------------
' Parameter 1 : (String) "MAGNETICFIELDSTRENGTH_ExtraSmall"
' Parameter 2 : (String) "Default value"
' Parameter 3 : (String) "Unlocked"
' Parameter 4 : (Boolean) False
'--------------------------------------------------

long1596 = settingRepository1.GetAttr("MAGNETICFIELDSTRENGTH_Nanometric")
'--------------------------------------------------
' Parameter 1 : (String) "MAGNETICFIELDSTRENGTH_Nanometric"
' Returned value : (Variant) (Long) 1
'--------------------------------------------------

Dim bSTR3191
bSTR3191 = ""
Dim bSTR3192
bSTR3192 = ""
Dim boolean1596
settingRepository1.GetAttrInfo "MAGNETICFIELDSTRENGTH_Nanometric", bSTR3191, bSTR3192, boolean1596
'--------------------------------------------------
' Parameter 1 : (String) "MAGNETICFIELDSTRENGTH_Nanometric"
' Parameter 2 : (String) "Default value"
' Parameter 3 : (String) "Unlocked"
' Parameter 4 : (Boolean) False
'--------------------------------------------------

long1597 = settingRepository1.GetAttr("MAGNETICFLUXDENSITY")
'--------------------------------------------------
' Parameter 1 : (String) "MAGNETICFLUXDENSITY"
' Returned value : (Variant) (Long) 1
'--------------------------------------------------

Dim bSTR3193
bSTR3193 = ""
Dim bSTR3194
bSTR3194 = ""
Dim boolean1597
settingRepository1.GetAttrInfo "MAGNETICFLUXDENSITY", bSTR3193, bSTR3194, boolean1597
'--------------------------------------------------
' Parameter 1 : (String) "MAGNETICFLUXDENSITY"
' Parameter 2 : (String) "Default value"
' Parameter 3 : (String) "Unlocked"
' Parameter 4 : (Boolean) False
'--------------------------------------------------

long1598 = settingRepository1.GetAttr("MAGNETICFLUXDENSITY_Large")
'--------------------------------------------------
' Parameter 1 : (String) "MAGNETICFLUXDENSITY_Large"
' Returned value : (Variant) (Long) 1
'--------------------------------------------------

Dim bSTR3195
bSTR3195 = ""
Dim bSTR3196
bSTR3196 = ""
Dim boolean1598
settingRepository1.GetAttrInfo "MAGNETICFLUXDENSITY_Large", bSTR3195, bSTR3196, boolean1598
'--------------------------------------------------
' Parameter 1 : (String) "MAGNETICFLUXDENSITY_Large"
' Parameter 2 : (String) "Default value"
' Parameter 3 : (String) "Unlocked"
' Parameter 4 : (Boolean) False
'--------------------------------------------------

long1599 = settingRepository1.GetAttr("MAGNETICFLUXDENSITY_ExtraLarge")
'--------------------------------------------------
' Parameter 1 : (String) "MAGNETICFLUXDENSITY_ExtraLarge"
' Returned value : (Variant) (Long) 1
'--------------------------------------------------

Dim bSTR3197
bSTR3197 = ""
Dim bSTR3198
bSTR3198 = ""
Dim boolean1599
settingRepository1.GetAttrInfo "MAGNETICFLUXDENSITY_ExtraLarge", bSTR3197, bSTR3198, boolean1599
'--------------------------------------------------
' Parameter 1 : (String) "MAGNETICFLUXDENSITY_ExtraLarge"
' Parameter 2 : (String) "Default value"
' Parameter 3 : (String) "Unlocked"
' Parameter 4 : (Boolean) False
'--------------------------------------------------

long1600 = settingRepository1.GetAttr("MAGNETICFLUXDENSITY_Small")
'--------------------------------------------------
' Parameter 1 : (String) "MAGNETICFLUXDENSITY_Small"
' Returned value : (Variant) (Long) 1
'--------------------------------------------------

Dim bSTR3199
bSTR3199 = ""
Dim bSTR3200
bSTR3200 = ""
Dim boolean1600
settingRepository1.GetAttrInfo "MAGNETICFLUXDENSITY_Small", bSTR3199, bSTR3200, boolean1600
'--------------------------------------------------
' Parameter 1 : (String) "MAGNETICFLUXDENSITY_Small"
' Parameter 2 : (String) "Default value"
' Parameter 3 : (String) "Unlocked"
' Parameter 4 : (Boolean) False
'--------------------------------------------------

long1601 = settingRepository1.GetAttr("MAGNETICFLUXDENSITY_ExtraSmall")
'--------------------------------------------------
' Parameter 1 : (String) "MAGNETICFLUXDENSITY_ExtraSmall"
' Returned value : (Variant) (Long) 1
'--------------------------------------------------

Dim bSTR3201
bSTR3201 = ""
Dim bSTR3202
bSTR3202 = ""
Dim boolean1601
settingRepository1.GetAttrInfo "MAGNETICFLUXDENSITY_ExtraSmall", bSTR3201, bSTR3202, boolean1601
'--------------------------------------------------
' Parameter 1 : (String) "MAGNETICFLUXDENSITY_ExtraSmall"
' Parameter 2 : (String) "Default value"
' Parameter 3 : (String) "Unlocked"
' Parameter 4 : (Boolean) False
'--------------------------------------------------

long1602 = settingRepository1.GetAttr("MAGNETICFLUXDENSITY_Nanometric")
'--------------------------------------------------
' Parameter 1 : (String) "MAGNETICFLUXDENSITY_Nanometric"
' Returned value : (Variant) (Long) 1
'--------------------------------------------------

Dim bSTR3203
bSTR3203 = ""
Dim bSTR3204
bSTR3204 = ""
Dim boolean1602
settingRepository1.GetAttrInfo "MAGNETICFLUXDENSITY_Nanometric", bSTR3203, bSTR3204, boolean1602
'--------------------------------------------------
' Parameter 1 : (String) "MAGNETICFLUXDENSITY_Nanometric"
' Parameter 2 : (String) "Default value"
' Parameter 3 : (String) "Unlocked"
' Parameter 4 : (Boolean) False
'--------------------------------------------------

long1603 = settingRepository1.GetAttr("MAGNETICFLUX")
'--------------------------------------------------
' Parameter 1 : (String) "MAGNETICFLUX"
' Returned value : (Variant) (Long) 1
'--------------------------------------------------

Dim bSTR3205
bSTR3205 = ""
Dim bSTR3206
bSTR3206 = ""
Dim boolean1603
settingRepository1.GetAttrInfo "MAGNETICFLUX", bSTR3205, bSTR3206, boolean1603
'--------------------------------------------------
' Parameter 1 : (String) "MAGNETICFLUX"
' Parameter 2 : (String) "Default value"
' Parameter 3 : (String) "Unlocked"
' Parameter 4 : (Boolean) False
'--------------------------------------------------

long1604 = settingRepository1.GetAttr("MAGNETICFLUX_Large")
'--------------------------------------------------
' Parameter 1 : (String) "MAGNETICFLUX_Large"
' Returned value : (Variant) (Long) 1
'--------------------------------------------------

Dim bSTR3207
bSTR3207 = ""
Dim bSTR3208
bSTR3208 = ""
Dim boolean1604
settingRepository1.GetAttrInfo "MAGNETICFLUX_Large", bSTR3207, bSTR3208, boolean1604
'--------------------------------------------------
' Parameter 1 : (String) "MAGNETICFLUX_Large"
' Parameter 2 : (String) "Default value"
' Parameter 3 : (String) "Unlocked"
' Parameter 4 : (Boolean) False
'--------------------------------------------------

long1605 = settingRepository1.GetAttr("MAGNETICFLUX_ExtraLarge")
'--------------------------------------------------
' Parameter 1 : (String) "MAGNETICFLUX_ExtraLarge"
' Returned value : (Variant) (Long) 1
'--------------------------------------------------

Dim bSTR3209
bSTR3209 = ""
Dim bSTR3210
bSTR3210 = ""
Dim boolean1605
settingRepository1.GetAttrInfo "MAGNETICFLUX_ExtraLarge", bSTR3209, bSTR3210, boolean1605
'--------------------------------------------------
' Parameter 1 : (String) "MAGNETICFLUX_ExtraLarge"
' Parameter 2 : (String) "Default value"
' Parameter 3 : (String) "Unlocked"
' Parameter 4 : (Boolean) False
'--------------------------------------------------

long1606 = settingRepository1.GetAttr("MAGNETICFLUX_Small")
'--------------------------------------------------
' Parameter 1 : (String) "MAGNETICFLUX_Small"
' Returned value : (Variant) (Long) 1
'--------------------------------------------------

Dim bSTR3211
bSTR3211 = ""
Dim bSTR3212
bSTR3212 = ""
Dim boolean1606
settingRepository1.GetAttrInfo "MAGNETICFLUX_Small", bSTR3211, bSTR3212, boolean1606
'--------------------------------------------------
' Parameter 1 : (String) "MAGNETICFLUX_Small"
' Parameter 2 : (String) "Default value"
' Parameter 3 : (String) "Unlocked"
' Parameter 4 : (Boolean) False
'--------------------------------------------------

long1607 = settingRepository1.GetAttr("MAGNETICFLUX_ExtraSmall")
'--------------------------------------------------
' Parameter 1 : (String) "MAGNETICFLUX_ExtraSmall"
' Returned value : (Variant) (Long) 1
'--------------------------------------------------

Dim bSTR3213
bSTR3213 = ""
Dim bSTR3214
bSTR3214 = ""
Dim boolean1607
settingRepository1.GetAttrInfo "MAGNETICFLUX_ExtraSmall", bSTR3213, bSTR3214, boolean1607
'--------------------------------------------------
' Parameter 1 : (String) "MAGNETICFLUX_ExtraSmall"
' Parameter 2 : (String) "Default value"
' Parameter 3 : (String) "Unlocked"
' Parameter 4 : (Boolean) False
'--------------------------------------------------

long1608 = settingRepository1.GetAttr("MAGNETICFLUX_Nanometric")
'--------------------------------------------------
' Parameter 1 : (String) "MAGNETICFLUX_Nanometric"
' Returned value : (Variant) (Long) 1
'--------------------------------------------------

Dim bSTR3215
bSTR3215 = ""
Dim bSTR3216
bSTR3216 = ""
Dim boolean1608
settingRepository1.GetAttrInfo "MAGNETICFLUX_Nanometric", bSTR3215, bSTR3216, boolean1608
'--------------------------------------------------
' Parameter 1 : (String) "MAGNETICFLUX_Nanometric"
' Parameter 2 : (String) "Default value"
' Parameter 3 : (String) "Unlocked"
' Parameter 4 : (Boolean) False
'--------------------------------------------------

long1609 = settingRepository1.GetAttr("MAGNETICVECTORPOTENTIAL")
'--------------------------------------------------
' Parameter 1 : (String) "MAGNETICVECTORPOTENTIAL"
' Returned value : (Variant) (Long) 1
'--------------------------------------------------

Dim bSTR3217
bSTR3217 = ""
Dim bSTR3218
bSTR3218 = ""
Dim boolean1609
settingRepository1.GetAttrInfo "MAGNETICVECTORPOTENTIAL", bSTR3217, bSTR3218, boolean1609
'--------------------------------------------------
' Parameter 1 : (String) "MAGNETICVECTORPOTENTIAL"
' Parameter 2 : (String) "Default value"
' Parameter 3 : (String) "Unlocked"
' Parameter 4 : (Boolean) False
'--------------------------------------------------

long1610 = settingRepository1.GetAttr("MAGNETICVECTORPOTENTIAL_Large")
'--------------------------------------------------
' Parameter 1 : (String) "MAGNETICVECTORPOTENTIAL_Large"
' Returned value : (Variant) (Long) 1
'--------------------------------------------------

Dim bSTR3219
bSTR3219 = ""
Dim bSTR3220
bSTR3220 = ""
Dim boolean1610
settingRepository1.GetAttrInfo "MAGNETICVECTORPOTENTIAL_Large", bSTR3219, bSTR3220, boolean1610
'--------------------------------------------------
' Parameter 1 : (String) "MAGNETICVECTORPOTENTIAL_Large"
' Parameter 2 : (String) "Default value"
' Parameter 3 : (String) "Unlocked"
' Parameter 4 : (Boolean) False
'--------------------------------------------------

long1611 = settingRepository1.GetAttr("MAGNETICVECTORPOTENTIAL_ExtraLarge")
'--------------------------------------------------
' Parameter 1 : (String) "MAGNETICVECTORPOTENTIAL_ExtraLarge"
' Returned value : (Variant) (Long) 1
'--------------------------------------------------

Dim bSTR3221
bSTR3221 = ""
Dim bSTR3222
bSTR3222 = ""
Dim boolean1611
settingRepository1.GetAttrInfo "MAGNETICVECTORPOTENTIAL_ExtraLarge", bSTR3221, bSTR3222, boolean1611
'--------------------------------------------------
' Parameter 1 : (String) "MAGNETICVECTORPOTENTIAL_ExtraLarge"
' Parameter 2 : (String) "Default value"
' Parameter 3 : (String) "Unlocked"
' Parameter 4 : (Boolean) False
'--------------------------------------------------

long1612 = settingRepository1.GetAttr("MAGNETICVECTORPOTENTIAL_Small")
'--------------------------------------------------
' Parameter 1 : (String) "MAGNETICVECTORPOTENTIAL_Small"
' Returned value : (Variant) (Long) 1
'--------------------------------------------------

Dim bSTR3223
bSTR3223 = ""
Dim bSTR3224
bSTR3224 = ""
Dim boolean1612
settingRepository1.GetAttrInfo "MAGNETICVECTORPOTENTIAL_Small", bSTR3223, bSTR3224, boolean1612
'--------------------------------------------------
' Parameter 1 : (String) "MAGNETICVECTORPOTENTIAL_Small"
' Parameter 2 : (String) "Default value"
' Parameter 3 : (String) "Unlocked"
' Parameter 4 : (Boolean) False
'--------------------------------------------------

long1613 = settingRepository1.GetAttr("MAGNETICVECTORPOTENTIAL_ExtraSmall")
'--------------------------------------------------
' Parameter 1 : (String) "MAGNETICVECTORPOTENTIAL_ExtraSmall"
' Returned value : (Variant) (Long) 1
'--------------------------------------------------

Dim bSTR3225
bSTR3225 = ""
Dim bSTR3226
bSTR3226 = ""
Dim boolean1613
settingRepository1.GetAttrInfo "MAGNETICVECTORPOTENTIAL_ExtraSmall", bSTR3225, bSTR3226, boolean1613
'--------------------------------------------------
' Parameter 1 : (String) "MAGNETICVECTORPOTENTIAL_ExtraSmall"
' Parameter 2 : (String) "Default value"
' Parameter 3 : (String) "Unlocked"
' Parameter 4 : (Boolean) False
'--------------------------------------------------

long1614 = settingRepository1.GetAttr("MAGNETICVECTORPOTENTIAL_Nanometric")
'--------------------------------------------------
' Parameter 1 : (String) "MAGNETICVECTORPOTENTIAL_Nanometric"
' Returned value : (Variant) (Long) 1
'--------------------------------------------------

Dim bSTR3227
bSTR3227 = ""
Dim bSTR3228
bSTR3228 = ""
Dim boolean1614
settingRepository1.GetAttrInfo "MAGNETICVECTORPOTENTIAL_Nanometric", bSTR3227, bSTR3228, boolean1614
'--------------------------------------------------
' Parameter 1 : (String) "MAGNETICVECTORPOTENTIAL_Nanometric"
' Parameter 2 : (String) "Default value"
' Parameter 3 : (String) "Unlocked"
' Parameter 4 : (Boolean) False
'--------------------------------------------------

long1615 = settingRepository1.GetAttr("INDUCTANCE")
'--------------------------------------------------
' Parameter 1 : (String) "INDUCTANCE"
' Returned value : (Variant) (Long) 1
'--------------------------------------------------

Dim bSTR3229
bSTR3229 = ""
Dim bSTR3230
bSTR3230 = ""
Dim boolean1615
settingRepository1.GetAttrInfo "INDUCTANCE", bSTR3229, bSTR3230, boolean1615
'--------------------------------------------------
' Parameter 1 : (String) "INDUCTANCE"
' Parameter 2 : (String) "Default value"
' Parameter 3 : (String) "Unlocked"
' Parameter 4 : (Boolean) False
'--------------------------------------------------

long1616 = settingRepository1.GetAttr("INDUCTANCE_Large")
'--------------------------------------------------
' Parameter 1 : (String) "INDUCTANCE_Large"
' Returned value : (Variant) (Long) 1
'--------------------------------------------------

Dim bSTR3231
bSTR3231 = ""
Dim bSTR3232
bSTR3232 = ""
Dim boolean1616
settingRepository1.GetAttrInfo "INDUCTANCE_Large", bSTR3231, bSTR3232, boolean1616
'--------------------------------------------------
' Parameter 1 : (String) "INDUCTANCE_Large"
' Parameter 2 : (String) "Default value"
' Parameter 3 : (String) "Unlocked"
' Parameter 4 : (Boolean) False
'--------------------------------------------------

long1617 = settingRepository1.GetAttr("INDUCTANCE_ExtraLarge")
'--------------------------------------------------
' Parameter 1 : (String) "INDUCTANCE_ExtraLarge"
' Returned value : (Variant) (Long) 1
'--------------------------------------------------

Dim bSTR3233
bSTR3233 = ""
Dim bSTR3234
bSTR3234 = ""
Dim boolean1617
settingRepository1.GetAttrInfo "INDUCTANCE_ExtraLarge", bSTR3233, bSTR3234, boolean1617
'--------------------------------------------------
' Parameter 1 : (String) "INDUCTANCE_ExtraLarge"
' Parameter 2 : (String) "Default value"
' Parameter 3 : (String) "Unlocked"
' Parameter 4 : (Boolean) False
'--------------------------------------------------

long1618 = settingRepository1.GetAttr("INDUCTANCE_Small")
'--------------------------------------------------
' Parameter 1 : (String) "INDUCTANCE_Small"
' Returned value : (Variant) (Long) 1
'--------------------------------------------------

Dim bSTR3235
bSTR3235 = ""
Dim bSTR3236
bSTR3236 = ""
Dim boolean1618
settingRepository1.GetAttrInfo "INDUCTANCE_Small", bSTR3235, bSTR3236, boolean1618
'--------------------------------------------------
' Parameter 1 : (String) "INDUCTANCE_Small"
' Parameter 2 : (String) "Default value"
' Parameter 3 : (String) "Unlocked"
' Parameter 4 : (Boolean) False
'--------------------------------------------------

long1619 = settingRepository1.GetAttr("INDUCTANCE_ExtraSmall")
'--------------------------------------------------
' Parameter 1 : (String) "INDUCTANCE_ExtraSmall"
' Returned value : (Variant) (Long) 1
'--------------------------------------------------

Dim bSTR3237
bSTR3237 = ""
Dim bSTR3238
bSTR3238 = ""
Dim boolean1619
settingRepository1.GetAttrInfo "INDUCTANCE_ExtraSmall", bSTR3237, bSTR3238, boolean1619
'--------------------------------------------------
' Parameter 1 : (String) "INDUCTANCE_ExtraSmall"
' Parameter 2 : (String) "Default value"
' Parameter 3 : (String) "Unlocked"
' Parameter 4 : (Boolean) False
'--------------------------------------------------

long1620 = settingRepository1.GetAttr("INDUCTANCE_Nanometric")
'--------------------------------------------------
' Parameter 1 : (String) "INDUCTANCE_Nanometric"
' Returned value : (Variant) (Long) 1
'--------------------------------------------------

Dim bSTR3239
bSTR3239 = ""
Dim bSTR3240
bSTR3240 = ""
Dim boolean1620
settingRepository1.GetAttrInfo "INDUCTANCE_Nanometric", bSTR3239, bSTR3240, boolean1620
'--------------------------------------------------
' Parameter 1 : (String) "INDUCTANCE_Nanometric"
' Parameter 2 : (String) "Default value"
' Parameter 3 : (String) "Unlocked"
' Parameter 4 : (Boolean) False
'--------------------------------------------------

long1621 = settingRepository1.GetAttr("ELECTROMAGNETICMOMENT")
'--------------------------------------------------
' Parameter 1 : (String) "ELECTROMAGNETICMOMENT"
' Returned value : (Variant) (Long) 1
'--------------------------------------------------

Dim bSTR3241
bSTR3241 = ""
Dim bSTR3242
bSTR3242 = ""
Dim boolean1621
settingRepository1.GetAttrInfo "ELECTROMAGNETICMOMENT", bSTR3241, bSTR3242, boolean1621
'--------------------------------------------------
' Parameter 1 : (String) "ELECTROMAGNETICMOMENT"
' Parameter 2 : (String) "Default value"
' Parameter 3 : (String) "Unlocked"
' Parameter 4 : (Boolean) False
'--------------------------------------------------

long1622 = settingRepository1.GetAttr("ELECTROMAGNETICMOMENT_Large")
'--------------------------------------------------
' Parameter 1 : (String) "ELECTROMAGNETICMOMENT_Large"
' Returned value : (Variant) (Long) 1
'--------------------------------------------------

Dim bSTR3243
bSTR3243 = ""
Dim bSTR3244
bSTR3244 = ""
Dim boolean1622
settingRepository1.GetAttrInfo "ELECTROMAGNETICMOMENT_Large", bSTR3243, bSTR3244, boolean1622
'--------------------------------------------------
' Parameter 1 : (String) "ELECTROMAGNETICMOMENT_Large"
' Parameter 2 : (String) "Default value"
' Parameter 3 : (String) "Unlocked"
' Parameter 4 : (Boolean) False
'--------------------------------------------------

long1623 = settingRepository1.GetAttr("ELECTROMAGNETICMOMENT_ExtraLarge")
'--------------------------------------------------
' Parameter 1 : (String) "ELECTROMAGNETICMOMENT_ExtraLarge"
' Returned value : (Variant) (Long) 1
'--------------------------------------------------

Dim bSTR3245
bSTR3245 = ""
Dim bSTR3246
bSTR3246 = ""
Dim boolean1623
settingRepository1.GetAttrInfo "ELECTROMAGNETICMOMENT_ExtraLarge", bSTR3245, bSTR3246, boolean1623
'--------------------------------------------------
' Parameter 1 : (String) "ELECTROMAGNETICMOMENT_ExtraLarge"
' Parameter 2 : (String) "Default value"
' Parameter 3 : (String) "Unlocked"
' Parameter 4 : (Boolean) False
'--------------------------------------------------

long1624 = settingRepository1.GetAttr("ELECTROMAGNETICMOMENT_Small")
'--------------------------------------------------
' Parameter 1 : (String) "ELECTROMAGNETICMOMENT_Small"
' Returned value : (Variant) (Long) 1
'--------------------------------------------------

Dim bSTR3247
bSTR3247 = ""
Dim bSTR3248
bSTR3248 = ""
Dim boolean1624
settingRepository1.GetAttrInfo "ELECTROMAGNETICMOMENT_Small", bSTR3247, bSTR3248, boolean1624
'--------------------------------------------------
' Parameter 1 : (String) "ELECTROMAGNETICMOMENT_Small"
' Parameter 2 : (String) "Default value"
' Parameter 3 : (String) "Unlocked"
' Parameter 4 : (Boolean) False
'--------------------------------------------------

long1625 = settingRepository1.GetAttr("ELECTROMAGNETICMOMENT_ExtraSmall")
'--------------------------------------------------
' Parameter 1 : (String) "ELECTROMAGNETICMOMENT_ExtraSmall"
' Returned value : (Variant) (Long) 1
'--------------------------------------------------

Dim bSTR3249
bSTR3249 = ""
Dim bSTR3250
bSTR3250 = ""
Dim boolean1625
settingRepository1.GetAttrInfo "ELECTROMAGNETICMOMENT_ExtraSmall", bSTR3249, bSTR3250, boolean1625
'--------------------------------------------------
' Parameter 1 : (String) "ELECTROMAGNETICMOMENT_ExtraSmall"
' Parameter 2 : (String) "Default value"
' Parameter 3 : (String) "Unlocked"
' Parameter 4 : (Boolean) False
'--------------------------------------------------

long1626 = settingRepository1.GetAttr("ELECTROMAGNETICMOMENT_Nanometric")
'--------------------------------------------------
' Parameter 1 : (String) "ELECTROMAGNETICMOMENT_Nanometric"
' Returned value : (Variant) (Long) 1
'--------------------------------------------------

Dim bSTR3251
bSTR3251 = ""
Dim bSTR3252
bSTR3252 = ""
Dim boolean1626
settingRepository1.GetAttrInfo "ELECTROMAGNETICMOMENT_Nanometric", bSTR3251, bSTR3252, boolean1626
'--------------------------------------------------
' Parameter 1 : (String) "ELECTROMAGNETICMOMENT_Nanometric"
' Parameter 2 : (String) "Default value"
' Parameter 3 : (String) "Unlocked"
' Parameter 4 : (Boolean) False
'--------------------------------------------------

long1627 = settingRepository1.GetAttr("MAGNETICDIPOLEMOMENT")
'--------------------------------------------------
' Parameter 1 : (String) "MAGNETICDIPOLEMOMENT"
' Returned value : (Variant) (Long) 1
'--------------------------------------------------

Dim bSTR3253
bSTR3253 = ""
Dim bSTR3254
bSTR3254 = ""
Dim boolean1627
settingRepository1.GetAttrInfo "MAGNETICDIPOLEMOMENT", bSTR3253, bSTR3254, boolean1627
'--------------------------------------------------
' Parameter 1 : (String) "MAGNETICDIPOLEMOMENT"
' Parameter 2 : (String) "Default value"
' Parameter 3 : (String) "Unlocked"
' Parameter 4 : (Boolean) False
'--------------------------------------------------

long1628 = settingRepository1.GetAttr("MAGNETICDIPOLEMOMENT_Large")
'--------------------------------------------------
' Parameter 1 : (String) "MAGNETICDIPOLEMOMENT_Large"
' Returned value : (Variant) (Long) 1
'--------------------------------------------------

Dim bSTR3255
bSTR3255 = ""
Dim bSTR3256
bSTR3256 = ""
Dim boolean1628
settingRepository1.GetAttrInfo "MAGNETICDIPOLEMOMENT_Large", bSTR3255, bSTR3256, boolean1628
'--------------------------------------------------
' Parameter 1 : (String) "MAGNETICDIPOLEMOMENT_Large"
' Parameter 2 : (String) "Default value"
' Parameter 3 : (String) "Unlocked"
' Parameter 4 : (Boolean) False
'--------------------------------------------------

long1629 = settingRepository1.GetAttr("MAGNETICDIPOLEMOMENT_ExtraLarge")
'--------------------------------------------------
' Parameter 1 : (String) "MAGNETICDIPOLEMOMENT_ExtraLarge"
' Returned value : (Variant) (Long) 1
'--------------------------------------------------

Dim bSTR3257
bSTR3257 = ""
Dim bSTR3258
bSTR3258 = ""
Dim boolean1629
settingRepository1.GetAttrInfo "MAGNETICDIPOLEMOMENT_ExtraLarge", bSTR3257, bSTR3258, boolean1629
'--------------------------------------------------
' Parameter 1 : (String) "MAGNETICDIPOLEMOMENT_ExtraLarge"
' Parameter 2 : (String) "Default value"
' Parameter 3 : (String) "Unlocked"
' Parameter 4 : (Boolean) False
'--------------------------------------------------

long1630 = settingRepository1.GetAttr("MAGNETICDIPOLEMOMENT_Small")
'--------------------------------------------------
' Parameter 1 : (String) "MAGNETICDIPOLEMOMENT_Small"
' Returned value : (Variant) (Long) 1
'--------------------------------------------------

Dim bSTR3259
bSTR3259 = ""
Dim bSTR3260
bSTR3260 = ""
Dim boolean1630
settingRepository1.GetAttrInfo "MAGNETICDIPOLEMOMENT_Small", bSTR3259, bSTR3260, boolean1630
'--------------------------------------------------
' Parameter 1 : (String) "MAGNETICDIPOLEMOMENT_Small"
' Parameter 2 : (String) "Default value"
' Parameter 3 : (String) "Unlocked"
' Parameter 4 : (Boolean) False
'--------------------------------------------------

long1631 = settingRepository1.GetAttr("MAGNETICDIPOLEMOMENT_ExtraSmall")
'--------------------------------------------------
' Parameter 1 : (String) "MAGNETICDIPOLEMOMENT_ExtraSmall"
' Returned value : (Variant) (Long) 1
'--------------------------------------------------

Dim bSTR3261
bSTR3261 = ""
Dim bSTR3262
bSTR3262 = ""
Dim boolean1631
settingRepository1.GetAttrInfo "MAGNETICDIPOLEMOMENT_ExtraSmall", bSTR3261, bSTR3262, boolean1631
'--------------------------------------------------
' Parameter 1 : (String) "MAGNETICDIPOLEMOMENT_ExtraSmall"
' Parameter 2 : (String) "Default value"
' Parameter 3 : (String) "Unlocked"
' Parameter 4 : (Boolean) False
'--------------------------------------------------

long1632 = settingRepository1.GetAttr("MAGNETICDIPOLEMOMENT_Nanometric")
'--------------------------------------------------
' Parameter 1 : (String) "MAGNETICDIPOLEMOMENT_Nanometric"
' Returned value : (Variant) (Long) 1
'--------------------------------------------------

Dim bSTR3263
bSTR3263 = ""
Dim bSTR3264
bSTR3264 = ""
Dim boolean1632
settingRepository1.GetAttrInfo "MAGNETICDIPOLEMOMENT_Nanometric", bSTR3263, bSTR3264, boolean1632
'--------------------------------------------------
' Parameter 1 : (String) "MAGNETICDIPOLEMOMENT_Nanometric"
' Parameter 2 : (String) "Default value"
' Parameter 3 : (String) "Unlocked"
' Parameter 4 : (Boolean) False
'--------------------------------------------------

long1633 = settingRepository1.GetAttr("MAGNETIZATION")
'--------------------------------------------------
' Parameter 1 : (String) "MAGNETIZATION"
' Returned value : (Variant) (Long) 1
'--------------------------------------------------

Dim bSTR3265
bSTR3265 = ""
Dim bSTR3266
bSTR3266 = ""
Dim boolean1633
settingRepository1.GetAttrInfo "MAGNETIZATION", bSTR3265, bSTR3266, boolean1633
'--------------------------------------------------
' Parameter 1 : (String) "MAGNETIZATION"
' Parameter 2 : (String) "Default value"
' Parameter 3 : (String) "Unlocked"
' Parameter 4 : (Boolean) False
'--------------------------------------------------

long1634 = settingRepository1.GetAttr("MAGNETIZATION_Large")
'--------------------------------------------------
' Parameter 1 : (String) "MAGNETIZATION_Large"
' Returned value : (Variant) (Long) 1
'--------------------------------------------------

Dim bSTR3267
bSTR3267 = ""
Dim bSTR3268
bSTR3268 = ""
Dim boolean1634
settingRepository1.GetAttrInfo "MAGNETIZATION_Large", bSTR3267, bSTR3268, boolean1634
'--------------------------------------------------
' Parameter 1 : (String) "MAGNETIZATION_Large"
' Parameter 2 : (String) "Default value"
' Parameter 3 : (String) "Unlocked"
' Parameter 4 : (Boolean) False
'--------------------------------------------------

long1635 = settingRepository1.GetAttr("MAGNETIZATION_ExtraLarge")
'--------------------------------------------------
' Parameter 1 : (String) "MAGNETIZATION_ExtraLarge"
' Returned value : (Variant) (Long) 1
'--------------------------------------------------

Dim bSTR3269
bSTR3269 = ""
Dim bSTR3270
bSTR3270 = ""
Dim boolean1635
settingRepository1.GetAttrInfo "MAGNETIZATION_ExtraLarge", bSTR3269, bSTR3270, boolean1635
'--------------------------------------------------
' Parameter 1 : (String) "MAGNETIZATION_ExtraLarge"
' Parameter 2 : (String) "Default value"
' Parameter 3 : (String) "Unlocked"
' Parameter 4 : (Boolean) False
'--------------------------------------------------

long1636 = settingRepository1.GetAttr("MAGNETIZATION_Small")
'--------------------------------------------------
' Parameter 1 : (String) "MAGNETIZATION_Small"
' Returned value : (Variant) (Long) 1
'--------------------------------------------------

Dim bSTR3271
bSTR3271 = ""
Dim bSTR3272
bSTR3272 = ""
Dim boolean1636
settingRepository1.GetAttrInfo "MAGNETIZATION_Small", bSTR3271, bSTR3272, boolean1636
'--------------------------------------------------
' Parameter 1 : (String) "MAGNETIZATION_Small"
' Parameter 2 : (String) "Default value"
' Parameter 3 : (String) "Unlocked"
' Parameter 4 : (Boolean) False
'--------------------------------------------------

long1637 = settingRepository1.GetAttr("MAGNETIZATION_ExtraSmall")
'--------------------------------------------------
' Parameter 1 : (String) "MAGNETIZATION_ExtraSmall"
' Returned value : (Variant) (Long) 1
'--------------------------------------------------

Dim bSTR3273
bSTR3273 = ""
Dim bSTR3274
bSTR3274 = ""
Dim boolean1637
settingRepository1.GetAttrInfo "MAGNETIZATION_ExtraSmall", bSTR3273, bSTR3274, boolean1637
'--------------------------------------------------
' Parameter 1 : (String) "MAGNETIZATION_ExtraSmall"
' Parameter 2 : (String) "Default value"
' Parameter 3 : (String) "Unlocked"
' Parameter 4 : (Boolean) False
'--------------------------------------------------

long1638 = settingRepository1.GetAttr("MAGNETIZATION_Nanometric")
'--------------------------------------------------
' Parameter 1 : (String) "MAGNETIZATION_Nanometric"
' Returned value : (Variant) (Long) 1
'--------------------------------------------------

Dim bSTR3275
bSTR3275 = ""
Dim bSTR3276
bSTR3276 = ""
Dim boolean1638
settingRepository1.GetAttrInfo "MAGNETIZATION_Nanometric", bSTR3275, bSTR3276, boolean1638
'--------------------------------------------------
' Parameter 1 : (String) "MAGNETIZATION_Nanometric"
' Parameter 2 : (String) "Default value"
' Parameter 3 : (String) "Unlocked"
' Parameter 4 : (Boolean) False
'--------------------------------------------------

long1639 = settingRepository1.GetAttr("MAGNETICPOLARIZATION")
'--------------------------------------------------
' Parameter 1 : (String) "MAGNETICPOLARIZATION"
' Returned value : (Variant) (Long) 1
'--------------------------------------------------

Dim bSTR3277
bSTR3277 = ""
Dim bSTR3278
bSTR3278 = ""
Dim boolean1639
settingRepository1.GetAttrInfo "MAGNETICPOLARIZATION", bSTR3277, bSTR3278, boolean1639
'--------------------------------------------------
' Parameter 1 : (String) "MAGNETICPOLARIZATION"
' Parameter 2 : (String) "Default value"
' Parameter 3 : (String) "Unlocked"
' Parameter 4 : (Boolean) False
'--------------------------------------------------

long1640 = settingRepository1.GetAttr("MAGNETICPOLARIZATION_Large")
'--------------------------------------------------
' Parameter 1 : (String) "MAGNETICPOLARIZATION_Large"
' Returned value : (Variant) (Long) 1
'--------------------------------------------------

Dim bSTR3279
bSTR3279 = ""
Dim bSTR3280
bSTR3280 = ""
Dim boolean1640
settingRepository1.GetAttrInfo "MAGNETICPOLARIZATION_Large", bSTR3279, bSTR3280, boolean1640
'--------------------------------------------------
' Parameter 1 : (String) "MAGNETICPOLARIZATION_Large"
' Parameter 2 : (String) "Default value"
' Parameter 3 : (String) "Unlocked"
' Parameter 4 : (Boolean) False
'--------------------------------------------------

long1641 = settingRepository1.GetAttr("MAGNETICPOLARIZATION_ExtraLarge")
'--------------------------------------------------
' Parameter 1 : (String) "MAGNETICPOLARIZATION_ExtraLarge"
' Returned value : (Variant) (Long) 1
'--------------------------------------------------

Dim bSTR3281
bSTR3281 = ""
Dim bSTR3282
bSTR3282 = ""
Dim boolean1641
settingRepository1.GetAttrInfo "MAGNETICPOLARIZATION_ExtraLarge", bSTR3281, bSTR3282, boolean1641
'--------------------------------------------------
' Parameter 1 : (String) "MAGNETICPOLARIZATION_ExtraLarge"
' Parameter 2 : (String) "Default value"
' Parameter 3 : (String) "Unlocked"
' Parameter 4 : (Boolean) False
'--------------------------------------------------

long1642 = settingRepository1.GetAttr("MAGNETICPOLARIZATION_Small")
'--------------------------------------------------
' Parameter 1 : (String) "MAGNETICPOLARIZATION_Small"
' Returned value : (Variant) (Long) 1
'--------------------------------------------------

Dim bSTR3283
bSTR3283 = ""
Dim bSTR3284
bSTR3284 = ""
Dim boolean1642
settingRepository1.GetAttrInfo "MAGNETICPOLARIZATION_Small", bSTR3283, bSTR3284, boolean1642
'--------------------------------------------------
' Parameter 1 : (String) "MAGNETICPOLARIZATION_Small"
' Parameter 2 : (String) "Default value"
' Parameter 3 : (String) "Unlocked"
' Parameter 4 : (Boolean) False
'--------------------------------------------------

long1643 = settingRepository1.GetAttr("MAGNETICPOLARIZATION_ExtraSmall")
'--------------------------------------------------
' Parameter 1 : (String) "MAGNETICPOLARIZATION_ExtraSmall"
' Returned value : (Variant) (Long) 1
'--------------------------------------------------

Dim bSTR3285
bSTR3285 = ""
Dim bSTR3286
bSTR3286 = ""
Dim boolean1643
settingRepository1.GetAttrInfo "MAGNETICPOLARIZATION_ExtraSmall", bSTR3285, bSTR3286, boolean1643
'--------------------------------------------------
' Parameter 1 : (String) "MAGNETICPOLARIZATION_ExtraSmall"
' Parameter 2 : (String) "Default value"
' Parameter 3 : (String) "Unlocked"
' Parameter 4 : (Boolean) False
'--------------------------------------------------

long1644 = settingRepository1.GetAttr("MAGNETICPOLARIZATION_Nanometric")
'--------------------------------------------------
' Parameter 1 : (String) "MAGNETICPOLARIZATION_Nanometric"
' Returned value : (Variant) (Long) 1
'--------------------------------------------------

Dim bSTR3287
bSTR3287 = ""
Dim bSTR3288
bSTR3288 = ""
Dim boolean1644
settingRepository1.GetAttrInfo "MAGNETICPOLARIZATION_Nanometric", bSTR3287, bSTR3288, boolean1644
'--------------------------------------------------
' Parameter 1 : (String) "MAGNETICPOLARIZATION_Nanometric"
' Parameter 2 : (String) "Default value"
' Parameter 3 : (String) "Unlocked"
' Parameter 4 : (Boolean) False
'--------------------------------------------------

long1645 = settingRepository1.GetAttr("POYNTINGVECTOR")
'--------------------------------------------------
' Parameter 1 : (String) "POYNTINGVECTOR"
' Returned value : (Variant) (Long) 1
'--------------------------------------------------

Dim bSTR3289
bSTR3289 = ""
Dim bSTR3290
bSTR3290 = ""
Dim boolean1645
settingRepository1.GetAttrInfo "POYNTINGVECTOR", bSTR3289, bSTR3290, boolean1645
'--------------------------------------------------
' Parameter 1 : (String) "POYNTINGVECTOR"
' Parameter 2 : (String) "Default value"
' Parameter 3 : (String) "Unlocked"
' Parameter 4 : (Boolean) False
'--------------------------------------------------

long1646 = settingRepository1.GetAttr("POYNTINGVECTOR_Large")
'--------------------------------------------------
' Parameter 1 : (String) "POYNTINGVECTOR_Large"
' Returned value : (Variant) (Long) 1
'--------------------------------------------------

Dim bSTR3291
bSTR3291 = ""
Dim bSTR3292
bSTR3292 = ""
Dim boolean1646
settingRepository1.GetAttrInfo "POYNTINGVECTOR_Large", bSTR3291, bSTR3292, boolean1646
'--------------------------------------------------
' Parameter 1 : (String) "POYNTINGVECTOR_Large"
' Parameter 2 : (String) "Default value"
' Parameter 3 : (String) "Unlocked"
' Parameter 4 : (Boolean) False
'--------------------------------------------------

long1647 = settingRepository1.GetAttr("POYNTINGVECTOR_ExtraLarge")
'--------------------------------------------------
' Parameter 1 : (String) "POYNTINGVECTOR_ExtraLarge"
' Returned value : (Variant) (Long) 1
'--------------------------------------------------

Dim bSTR3293
bSTR3293 = ""
Dim bSTR3294
bSTR3294 = ""
Dim boolean1647
settingRepository1.GetAttrInfo "POYNTINGVECTOR_ExtraLarge", bSTR3293, bSTR3294, boolean1647
'--------------------------------------------------
' Parameter 1 : (String) "POYNTINGVECTOR_ExtraLarge"
' Parameter 2 : (String) "Default value"
' Parameter 3 : (String) "Unlocked"
' Parameter 4 : (Boolean) False
'--------------------------------------------------

long1648 = settingRepository1.GetAttr("POYNTINGVECTOR_Small")
'--------------------------------------------------
' Parameter 1 : (String) "POYNTINGVECTOR_Small"
' Returned value : (Variant) (Long) 1
'--------------------------------------------------

Dim bSTR3295
bSTR3295 = ""
Dim bSTR3296
bSTR3296 = ""
Dim boolean1648
settingRepository1.GetAttrInfo "POYNTINGVECTOR_Small", bSTR3295, bSTR3296, boolean1648
'--------------------------------------------------
' Parameter 1 : (String) "POYNTINGVECTOR_Small"
' Parameter 2 : (String) "Default value"
' Parameter 3 : (String) "Unlocked"
' Parameter 4 : (Boolean) False
'--------------------------------------------------

long1649 = settingRepository1.GetAttr("POYNTINGVECTOR_ExtraSmall")
'--------------------------------------------------
' Parameter 1 : (String) "POYNTINGVECTOR_ExtraSmall"
' Returned value : (Variant) (Long) 1
'--------------------------------------------------

Dim bSTR3297
bSTR3297 = ""
Dim bSTR3298
bSTR3298 = ""
Dim boolean1649
settingRepository1.GetAttrInfo "POYNTINGVECTOR_ExtraSmall", bSTR3297, bSTR3298, boolean1649
'--------------------------------------------------
' Parameter 1 : (String) "POYNTINGVECTOR_ExtraSmall"
' Parameter 2 : (String) "Default value"
' Parameter 3 : (String) "Unlocked"
' Parameter 4 : (Boolean) False
'--------------------------------------------------

long1650 = settingRepository1.GetAttr("POYNTINGVECTOR_Nanometric")
'--------------------------------------------------
' Parameter 1 : (String) "POYNTINGVECTOR_Nanometric"
' Returned value : (Variant) (Long) 1
'--------------------------------------------------

Dim bSTR3299
bSTR3299 = ""
Dim bSTR3300
bSTR3300 = ""
Dim boolean1650
settingRepository1.GetAttrInfo "POYNTINGVECTOR_Nanometric", bSTR3299, bSTR3300, boolean1650
'--------------------------------------------------
' Parameter 1 : (String) "POYNTINGVECTOR_Nanometric"
' Parameter 2 : (String) "Default value"
' Parameter 3 : (String) "Unlocked"
' Parameter 4 : (Boolean) False
'--------------------------------------------------

long1651 = settingRepository1.GetAttr("RESISTIVITY")
'--------------------------------------------------
' Parameter 1 : (String) "RESISTIVITY"
' Returned value : (Variant) (Long) 1
'--------------------------------------------------

Dim bSTR3301
bSTR3301 = ""
Dim bSTR3302
bSTR3302 = ""
Dim boolean1651
settingRepository1.GetAttrInfo "RESISTIVITY", bSTR3301, bSTR3302, boolean1651
'--------------------------------------------------
' Parameter 1 : (String) "RESISTIVITY"
' Parameter 2 : (String) "Default value"
' Parameter 3 : (String) "Unlocked"
' Parameter 4 : (Boolean) False
'--------------------------------------------------

long1652 = settingRepository1.GetAttr("RESISTIVITY_Large")
'--------------------------------------------------
' Parameter 1 : (String) "RESISTIVITY_Large"
' Returned value : (Variant) (Long) 1
'--------------------------------------------------

Dim bSTR3303
bSTR3303 = ""
Dim bSTR3304
bSTR3304 = ""
Dim boolean1652
settingRepository1.GetAttrInfo "RESISTIVITY_Large", bSTR3303, bSTR3304, boolean1652
'--------------------------------------------------
' Parameter 1 : (String) "RESISTIVITY_Large"
' Parameter 2 : (String) "Default value"
' Parameter 3 : (String) "Unlocked"
' Parameter 4 : (Boolean) False
'--------------------------------------------------

long1653 = settingRepository1.GetAttr("RESISTIVITY_ExtraLarge")
'--------------------------------------------------
' Parameter 1 : (String) "RESISTIVITY_ExtraLarge"
' Returned value : (Variant) (Long) 1
'--------------------------------------------------

Dim bSTR3305
bSTR3305 = ""
Dim bSTR3306
bSTR3306 = ""
Dim boolean1653
settingRepository1.GetAttrInfo "RESISTIVITY_ExtraLarge", bSTR3305, bSTR3306, boolean1653
'--------------------------------------------------
' Parameter 1 : (String) "RESISTIVITY_ExtraLarge"
' Parameter 2 : (String) "Default value"
' Parameter 3 : (String) "Unlocked"
' Parameter 4 : (Boolean) False
'--------------------------------------------------

long1654 = settingRepository1.GetAttr("RESISTIVITY_Small")
'--------------------------------------------------
' Parameter 1 : (String) "RESISTIVITY_Small"
' Returned value : (Variant) (Long) 1
'--------------------------------------------------

Dim bSTR3307
bSTR3307 = ""
Dim bSTR3308
bSTR3308 = ""
Dim boolean1654
settingRepository1.GetAttrInfo "RESISTIVITY_Small", bSTR3307, bSTR3308, boolean1654
'--------------------------------------------------
' Parameter 1 : (String) "RESISTIVITY_Small"
' Parameter 2 : (String) "Default value"
' Parameter 3 : (String) "Unlocked"
' Parameter 4 : (Boolean) False
'--------------------------------------------------

long1655 = settingRepository1.GetAttr("RESISTIVITY_ExtraSmall")
'--------------------------------------------------
' Parameter 1 : (String) "RESISTIVITY_ExtraSmall"
' Returned value : (Variant) (Long) 1
'--------------------------------------------------

Dim bSTR3309
bSTR3309 = ""
Dim bSTR3310
bSTR3310 = ""
Dim boolean1655
settingRepository1.GetAttrInfo "RESISTIVITY_ExtraSmall", bSTR3309, bSTR3310, boolean1655
'--------------------------------------------------
' Parameter 1 : (String) "RESISTIVITY_ExtraSmall"
' Parameter 2 : (String) "Default value"
' Parameter 3 : (String) "Unlocked"
' Parameter 4 : (Boolean) False
'--------------------------------------------------

long1656 = settingRepository1.GetAttr("RESISTIVITY_Nanometric")
'--------------------------------------------------
' Parameter 1 : (String) "RESISTIVITY_Nanometric"
' Returned value : (Variant) (Long) 1
'--------------------------------------------------

Dim bSTR3311
bSTR3311 = ""
Dim bSTR3312
bSTR3312 = ""
Dim boolean1656
settingRepository1.GetAttrInfo "RESISTIVITY_Nanometric", bSTR3311, bSTR3312, boolean1656
'--------------------------------------------------
' Parameter 1 : (String) "RESISTIVITY_Nanometric"
' Parameter 2 : (String) "Default value"
' Parameter 3 : (String) "Unlocked"
' Parameter 4 : (Boolean) False
'--------------------------------------------------

long1657 = settingRepository1.GetAttr("RELUCTANCE")
'--------------------------------------------------
' Parameter 1 : (String) "RELUCTANCE"
' Returned value : (Variant) (Long) 1
'--------------------------------------------------

Dim bSTR3313
bSTR3313 = ""
Dim bSTR3314
bSTR3314 = ""
Dim boolean1657
settingRepository1.GetAttrInfo "RELUCTANCE", bSTR3313, bSTR3314, boolean1657
'--------------------------------------------------
' Parameter 1 : (String) "RELUCTANCE"
' Parameter 2 : (String) "Default value"
' Parameter 3 : (String) "Unlocked"
' Parameter 4 : (Boolean) False
'--------------------------------------------------

long1658 = settingRepository1.GetAttr("RELUCTANCE_Large")
'--------------------------------------------------
' Parameter 1 : (String) "RELUCTANCE_Large"
' Returned value : (Variant) (Long) 1
'--------------------------------------------------

Dim bSTR3315
bSTR3315 = ""
Dim bSTR3316
bSTR3316 = ""
Dim boolean1658
settingRepository1.GetAttrInfo "RELUCTANCE_Large", bSTR3315, bSTR3316, boolean1658
'--------------------------------------------------
' Parameter 1 : (String) "RELUCTANCE_Large"
' Parameter 2 : (String) "Default value"
' Parameter 3 : (String) "Unlocked"
' Parameter 4 : (Boolean) False
'--------------------------------------------------

long1659 = settingRepository1.GetAttr("RELUCTANCE_ExtraLarge")
'--------------------------------------------------
' Parameter 1 : (String) "RELUCTANCE_ExtraLarge"
' Returned value : (Variant) (Long) 1
'--------------------------------------------------

Dim bSTR3317
bSTR3317 = ""
Dim bSTR3318
bSTR3318 = ""
Dim boolean1659
settingRepository1.GetAttrInfo "RELUCTANCE_ExtraLarge", bSTR3317, bSTR3318, boolean1659
'--------------------------------------------------
' Parameter 1 : (String) "RELUCTANCE_ExtraLarge"
' Parameter 2 : (String) "Default value"
' Parameter 3 : (String) "Unlocked"
' Parameter 4 : (Boolean) False
'--------------------------------------------------

long1660 = settingRepository1.GetAttr("RELUCTANCE_Small")
'--------------------------------------------------
' Parameter 1 : (String) "RELUCTANCE_Small"
' Returned value : (Variant) (Long) 1
'--------------------------------------------------

Dim bSTR3319
bSTR3319 = ""
Dim bSTR3320
bSTR3320 = ""
Dim boolean1660
settingRepository1.GetAttrInfo "RELUCTANCE_Small", bSTR3319, bSTR3320, boolean1660
'--------------------------------------------------
' Parameter 1 : (String) "RELUCTANCE_Small"
' Parameter 2 : (String) "Default value"
' Parameter 3 : (String) "Unlocked"
' Parameter 4 : (Boolean) False
'--------------------------------------------------

long1661 = settingRepository1.GetAttr("RELUCTANCE_ExtraSmall")
'--------------------------------------------------
' Parameter 1 : (String) "RELUCTANCE_ExtraSmall"
' Returned value : (Variant) (Long) 1
'--------------------------------------------------

Dim bSTR3321
bSTR3321 = ""
Dim bSTR3322
bSTR3322 = ""
Dim boolean1661
settingRepository1.GetAttrInfo "RELUCTANCE_ExtraSmall", bSTR3321, bSTR3322, boolean1661
'--------------------------------------------------
' Parameter 1 : (String) "RELUCTANCE_ExtraSmall"
' Parameter 2 : (String) "Default value"
' Parameter 3 : (String) "Unlocked"
' Parameter 4 : (Boolean) False
'--------------------------------------------------

long1662 = settingRepository1.GetAttr("RELUCTANCE_Nanometric")
'--------------------------------------------------
' Parameter 1 : (String) "RELUCTANCE_Nanometric"
' Returned value : (Variant) (Long) 1
'--------------------------------------------------

Dim bSTR3323
bSTR3323 = ""
Dim bSTR3324
bSTR3324 = ""
Dim boolean1662
settingRepository1.GetAttrInfo "RELUCTANCE_Nanometric", bSTR3323, bSTR3324, boolean1662
'--------------------------------------------------
' Parameter 1 : (String) "RELUCTANCE_Nanometric"
' Parameter 2 : (String) "Default value"
' Parameter 3 : (String) "Unlocked"
' Parameter 4 : (Boolean) False
'--------------------------------------------------

long1663 = settingRepository1.GetAttr("PERMEANCE")
'--------------------------------------------------
' Parameter 1 : (String) "PERMEANCE"
' Returned value : (Variant) (Long) 1
'--------------------------------------------------

Dim bSTR3325
bSTR3325 = ""
Dim bSTR3326
bSTR3326 = ""
Dim boolean1663
settingRepository1.GetAttrInfo "PERMEANCE", bSTR3325, bSTR3326, boolean1663
'--------------------------------------------------
' Parameter 1 : (String) "PERMEANCE"
' Parameter 2 : (String) "Default value"
' Parameter 3 : (String) "Unlocked"
' Parameter 4 : (Boolean) False
'--------------------------------------------------

long1664 = settingRepository1.GetAttr("PERMEANCE_Large")
'--------------------------------------------------
' Parameter 1 : (String) "PERMEANCE_Large"
' Returned value : (Variant) (Long) 1
'--------------------------------------------------

Dim bSTR3327
bSTR3327 = ""
Dim bSTR3328
bSTR3328 = ""
Dim boolean1664
settingRepository1.GetAttrInfo "PERMEANCE_Large", bSTR3327, bSTR3328, boolean1664
'--------------------------------------------------
' Parameter 1 : (String) "PERMEANCE_Large"
' Parameter 2 : (String) "Default value"
' Parameter 3 : (String) "Unlocked"
' Parameter 4 : (Boolean) False
'--------------------------------------------------

long1665 = settingRepository1.GetAttr("PERMEANCE_ExtraLarge")
'--------------------------------------------------
' Parameter 1 : (String) "PERMEANCE_ExtraLarge"
' Returned value : (Variant) (Long) 1
'--------------------------------------------------

Dim bSTR3329
bSTR3329 = ""
Dim bSTR3330
bSTR3330 = ""
Dim boolean1665
settingRepository1.GetAttrInfo "PERMEANCE_ExtraLarge", bSTR3329, bSTR3330, boolean1665
'--------------------------------------------------
' Parameter 1 : (String) "PERMEANCE_ExtraLarge"
' Parameter 2 : (String) "Default value"
' Parameter 3 : (String) "Unlocked"
' Parameter 4 : (Boolean) False
'--------------------------------------------------

long1666 = settingRepository1.GetAttr("PERMEANCE_Small")
'--------------------------------------------------
' Parameter 1 : (String) "PERMEANCE_Small"
' Returned value : (Variant) (Long) 1
'--------------------------------------------------

Dim bSTR3331
bSTR3331 = ""
Dim bSTR3332
bSTR3332 = ""
Dim boolean1666
settingRepository1.GetAttrInfo "PERMEANCE_Small", bSTR3331, bSTR3332, boolean1666
'--------------------------------------------------
' Parameter 1 : (String) "PERMEANCE_Small"
' Parameter 2 : (String) "Default value"
' Parameter 3 : (String) "Unlocked"
' Parameter 4 : (Boolean) False
'--------------------------------------------------

long1667 = settingRepository1.GetAttr("PERMEANCE_ExtraSmall")
'--------------------------------------------------
' Parameter 1 : (String) "PERMEANCE_ExtraSmall"
' Returned value : (Variant) (Long) 1
'--------------------------------------------------

Dim bSTR3333
bSTR3333 = ""
Dim bSTR3334
bSTR3334 = ""
Dim boolean1667
settingRepository1.GetAttrInfo "PERMEANCE_ExtraSmall", bSTR3333, bSTR3334, boolean1667
'--------------------------------------------------
' Parameter 1 : (String) "PERMEANCE_ExtraSmall"
' Parameter 2 : (String) "Default value"
' Parameter 3 : (String) "Unlocked"
' Parameter 4 : (Boolean) False
'--------------------------------------------------

long1668 = settingRepository1.GetAttr("PERMEANCE_Nanometric")
'--------------------------------------------------
' Parameter 1 : (String) "PERMEANCE_Nanometric"
' Returned value : (Variant) (Long) 1
'--------------------------------------------------

Dim bSTR3335
bSTR3335 = ""
Dim bSTR3336
bSTR3336 = ""
Dim boolean1668
settingRepository1.GetAttrInfo "PERMEANCE_Nanometric", bSTR3335, bSTR3336, boolean1668
'--------------------------------------------------
' Parameter 1 : (String) "PERMEANCE_Nanometric"
' Parameter 2 : (String) "Default value"
' Parameter 3 : (String) "Unlocked"
' Parameter 4 : (Boolean) False
'--------------------------------------------------

long1669 = settingRepository1.GetAttr("CONDUCTANCE")
'--------------------------------------------------
' Parameter 1 : (String) "CONDUCTANCE"
' Returned value : (Variant) (Long) 1
'--------------------------------------------------

Dim bSTR3337
bSTR3337 = ""
Dim bSTR3338
bSTR3338 = ""
Dim boolean1669
settingRepository1.GetAttrInfo "CONDUCTANCE", bSTR3337, bSTR3338, boolean1669
'--------------------------------------------------
' Parameter 1 : (String) "CONDUCTANCE"
' Parameter 2 : (String) "Default value"
' Parameter 3 : (String) "Unlocked"
' Parameter 4 : (Boolean) False
'--------------------------------------------------

long1670 = settingRepository1.GetAttr("CONDUCTANCE_Large")
'--------------------------------------------------
' Parameter 1 : (String) "CONDUCTANCE_Large"
' Returned value : (Variant) (Long) 1
'--------------------------------------------------

Dim bSTR3339
bSTR3339 = ""
Dim bSTR3340
bSTR3340 = ""
Dim boolean1670
settingRepository1.GetAttrInfo "CONDUCTANCE_Large", bSTR3339, bSTR3340, boolean1670
'--------------------------------------------------
' Parameter 1 : (String) "CONDUCTANCE_Large"
' Parameter 2 : (String) "Default value"
' Parameter 3 : (String) "Unlocked"
' Parameter 4 : (Boolean) False
'--------------------------------------------------

long1671 = settingRepository1.GetAttr("CONDUCTANCE_ExtraLarge")
'--------------------------------------------------
' Parameter 1 : (String) "CONDUCTANCE_ExtraLarge"
' Returned value : (Variant) (Long) 1
'--------------------------------------------------

Dim bSTR3341
bSTR3341 = ""
Dim bSTR3342
bSTR3342 = ""
Dim boolean1671
settingRepository1.GetAttrInfo "CONDUCTANCE_ExtraLarge", bSTR3341, bSTR3342, boolean1671
'--------------------------------------------------
' Parameter 1 : (String) "CONDUCTANCE_ExtraLarge"
' Parameter 2 : (String) "Default value"
' Parameter 3 : (String) "Unlocked"
' Parameter 4 : (Boolean) False
'--------------------------------------------------

long1672 = settingRepository1.GetAttr("CONDUCTANCE_Small")
'--------------------------------------------------
' Parameter 1 : (String) "CONDUCTANCE_Small"
' Returned value : (Variant) (Long) 1
'--------------------------------------------------

Dim bSTR3343
bSTR3343 = ""
Dim bSTR3344
bSTR3344 = ""
Dim boolean1672
settingRepository1.GetAttrInfo "CONDUCTANCE_Small", bSTR3343, bSTR3344, boolean1672
'--------------------------------------------------
' Parameter 1 : (String) "CONDUCTANCE_Small"
' Parameter 2 : (String) "Default value"
' Parameter 3 : (String) "Unlocked"
' Parameter 4 : (Boolean) False
'--------------------------------------------------

long1673 = settingRepository1.GetAttr("CONDUCTANCE_ExtraSmall")
'--------------------------------------------------
' Parameter 1 : (String) "CONDUCTANCE_ExtraSmall"
' Returned value : (Variant) (Long) 1
'--------------------------------------------------

Dim bSTR3345
bSTR3345 = ""
Dim bSTR3346
bSTR3346 = ""
Dim boolean1673
settingRepository1.GetAttrInfo "CONDUCTANCE_ExtraSmall", bSTR3345, bSTR3346, boolean1673
'--------------------------------------------------
' Parameter 1 : (String) "CONDUCTANCE_ExtraSmall"
' Parameter 2 : (String) "Default value"
' Parameter 3 : (String) "Unlocked"
' Parameter 4 : (Boolean) False
'--------------------------------------------------

long1674 = settingRepository1.GetAttr("CONDUCTANCE_Nanometric")
'--------------------------------------------------
' Parameter 1 : (String) "CONDUCTANCE_Nanometric"
' Returned value : (Variant) (Long) 1
'--------------------------------------------------

Dim bSTR3347
bSTR3347 = ""
Dim bSTR3348
bSTR3348 = ""
Dim boolean1674
settingRepository1.GetAttrInfo "CONDUCTANCE_Nanometric", bSTR3347, bSTR3348, boolean1674
'--------------------------------------------------
' Parameter 1 : (String) "CONDUCTANCE_Nanometric"
' Parameter 2 : (String) "Default value"
' Parameter 3 : (String) "Unlocked"
' Parameter 4 : (Boolean) False
'--------------------------------------------------

long1675 = settingRepository1.GetAttr("APPARENTPOWER")
'--------------------------------------------------
' Parameter 1 : (String) "APPARENTPOWER"
' Returned value : (Variant) (Long) 1
'--------------------------------------------------

Dim bSTR3349
bSTR3349 = ""
Dim bSTR3350
bSTR3350 = ""
Dim boolean1675
settingRepository1.GetAttrInfo "APPARENTPOWER", bSTR3349, bSTR3350, boolean1675
'--------------------------------------------------
' Parameter 1 : (String) "APPARENTPOWER"
' Parameter 2 : (String) "Default value"
' Parameter 3 : (String) "Unlocked"
' Parameter 4 : (Boolean) False
'--------------------------------------------------

long1676 = settingRepository1.GetAttr("APPARENTPOWER_Large")
'--------------------------------------------------
' Parameter 1 : (String) "APPARENTPOWER_Large"
' Returned value : (Variant) (Long) 1
'--------------------------------------------------

Dim bSTR3351
bSTR3351 = ""
Dim bSTR3352
bSTR3352 = ""
Dim boolean1676
settingRepository1.GetAttrInfo "APPARENTPOWER_Large", bSTR3351, bSTR3352, boolean1676
'--------------------------------------------------
' Parameter 1 : (String) "APPARENTPOWER_Large"
' Parameter 2 : (String) "Default value"
' Parameter 3 : (String) "Unlocked"
' Parameter 4 : (Boolean) False
'--------------------------------------------------

long1677 = settingRepository1.GetAttr("APPARENTPOWER_ExtraLarge")
'--------------------------------------------------
' Parameter 1 : (String) "APPARENTPOWER_ExtraLarge"
' Returned value : (Variant) (Long) 1
'--------------------------------------------------

Dim bSTR3353
bSTR3353 = ""
Dim bSTR3354
bSTR3354 = ""
Dim boolean1677
settingRepository1.GetAttrInfo "APPARENTPOWER_ExtraLarge", bSTR3353, bSTR3354, boolean1677
'--------------------------------------------------
' Parameter 1 : (String) "APPARENTPOWER_ExtraLarge"
' Parameter 2 : (String) "Default value"
' Parameter 3 : (String) "Unlocked"
' Parameter 4 : (Boolean) False
'--------------------------------------------------

long1678 = settingRepository1.GetAttr("APPARENTPOWER_Small")
'--------------------------------------------------
' Parameter 1 : (String) "APPARENTPOWER_Small"
' Returned value : (Variant) (Long) 1
'--------------------------------------------------

Dim bSTR3355
bSTR3355 = ""
Dim bSTR3356
bSTR3356 = ""
Dim boolean1678
settingRepository1.GetAttrInfo "APPARENTPOWER_Small", bSTR3355, bSTR3356, boolean1678
'--------------------------------------------------
' Parameter 1 : (String) "APPARENTPOWER_Small"
' Parameter 2 : (String) "Default value"
' Parameter 3 : (String) "Unlocked"
' Parameter 4 : (Boolean) False
'--------------------------------------------------

long1679 = settingRepository1.GetAttr("APPARENTPOWER_ExtraSmall")
'--------------------------------------------------
' Parameter 1 : (String) "APPARENTPOWER_ExtraSmall"
' Returned value : (Variant) (Long) 1
'--------------------------------------------------

Dim bSTR3357
bSTR3357 = ""
Dim bSTR3358
bSTR3358 = ""
Dim boolean1679
settingRepository1.GetAttrInfo "APPARENTPOWER_ExtraSmall", bSTR3357, bSTR3358, boolean1679
'--------------------------------------------------
' Parameter 1 : (String) "APPARENTPOWER_ExtraSmall"
' Parameter 2 : (String) "Default value"
' Parameter 3 : (String) "Unlocked"
' Parameter 4 : (Boolean) False
'--------------------------------------------------

long1680 = settingRepository1.GetAttr("APPARENTPOWER_Nanometric")
'--------------------------------------------------
' Parameter 1 : (String) "APPARENTPOWER_Nanometric"
' Returned value : (Variant) (Long) 1
'--------------------------------------------------

Dim bSTR3359
bSTR3359 = ""
Dim bSTR3360
bSTR3360 = ""
Dim boolean1680
settingRepository1.GetAttrInfo "APPARENTPOWER_Nanometric", bSTR3359, bSTR3360, boolean1680
'--------------------------------------------------
' Parameter 1 : (String) "APPARENTPOWER_Nanometric"
' Parameter 2 : (String) "Default value"
' Parameter 3 : (String) "Unlocked"
' Parameter 4 : (Boolean) False
'--------------------------------------------------

long1681 = settingRepository1.GetAttr("REACTIVEPOWER")
'--------------------------------------------------
' Parameter 1 : (String) "REACTIVEPOWER"
' Returned value : (Variant) (Long) 1
'--------------------------------------------------

Dim bSTR3361
bSTR3361 = ""
Dim bSTR3362
bSTR3362 = ""
Dim boolean1681
settingRepository1.GetAttrInfo "REACTIVEPOWER", bSTR3361, bSTR3362, boolean1681
'--------------------------------------------------
' Parameter 1 : (String) "REACTIVEPOWER"
' Parameter 2 : (String) "Default value"
' Parameter 3 : (String) "Unlocked"
' Parameter 4 : (Boolean) False
'--------------------------------------------------

long1682 = settingRepository1.GetAttr("REACTIVEPOWER_Large")
'--------------------------------------------------
' Parameter 1 : (String) "REACTIVEPOWER_Large"
' Returned value : (Variant) (Long) 1
'--------------------------------------------------

Dim bSTR3363
bSTR3363 = ""
Dim bSTR3364
bSTR3364 = ""
Dim boolean1682
settingRepository1.GetAttrInfo "REACTIVEPOWER_Large", bSTR3363, bSTR3364, boolean1682
'--------------------------------------------------
' Parameter 1 : (String) "REACTIVEPOWER_Large"
' Parameter 2 : (String) "Default value"
' Parameter 3 : (String) "Unlocked"
' Parameter 4 : (Boolean) False
'--------------------------------------------------

long1683 = settingRepository1.GetAttr("REACTIVEPOWER_ExtraLarge")
'--------------------------------------------------
' Parameter 1 : (String) "REACTIVEPOWER_ExtraLarge"
' Returned value : (Variant) (Long) 1
'--------------------------------------------------

Dim bSTR3365
bSTR3365 = ""
Dim bSTR3366
bSTR3366 = ""
Dim boolean1683
settingRepository1.GetAttrInfo "REACTIVEPOWER_ExtraLarge", bSTR3365, bSTR3366, boolean1683
'--------------------------------------------------
' Parameter 1 : (String) "REACTIVEPOWER_ExtraLarge"
' Parameter 2 : (String) "Default value"
' Parameter 3 : (String) "Unlocked"
' Parameter 4 : (Boolean) False
'--------------------------------------------------

long1684 = settingRepository1.GetAttr("REACTIVEPOWER_Small")
'--------------------------------------------------
' Parameter 1 : (String) "REACTIVEPOWER_Small"
' Returned value : (Variant) (Long) 1
'--------------------------------------------------

Dim bSTR3367
bSTR3367 = ""
Dim bSTR3368
bSTR3368 = ""
Dim boolean1684
settingRepository1.GetAttrInfo "REACTIVEPOWER_Small", bSTR3367, bSTR3368, boolean1684
'--------------------------------------------------
' Parameter 1 : (String) "REACTIVEPOWER_Small"
' Parameter 2 : (String) "Default value"
' Parameter 3 : (String) "Unlocked"
' Parameter 4 : (Boolean) False
'--------------------------------------------------

long1685 = settingRepository1.GetAttr("REACTIVEPOWER_ExtraSmall")
'--------------------------------------------------
' Parameter 1 : (String) "REACTIVEPOWER_ExtraSmall"
' Returned value : (Variant) (Long) 1
'--------------------------------------------------

Dim bSTR3369
bSTR3369 = ""
Dim bSTR3370
bSTR3370 = ""
Dim boolean1685
settingRepository1.GetAttrInfo "REACTIVEPOWER_ExtraSmall", bSTR3369, bSTR3370, boolean1685
'--------------------------------------------------
' Parameter 1 : (String) "REACTIVEPOWER_ExtraSmall"
' Parameter 2 : (String) "Default value"
' Parameter 3 : (String) "Unlocked"
' Parameter 4 : (Boolean) False
'--------------------------------------------------

long1686 = settingRepository1.GetAttr("REACTIVEPOWER_Nanometric")
'--------------------------------------------------
' Parameter 1 : (String) "REACTIVEPOWER_Nanometric"
' Returned value : (Variant) (Long) 1
'--------------------------------------------------

Dim bSTR3371
bSTR3371 = ""
Dim bSTR3372
bSTR3372 = ""
Dim boolean1686
settingRepository1.GetAttrInfo "REACTIVEPOWER_Nanometric", bSTR3371, bSTR3372, boolean1686
'--------------------------------------------------
' Parameter 1 : (String) "REACTIVEPOWER_Nanometric"
' Parameter 2 : (String) "Default value"
' Parameter 3 : (String) "Unlocked"
' Parameter 4 : (Boolean) False
'--------------------------------------------------

long1687 = settingRepository1.GetAttr("TRANSCONDUCTANCE")
'--------------------------------------------------
' Parameter 1 : (String) "TRANSCONDUCTANCE"
' Returned value : (Variant) (Long) 1
'--------------------------------------------------

Dim bSTR3373
bSTR3373 = ""
Dim bSTR3374
bSTR3374 = ""
Dim boolean1687
settingRepository1.GetAttrInfo "TRANSCONDUCTANCE", bSTR3373, bSTR3374, boolean1687
'--------------------------------------------------
' Parameter 1 : (String) "TRANSCONDUCTANCE"
' Parameter 2 : (String) "Default value"
' Parameter 3 : (String) "Unlocked"
' Parameter 4 : (Boolean) False
'--------------------------------------------------

long1688 = settingRepository1.GetAttr("TRANSCONDUCTANCE_Large")
'--------------------------------------------------
' Parameter 1 : (String) "TRANSCONDUCTANCE_Large"
' Returned value : (Variant) (Long) 1
'--------------------------------------------------

Dim bSTR3375
bSTR3375 = ""
Dim bSTR3376
bSTR3376 = ""
Dim boolean1688
settingRepository1.GetAttrInfo "TRANSCONDUCTANCE_Large", bSTR3375, bSTR3376, boolean1688
'--------------------------------------------------
' Parameter 1 : (String) "TRANSCONDUCTANCE_Large"
' Parameter 2 : (String) "Default value"
' Parameter 3 : (String) "Unlocked"
' Parameter 4 : (Boolean) False
'--------------------------------------------------

long1689 = settingRepository1.GetAttr("TRANSCONDUCTANCE_ExtraLarge")
'--------------------------------------------------
' Parameter 1 : (String) "TRANSCONDUCTANCE_ExtraLarge"
' Returned value : (Variant) (Long) 1
'--------------------------------------------------

Dim bSTR3377
bSTR3377 = ""
Dim bSTR3378
bSTR3378 = ""
Dim boolean1689
settingRepository1.GetAttrInfo "TRANSCONDUCTANCE_ExtraLarge", bSTR3377, bSTR3378, boolean1689
'--------------------------------------------------
' Parameter 1 : (String) "TRANSCONDUCTANCE_ExtraLarge"
' Parameter 2 : (String) "Default value"
' Parameter 3 : (String) "Unlocked"
' Parameter 4 : (Boolean) False
'--------------------------------------------------

long1690 = settingRepository1.GetAttr("TRANSCONDUCTANCE_Small")
'--------------------------------------------------
' Parameter 1 : (String) "TRANSCONDUCTANCE_Small"
' Returned value : (Variant) (Long) 1
'--------------------------------------------------

Dim bSTR3379
bSTR3379 = ""
Dim bSTR3380
bSTR3380 = ""
Dim boolean1690
settingRepository1.GetAttrInfo "TRANSCONDUCTANCE_Small", bSTR3379, bSTR3380, boolean1690
'--------------------------------------------------
' Parameter 1 : (String) "TRANSCONDUCTANCE_Small"
' Parameter 2 : (String) "Default value"
' Parameter 3 : (String) "Unlocked"
' Parameter 4 : (Boolean) False
'--------------------------------------------------

long1691 = settingRepository1.GetAttr("TRANSCONDUCTANCE_ExtraSmall")
'--------------------------------------------------
' Parameter 1 : (String) "TRANSCONDUCTANCE_ExtraSmall"
' Returned value : (Variant) (Long) 1
'--------------------------------------------------

Dim bSTR3381
bSTR3381 = ""
Dim bSTR3382
bSTR3382 = ""
Dim boolean1691
settingRepository1.GetAttrInfo "TRANSCONDUCTANCE_ExtraSmall", bSTR3381, bSTR3382, boolean1691
'--------------------------------------------------
' Parameter 1 : (String) "TRANSCONDUCTANCE_ExtraSmall"
' Parameter 2 : (String) "Default value"
' Parameter 3 : (String) "Unlocked"
' Parameter 4 : (Boolean) False
'--------------------------------------------------

long1692 = settingRepository1.GetAttr("TRANSCONDUCTANCE_Nanometric")
'--------------------------------------------------
' Parameter 1 : (String) "TRANSCONDUCTANCE_Nanometric"
' Returned value : (Variant) (Long) 1
'--------------------------------------------------

Dim bSTR3383
bSTR3383 = ""
Dim bSTR3384
bSTR3384 = ""
Dim boolean1692
settingRepository1.GetAttrInfo "TRANSCONDUCTANCE_Nanometric", bSTR3383, bSTR3384, boolean1692
'--------------------------------------------------
' Parameter 1 : (String) "TRANSCONDUCTANCE_Nanometric"
' Parameter 2 : (String) "Default value"
' Parameter 3 : (String) "Unlocked"
' Parameter 4 : (Boolean) False
'--------------------------------------------------

long1693 = settingRepository1.GetAttr("INVERSEPOTENTIAL")
'--------------------------------------------------
' Parameter 1 : (String) "INVERSEPOTENTIAL"
' Returned value : (Variant) (Long) 1
'--------------------------------------------------

Dim bSTR3385
bSTR3385 = ""
Dim bSTR3386
bSTR3386 = ""
Dim boolean1693
settingRepository1.GetAttrInfo "INVERSEPOTENTIAL", bSTR3385, bSTR3386, boolean1693
'--------------------------------------------------
' Parameter 1 : (String) "INVERSEPOTENTIAL"
' Parameter 2 : (String) "Default value"
' Parameter 3 : (String) "Unlocked"
' Parameter 4 : (Boolean) False
'--------------------------------------------------

long1694 = settingRepository1.GetAttr("INVERSEPOTENTIAL_Large")
'--------------------------------------------------
' Parameter 1 : (String) "INVERSEPOTENTIAL_Large"
' Returned value : (Variant) (Long) 1
'--------------------------------------------------

Dim bSTR3387
bSTR3387 = ""
Dim bSTR3388
bSTR3388 = ""
Dim boolean1694
settingRepository1.GetAttrInfo "INVERSEPOTENTIAL_Large", bSTR3387, bSTR3388, boolean1694
'--------------------------------------------------
' Parameter 1 : (String) "INVERSEPOTENTIAL_Large"
' Parameter 2 : (String) "Default value"
' Parameter 3 : (String) "Unlocked"
' Parameter 4 : (Boolean) False
'--------------------------------------------------

long1695 = settingRepository1.GetAttr("INVERSEPOTENTIAL_ExtraLarge")
'--------------------------------------------------
' Parameter 1 : (String) "INVERSEPOTENTIAL_ExtraLarge"
' Returned value : (Variant) (Long) 1
'--------------------------------------------------

Dim bSTR3389
bSTR3389 = ""
Dim bSTR3390
bSTR3390 = ""
Dim boolean1695
settingRepository1.GetAttrInfo "INVERSEPOTENTIAL_ExtraLarge", bSTR3389, bSTR3390, boolean1695
'--------------------------------------------------
' Parameter 1 : (String) "INVERSEPOTENTIAL_ExtraLarge"
' Parameter 2 : (String) "Default value"
' Parameter 3 : (String) "Unlocked"
' Parameter 4 : (Boolean) False
'--------------------------------------------------

long1696 = settingRepository1.GetAttr("INVERSEPOTENTIAL_Small")
'--------------------------------------------------
' Parameter 1 : (String) "INVERSEPOTENTIAL_Small"
' Returned value : (Variant) (Long) 1
'--------------------------------------------------

Dim bSTR3391
bSTR3391 = ""
Dim bSTR3392
bSTR3392 = ""
Dim boolean1696
settingRepository1.GetAttrInfo "INVERSEPOTENTIAL_Small", bSTR3391, bSTR3392, boolean1696
'--------------------------------------------------
' Parameter 1 : (String) "INVERSEPOTENTIAL_Small"
' Parameter 2 : (String) "Default value"
' Parameter 3 : (String) "Unlocked"
' Parameter 4 : (Boolean) False
'--------------------------------------------------

long1697 = settingRepository1.GetAttr("INVERSEPOTENTIAL_ExtraSmall")
'--------------------------------------------------
' Parameter 1 : (String) "INVERSEPOTENTIAL_ExtraSmall"
' Returned value : (Variant) (Long) 1
'--------------------------------------------------

Dim bSTR3393
bSTR3393 = ""
Dim bSTR3394
bSTR3394 = ""
Dim boolean1697
settingRepository1.GetAttrInfo "INVERSEPOTENTIAL_ExtraSmall", bSTR3393, bSTR3394, boolean1697
'--------------------------------------------------
' Parameter 1 : (String) "INVERSEPOTENTIAL_ExtraSmall"
' Parameter 2 : (String) "Default value"
' Parameter 3 : (String) "Unlocked"
' Parameter 4 : (Boolean) False
'--------------------------------------------------

long1698 = settingRepository1.GetAttr("INVERSEPOTENTIAL_Nanometric")
'--------------------------------------------------
' Parameter 1 : (String) "INVERSEPOTENTIAL_Nanometric"
' Returned value : (Variant) (Long) 1
'--------------------------------------------------

Dim bSTR3395
bSTR3395 = ""
Dim bSTR3396
bSTR3396 = ""
Dim boolean1698
settingRepository1.GetAttrInfo "INVERSEPOTENTIAL_Nanometric", bSTR3395, bSTR3396, boolean1698
'--------------------------------------------------
' Parameter 1 : (String) "INVERSEPOTENTIAL_Nanometric"
' Parameter 2 : (String) "Default value"
' Parameter 3 : (String) "Unlocked"
' Parameter 4 : (Boolean) False
'--------------------------------------------------

long1699 = settingRepository1.GetAttr("RADIANTENERGY")
'--------------------------------------------------
' Parameter 1 : (String) "RADIANTENERGY"
' Returned value : (Variant) (Long) 1
'--------------------------------------------------

Dim bSTR3397
bSTR3397 = ""
Dim bSTR3398
bSTR3398 = ""
Dim boolean1699
settingRepository1.GetAttrInfo "RADIANTENERGY", bSTR3397, bSTR3398, boolean1699
'--------------------------------------------------
' Parameter 1 : (String) "RADIANTENERGY"
' Parameter 2 : (String) "Default value"
' Parameter 3 : (String) "Unlocked"
' Parameter 4 : (Boolean) False
'--------------------------------------------------

long1700 = settingRepository1.GetAttr("RADIANTENERGY_Large")
'--------------------------------------------------
' Parameter 1 : (String) "RADIANTENERGY_Large"
' Returned value : (Variant) (Long) 1
'--------------------------------------------------

Dim bSTR3399
bSTR3399 = ""
Dim bSTR3400
bSTR3400 = ""
Dim boolean1700
settingRepository1.GetAttrInfo "RADIANTENERGY_Large", bSTR3399, bSTR3400, boolean1700
'--------------------------------------------------
' Parameter 1 : (String) "RADIANTENERGY_Large"
' Parameter 2 : (String) "Default value"
' Parameter 3 : (String) "Unlocked"
' Parameter 4 : (Boolean) False
'--------------------------------------------------

long1701 = settingRepository1.GetAttr("RADIANTENERGY_ExtraLarge")
'--------------------------------------------------
' Parameter 1 : (String) "RADIANTENERGY_ExtraLarge"
' Returned value : (Variant) (Long) 1
'--------------------------------------------------

Dim bSTR3401
bSTR3401 = ""
Dim bSTR3402
bSTR3402 = ""
Dim boolean1701
settingRepository1.GetAttrInfo "RADIANTENERGY_ExtraLarge", bSTR3401, bSTR3402, boolean1701
'--------------------------------------------------
' Parameter 1 : (String) "RADIANTENERGY_ExtraLarge"
' Parameter 2 : (String) "Default value"
' Parameter 3 : (String) "Unlocked"
' Parameter 4 : (Boolean) False
'--------------------------------------------------

long1702 = settingRepository1.GetAttr("RADIANTENERGY_Small")
'--------------------------------------------------
' Parameter 1 : (String) "RADIANTENERGY_Small"
' Returned value : (Variant) (Long) 1
'--------------------------------------------------

Dim bSTR3403
bSTR3403 = ""
Dim bSTR3404
bSTR3404 = ""
Dim boolean1702
settingRepository1.GetAttrInfo "RADIANTENERGY_Small", bSTR3403, bSTR3404, boolean1702
'--------------------------------------------------
' Parameter 1 : (String) "RADIANTENERGY_Small"
' Parameter 2 : (String) "Default value"
' Parameter 3 : (String) "Unlocked"
' Parameter 4 : (Boolean) False
'--------------------------------------------------

long1703 = settingRepository1.GetAttr("RADIANTENERGY_ExtraSmall")
'--------------------------------------------------
' Parameter 1 : (String) "RADIANTENERGY_ExtraSmall"
' Returned value : (Variant) (Long) 1
'--------------------------------------------------

Dim bSTR3405
bSTR3405 = ""
Dim bSTR3406
bSTR3406 = ""
Dim boolean1703
settingRepository1.GetAttrInfo "RADIANTENERGY_ExtraSmall", bSTR3405, bSTR3406, boolean1703
'--------------------------------------------------
' Parameter 1 : (String) "RADIANTENERGY_ExtraSmall"
' Parameter 2 : (String) "Default value"
' Parameter 3 : (String) "Unlocked"
' Parameter 4 : (Boolean) False
'--------------------------------------------------

long1704 = settingRepository1.GetAttr("RADIANTENERGY_Nanometric")
'--------------------------------------------------
' Parameter 1 : (String) "RADIANTENERGY_Nanometric"
' Returned value : (Variant) (Long) 1
'--------------------------------------------------

Dim bSTR3407
bSTR3407 = ""
Dim bSTR3408
bSTR3408 = ""
Dim boolean1704
settingRepository1.GetAttrInfo "RADIANTENERGY_Nanometric", bSTR3407, bSTR3408, boolean1704
'--------------------------------------------------
' Parameter 1 : (String) "RADIANTENERGY_Nanometric"
' Parameter 2 : (String) "Default value"
' Parameter 3 : (String) "Unlocked"
' Parameter 4 : (Boolean) False
'--------------------------------------------------

long1705 = settingRepository1.GetAttr("SPECTRALRADIANTENERGYDENSITY")
'--------------------------------------------------
' Parameter 1 : (String) "SPECTRALRADIANTENERGYDENSITY"
' Returned value : (Variant) (Long) 1
'--------------------------------------------------

Dim bSTR3409
bSTR3409 = ""
Dim bSTR3410
bSTR3410 = ""
Dim boolean1705
settingRepository1.GetAttrInfo "SPECTRALRADIANTENERGYDENSITY", bSTR3409, bSTR3410, boolean1705
'--------------------------------------------------
' Parameter 1 : (String) "SPECTRALRADIANTENERGYDENSITY"
' Parameter 2 : (String) "Default value"
' Parameter 3 : (String) "Unlocked"
' Parameter 4 : (Boolean) False
'--------------------------------------------------

long1706 = settingRepository1.GetAttr("SPECTRALRADIANTENERGYDENSITY_Large")
'--------------------------------------------------
' Parameter 1 : (String) "SPECTRALRADIANTENERGYDENSITY_Large"
' Returned value : (Variant) (Long) 1
'--------------------------------------------------

Dim bSTR3411
bSTR3411 = ""
Dim bSTR3412
bSTR3412 = ""
Dim boolean1706
settingRepository1.GetAttrInfo "SPECTRALRADIANTENERGYDENSITY_Large", bSTR3411, bSTR3412, boolean1706
'--------------------------------------------------
' Parameter 1 : (String) "SPECTRALRADIANTENERGYDENSITY_Large"
' Parameter 2 : (String) "Default value"
' Parameter 3 : (String) "Unlocked"
' Parameter 4 : (Boolean) False
'--------------------------------------------------

long1707 = settingRepository1.GetAttr("SPECTRALRADIANTENERGYDENSITY_ExtraLarge")
'--------------------------------------------------
' Parameter 1 : (String) "SPECTRALRADIANTENERGYDENSITY_ExtraLarge"
' Returned value : (Variant) (Long) 1
'--------------------------------------------------

Dim bSTR3413
bSTR3413 = ""
Dim bSTR3414
bSTR3414 = ""
Dim boolean1707
settingRepository1.GetAttrInfo "SPECTRALRADIANTENERGYDENSITY_ExtraLarge", bSTR3413, bSTR3414, boolean1707
'--------------------------------------------------
' Parameter 1 : (String) "SPECTRALRADIANTENERGYDENSITY_ExtraLarge"
' Parameter 2 : (String) "Default value"
' Parameter 3 : (String) "Unlocked"
' Parameter 4 : (Boolean) False
'--------------------------------------------------

long1708 = settingRepository1.GetAttr("SPECTRALRADIANTENERGYDENSITY_Small")
'--------------------------------------------------
' Parameter 1 : (String) "SPECTRALRADIANTENERGYDENSITY_Small"
' Returned value : (Variant) (Long) 1
'--------------------------------------------------

Dim bSTR3415
bSTR3415 = ""
Dim bSTR3416
bSTR3416 = ""
Dim boolean1708
settingRepository1.GetAttrInfo "SPECTRALRADIANTENERGYDENSITY_Small", bSTR3415, bSTR3416, boolean1708
'--------------------------------------------------
' Parameter 1 : (String) "SPECTRALRADIANTENERGYDENSITY_Small"
' Parameter 2 : (String) "Default value"
' Parameter 3 : (String) "Unlocked"
' Parameter 4 : (Boolean) False
'--------------------------------------------------

long1709 = settingRepository1.GetAttr("SPECTRALRADIANTENERGYDENSITY_ExtraSmall")
'--------------------------------------------------
' Parameter 1 : (String) "SPECTRALRADIANTENERGYDENSITY_ExtraSmall"
' Returned value : (Variant) (Long) 1
'--------------------------------------------------

Dim bSTR3417
bSTR3417 = ""
Dim bSTR3418
bSTR3418 = ""
Dim boolean1709
settingRepository1.GetAttrInfo "SPECTRALRADIANTENERGYDENSITY_ExtraSmall", bSTR3417, bSTR3418, boolean1709
'--------------------------------------------------
' Parameter 1 : (String) "SPECTRALRADIANTENERGYDENSITY_ExtraSmall"
' Parameter 2 : (String) "Default value"
' Parameter 3 : (String) "Unlocked"
' Parameter 4 : (Boolean) False
'--------------------------------------------------

long1710 = settingRepository1.GetAttr("SPECTRALRADIANTENERGYDENSITY_Nanometric")
'--------------------------------------------------
' Parameter 1 : (String) "SPECTRALRADIANTENERGYDENSITY_Nanometric"
' Returned value : (Variant) (Long) 1
'--------------------------------------------------

Dim bSTR3419
bSTR3419 = ""
Dim bSTR3420
bSTR3420 = ""
Dim boolean1710
settingRepository1.GetAttrInfo "SPECTRALRADIANTENERGYDENSITY_Nanometric", bSTR3419, bSTR3420, boolean1710
'--------------------------------------------------
' Parameter 1 : (String) "SPECTRALRADIANTENERGYDENSITY_Nanometric"
' Parameter 2 : (String) "Default value"
' Parameter 3 : (String) "Unlocked"
' Parameter 4 : (Boolean) False
'--------------------------------------------------

long1711 = settingRepository1.GetAttr("RADIANTENERGYFLUENCERATE")
'--------------------------------------------------
' Parameter 1 : (String) "RADIANTENERGYFLUENCERATE"
' Returned value : (Variant) (Long) 1
'--------------------------------------------------

Dim bSTR3421
bSTR3421 = ""
Dim bSTR3422
bSTR3422 = ""
Dim boolean1711
settingRepository1.GetAttrInfo "RADIANTENERGYFLUENCERATE", bSTR3421, bSTR3422, boolean1711
'--------------------------------------------------
' Parameter 1 : (String) "RADIANTENERGYFLUENCERATE"
' Parameter 2 : (String) "Default value"
' Parameter 3 : (String) "Unlocked"
' Parameter 4 : (Boolean) False
'--------------------------------------------------

long1712 = settingRepository1.GetAttr("RADIANTENERGYFLUENCERATE_Large")
'--------------------------------------------------
' Parameter 1 : (String) "RADIANTENERGYFLUENCERATE_Large"
' Returned value : (Variant) (Long) 1
'--------------------------------------------------

Dim bSTR3423
bSTR3423 = ""
Dim bSTR3424
bSTR3424 = ""
Dim boolean1712
settingRepository1.GetAttrInfo "RADIANTENERGYFLUENCERATE_Large", bSTR3423, bSTR3424, boolean1712
'--------------------------------------------------
' Parameter 1 : (String) "RADIANTENERGYFLUENCERATE_Large"
' Parameter 2 : (String) "Default value"
' Parameter 3 : (String) "Unlocked"
' Parameter 4 : (Boolean) False
'--------------------------------------------------

long1713 = settingRepository1.GetAttr("RADIANTENERGYFLUENCERATE_ExtraLarge")
'--------------------------------------------------
' Parameter 1 : (String) "RADIANTENERGYFLUENCERATE_ExtraLarge"
' Returned value : (Variant) (Long) 1
'--------------------------------------------------

Dim bSTR3425
bSTR3425 = ""
Dim bSTR3426
bSTR3426 = ""
Dim boolean1713
settingRepository1.GetAttrInfo "RADIANTENERGYFLUENCERATE_ExtraLarge", bSTR3425, bSTR3426, boolean1713
'--------------------------------------------------
' Parameter 1 : (String) "RADIANTENERGYFLUENCERATE_ExtraLarge"
' Parameter 2 : (String) "Default value"
' Parameter 3 : (String) "Unlocked"
' Parameter 4 : (Boolean) False
'--------------------------------------------------

long1714 = settingRepository1.GetAttr("RADIANTENERGYFLUENCERATE_Small")
'--------------------------------------------------
' Parameter 1 : (String) "RADIANTENERGYFLUENCERATE_Small"
' Returned value : (Variant) (Long) 1
'--------------------------------------------------

Dim bSTR3427
bSTR3427 = ""
Dim bSTR3428
bSTR3428 = ""
Dim boolean1714
settingRepository1.GetAttrInfo "RADIANTENERGYFLUENCERATE_Small", bSTR3427, bSTR3428, boolean1714
'--------------------------------------------------
' Parameter 1 : (String) "RADIANTENERGYFLUENCERATE_Small"
' Parameter 2 : (String) "Default value"
' Parameter 3 : (String) "Unlocked"
' Parameter 4 : (Boolean) False
'--------------------------------------------------

long1715 = settingRepository1.GetAttr("RADIANTENERGYFLUENCERATE_ExtraSmall")
'--------------------------------------------------
' Parameter 1 : (String) "RADIANTENERGYFLUENCERATE_ExtraSmall"
' Returned value : (Variant) (Long) 1
'--------------------------------------------------

Dim bSTR3429
bSTR3429 = ""
Dim bSTR3430
bSTR3430 = ""
Dim boolean1715
settingRepository1.GetAttrInfo "RADIANTENERGYFLUENCERATE_ExtraSmall", bSTR3429, bSTR3430, boolean1715
'--------------------------------------------------
' Parameter 1 : (String) "RADIANTENERGYFLUENCERATE_ExtraSmall"
' Parameter 2 : (String) "Default value"
' Parameter 3 : (String) "Unlocked"
' Parameter 4 : (Boolean) False
'--------------------------------------------------

long1716 = settingRepository1.GetAttr("RADIANTENERGYFLUENCERATE_Nanometric")
'--------------------------------------------------
' Parameter 1 : (String) "RADIANTENERGYFLUENCERATE_Nanometric"
' Returned value : (Variant) (Long) 1
'--------------------------------------------------

Dim bSTR3431
bSTR3431 = ""
Dim bSTR3432
bSTR3432 = ""
Dim boolean1716
settingRepository1.GetAttrInfo "RADIANTENERGYFLUENCERATE_Nanometric", bSTR3431, bSTR3432, boolean1716
'--------------------------------------------------
' Parameter 1 : (String) "RADIANTENERGYFLUENCERATE_Nanometric"
' Parameter 2 : (String) "Default value"
' Parameter 3 : (String) "Unlocked"
' Parameter 4 : (Boolean) False
'--------------------------------------------------

long1717 = settingRepository1.GetAttr("QUANTITYOFLIGHT")
'--------------------------------------------------
' Parameter 1 : (String) "QUANTITYOFLIGHT"
' Returned value : (Variant) (Long) 1
'--------------------------------------------------

Dim bSTR3433
bSTR3433 = ""
Dim bSTR3434
bSTR3434 = ""
Dim boolean1717
settingRepository1.GetAttrInfo "QUANTITYOFLIGHT", bSTR3433, bSTR3434, boolean1717
'--------------------------------------------------
' Parameter 1 : (String) "QUANTITYOFLIGHT"
' Parameter 2 : (String) "Default value"
' Parameter 3 : (String) "Unlocked"
' Parameter 4 : (Boolean) False
'--------------------------------------------------

long1718 = settingRepository1.GetAttr("QUANTITYOFLIGHT_Large")
'--------------------------------------------------
' Parameter 1 : (String) "QUANTITYOFLIGHT_Large"
' Returned value : (Variant) (Long) 1
'--------------------------------------------------

Dim bSTR3435
bSTR3435 = ""
Dim bSTR3436
bSTR3436 = ""
Dim boolean1718
settingRepository1.GetAttrInfo "QUANTITYOFLIGHT_Large", bSTR3435, bSTR3436, boolean1718
'--------------------------------------------------
' Parameter 1 : (String) "QUANTITYOFLIGHT_Large"
' Parameter 2 : (String) "Default value"
' Parameter 3 : (String) "Unlocked"
' Parameter 4 : (Boolean) False
'--------------------------------------------------

long1719 = settingRepository1.GetAttr("QUANTITYOFLIGHT_ExtraLarge")
'--------------------------------------------------
' Parameter 1 : (String) "QUANTITYOFLIGHT_ExtraLarge"
' Returned value : (Variant) (Long) 1
'--------------------------------------------------

Dim bSTR3437
bSTR3437 = ""
Dim bSTR3438
bSTR3438 = ""
Dim boolean1719
settingRepository1.GetAttrInfo "QUANTITYOFLIGHT_ExtraLarge", bSTR3437, bSTR3438, boolean1719
'--------------------------------------------------
' Parameter 1 : (String) "QUANTITYOFLIGHT_ExtraLarge"
' Parameter 2 : (String) "Default value"
' Parameter 3 : (String) "Unlocked"
' Parameter 4 : (Boolean) False
'--------------------------------------------------

long1720 = settingRepository1.GetAttr("QUANTITYOFLIGHT_Small")
'--------------------------------------------------
' Parameter 1 : (String) "QUANTITYOFLIGHT_Small"
' Returned value : (Variant) (Long) 1
'--------------------------------------------------

Dim bSTR3439
bSTR3439 = ""
Dim bSTR3440
bSTR3440 = ""
Dim boolean1720
settingRepository1.GetAttrInfo "QUANTITYOFLIGHT_Small", bSTR3439, bSTR3440, boolean1720
'--------------------------------------------------
' Parameter 1 : (String) "QUANTITYOFLIGHT_Small"
' Parameter 2 : (String) "Default value"
' Parameter 3 : (String) "Unlocked"
' Parameter 4 : (Boolean) False
'--------------------------------------------------

long1721 = settingRepository1.GetAttr("QUANTITYOFLIGHT_ExtraSmall")
'--------------------------------------------------
' Parameter 1 : (String) "QUANTITYOFLIGHT_ExtraSmall"
' Returned value : (Variant) (Long) 1
'--------------------------------------------------

Dim bSTR3441
bSTR3441 = ""
Dim bSTR3442
bSTR3442 = ""
Dim boolean1721
settingRepository1.GetAttrInfo "QUANTITYOFLIGHT_ExtraSmall", bSTR3441, bSTR3442, boolean1721
'--------------------------------------------------
' Parameter 1 : (String) "QUANTITYOFLIGHT_ExtraSmall"
' Parameter 2 : (String) "Default value"
' Parameter 3 : (String) "Unlocked"
' Parameter 4 : (Boolean) False
'--------------------------------------------------

long1722 = settingRepository1.GetAttr("QUANTITYOFLIGHT_Nanometric")
'--------------------------------------------------
' Parameter 1 : (String) "QUANTITYOFLIGHT_Nanometric"
' Returned value : (Variant) (Long) 1
'--------------------------------------------------

Dim bSTR3443
bSTR3443 = ""
Dim bSTR3444
bSTR3444 = ""
Dim boolean1722
settingRepository1.GetAttrInfo "QUANTITYOFLIGHT_Nanometric", bSTR3443, bSTR3444, boolean1722
'--------------------------------------------------
' Parameter 1 : (String) "QUANTITYOFLIGHT_Nanometric"
' Parameter 2 : (String) "Default value"
' Parameter 3 : (String) "Unlocked"
' Parameter 4 : (Boolean) False
'--------------------------------------------------

long1723 = settingRepository1.GetAttr("LUMINOUSEXITANCE")
'--------------------------------------------------
' Parameter 1 : (String) "LUMINOUSEXITANCE"
' Returned value : (Variant) (Long) 1
'--------------------------------------------------

Dim bSTR3445
bSTR3445 = ""
Dim bSTR3446
bSTR3446 = ""
Dim boolean1723
settingRepository1.GetAttrInfo "LUMINOUSEXITANCE", bSTR3445, bSTR3446, boolean1723
'--------------------------------------------------
' Parameter 1 : (String) "LUMINOUSEXITANCE"
' Parameter 2 : (String) "Default value"
' Parameter 3 : (String) "Unlocked"
' Parameter 4 : (Boolean) False
'--------------------------------------------------

long1724 = settingRepository1.GetAttr("LUMINOUSEXITANCE_Large")
'--------------------------------------------------
' Parameter 1 : (String) "LUMINOUSEXITANCE_Large"
' Returned value : (Variant) (Long) 1
'--------------------------------------------------

Dim bSTR3447
bSTR3447 = ""
Dim bSTR3448
bSTR3448 = ""
Dim boolean1724
settingRepository1.GetAttrInfo "LUMINOUSEXITANCE_Large", bSTR3447, bSTR3448, boolean1724
'--------------------------------------------------
' Parameter 1 : (String) "LUMINOUSEXITANCE_Large"
' Parameter 2 : (String) "Default value"
' Parameter 3 : (String) "Unlocked"
' Parameter 4 : (Boolean) False
'--------------------------------------------------

long1725 = settingRepository1.GetAttr("LUMINOUSEXITANCE_ExtraLarge")
'--------------------------------------------------
' Parameter 1 : (String) "LUMINOUSEXITANCE_ExtraLarge"
' Returned value : (Variant) (Long) 1
'--------------------------------------------------

Dim bSTR3449
bSTR3449 = ""
Dim bSTR3450
bSTR3450 = ""
Dim boolean1725
settingRepository1.GetAttrInfo "LUMINOUSEXITANCE_ExtraLarge", bSTR3449, bSTR3450, boolean1725
'--------------------------------------------------
' Parameter 1 : (String) "LUMINOUSEXITANCE_ExtraLarge"
' Parameter 2 : (String) "Default value"
' Parameter 3 : (String) "Unlocked"
' Parameter 4 : (Boolean) False
'--------------------------------------------------

long1726 = settingRepository1.GetAttr("LUMINOUSEXITANCE_Small")
'--------------------------------------------------
' Parameter 1 : (String) "LUMINOUSEXITANCE_Small"
' Returned value : (Variant) (Long) 1
'--------------------------------------------------

Dim bSTR3451
bSTR3451 = ""
Dim bSTR3452
bSTR3452 = ""
Dim boolean1726
settingRepository1.GetAttrInfo "LUMINOUSEXITANCE_Small", bSTR3451, bSTR3452, boolean1726
'--------------------------------------------------
' Parameter 1 : (String) "LUMINOUSEXITANCE_Small"
' Parameter 2 : (String) "Default value"
' Parameter 3 : (String) "Unlocked"
' Parameter 4 : (Boolean) False
'--------------------------------------------------

long1727 = settingRepository1.GetAttr("LUMINOUSEXITANCE_ExtraSmall")
'--------------------------------------------------
' Parameter 1 : (String) "LUMINOUSEXITANCE_ExtraSmall"
' Returned value : (Variant) (Long) 1
'--------------------------------------------------

Dim bSTR3453
bSTR3453 = ""
Dim bSTR3454
bSTR3454 = ""
Dim boolean1727
settingRepository1.GetAttrInfo "LUMINOUSEXITANCE_ExtraSmall", bSTR3453, bSTR3454, boolean1727
'--------------------------------------------------
' Parameter 1 : (String) "LUMINOUSEXITANCE_ExtraSmall"
' Parameter 2 : (String) "Default value"
' Parameter 3 : (String) "Unlocked"
' Parameter 4 : (Boolean) False
'--------------------------------------------------

long1728 = settingRepository1.GetAttr("LUMINOUSEXITANCE_Nanometric")
'--------------------------------------------------
' Parameter 1 : (String) "LUMINOUSEXITANCE_Nanometric"
' Returned value : (Variant) (Long) 1
'--------------------------------------------------

Dim bSTR3455
bSTR3455 = ""
Dim bSTR3456
bSTR3456 = ""
Dim boolean1728
settingRepository1.GetAttrInfo "LUMINOUSEXITANCE_Nanometric", bSTR3455, bSTR3456, boolean1728
'--------------------------------------------------
' Parameter 1 : (String) "LUMINOUSEXITANCE_Nanometric"
' Parameter 2 : (String) "Default value"
' Parameter 3 : (String) "Unlocked"
' Parameter 4 : (Boolean) False
'--------------------------------------------------

long1729 = settingRepository1.GetAttr("LIGHTEXPOSURE")
'--------------------------------------------------
' Parameter 1 : (String) "LIGHTEXPOSURE"
' Returned value : (Variant) (Long) 1
'--------------------------------------------------

Dim bSTR3457
bSTR3457 = ""
Dim bSTR3458
bSTR3458 = ""
Dim boolean1729
settingRepository1.GetAttrInfo "LIGHTEXPOSURE", bSTR3457, bSTR3458, boolean1729
'--------------------------------------------------
' Parameter 1 : (String) "LIGHTEXPOSURE"
' Parameter 2 : (String) "Default value"
' Parameter 3 : (String) "Unlocked"
' Parameter 4 : (Boolean) False
'--------------------------------------------------

long1730 = settingRepository1.GetAttr("LIGHTEXPOSURE_Large")
'--------------------------------------------------
' Parameter 1 : (String) "LIGHTEXPOSURE_Large"
' Returned value : (Variant) (Long) 1
'--------------------------------------------------

Dim bSTR3459
bSTR3459 = ""
Dim bSTR3460
bSTR3460 = ""
Dim boolean1730
settingRepository1.GetAttrInfo "LIGHTEXPOSURE_Large", bSTR3459, bSTR3460, boolean1730
'--------------------------------------------------
' Parameter 1 : (String) "LIGHTEXPOSURE_Large"
' Parameter 2 : (String) "Default value"
' Parameter 3 : (String) "Unlocked"
' Parameter 4 : (Boolean) False
'--------------------------------------------------

long1731 = settingRepository1.GetAttr("LIGHTEXPOSURE_ExtraLarge")
'--------------------------------------------------
' Parameter 1 : (String) "LIGHTEXPOSURE_ExtraLarge"
' Returned value : (Variant) (Long) 1
'--------------------------------------------------

Dim bSTR3461
bSTR3461 = ""
Dim bSTR3462
bSTR3462 = ""
Dim boolean1731
settingRepository1.GetAttrInfo "LIGHTEXPOSURE_ExtraLarge", bSTR3461, bSTR3462, boolean1731
'--------------------------------------------------
' Parameter 1 : (String) "LIGHTEXPOSURE_ExtraLarge"
' Parameter 2 : (String) "Default value"
' Parameter 3 : (String) "Unlocked"
' Parameter 4 : (Boolean) False
'--------------------------------------------------

long1732 = settingRepository1.GetAttr("LIGHTEXPOSURE_Small")
'--------------------------------------------------
' Parameter 1 : (String) "LIGHTEXPOSURE_Small"
' Returned value : (Variant) (Long) 1
'--------------------------------------------------

Dim bSTR3463
bSTR3463 = ""
Dim bSTR3464
bSTR3464 = ""
Dim boolean1732
settingRepository1.GetAttrInfo "LIGHTEXPOSURE_Small", bSTR3463, bSTR3464, boolean1732
'--------------------------------------------------
' Parameter 1 : (String) "LIGHTEXPOSURE_Small"
' Parameter 2 : (String) "Default value"
' Parameter 3 : (String) "Unlocked"
' Parameter 4 : (Boolean) False
'--------------------------------------------------

long1733 = settingRepository1.GetAttr("LIGHTEXPOSURE_ExtraSmall")
'--------------------------------------------------
' Parameter 1 : (String) "LIGHTEXPOSURE_ExtraSmall"
' Returned value : (Variant) (Long) 1
'--------------------------------------------------

Dim bSTR3465
bSTR3465 = ""
Dim bSTR3466
bSTR3466 = ""
Dim boolean1733
settingRepository1.GetAttrInfo "LIGHTEXPOSURE_ExtraSmall", bSTR3465, bSTR3466, boolean1733
'--------------------------------------------------
' Parameter 1 : (String) "LIGHTEXPOSURE_ExtraSmall"
' Parameter 2 : (String) "Default value"
' Parameter 3 : (String) "Unlocked"
' Parameter 4 : (Boolean) False
'--------------------------------------------------

long1734 = settingRepository1.GetAttr("LIGHTEXPOSURE_Nanometric")
'--------------------------------------------------
' Parameter 1 : (String) "LIGHTEXPOSURE_Nanometric"
' Returned value : (Variant) (Long) 1
'--------------------------------------------------

Dim bSTR3467
bSTR3467 = ""
Dim bSTR3468
bSTR3468 = ""
Dim boolean1734
settingRepository1.GetAttrInfo "LIGHTEXPOSURE_Nanometric", bSTR3467, bSTR3468, boolean1734
'--------------------------------------------------
' Parameter 1 : (String) "LIGHTEXPOSURE_Nanometric"
' Parameter 2 : (String) "Default value"
' Parameter 3 : (String) "Unlocked"
' Parameter 4 : (Boolean) False
'--------------------------------------------------

long1735 = settingRepository1.GetAttr("LUMINOUSEFFICACY")
'--------------------------------------------------
' Parameter 1 : (String) "LUMINOUSEFFICACY"
' Returned value : (Variant) (Long) 1
'--------------------------------------------------

Dim bSTR3469
bSTR3469 = ""
Dim bSTR3470
bSTR3470 = ""
Dim boolean1735
settingRepository1.GetAttrInfo "LUMINOUSEFFICACY", bSTR3469, bSTR3470, boolean1735
'--------------------------------------------------
' Parameter 1 : (String) "LUMINOUSEFFICACY"
' Parameter 2 : (String) "Default value"
' Parameter 3 : (String) "Unlocked"
' Parameter 4 : (Boolean) False
'--------------------------------------------------

long1736 = settingRepository1.GetAttr("LUMINOUSEFFICACY_Large")
'--------------------------------------------------
' Parameter 1 : (String) "LUMINOUSEFFICACY_Large"
' Returned value : (Variant) (Long) 1
'--------------------------------------------------

Dim bSTR3471
bSTR3471 = ""
Dim bSTR3472
bSTR3472 = ""
Dim boolean1736
settingRepository1.GetAttrInfo "LUMINOUSEFFICACY_Large", bSTR3471, bSTR3472, boolean1736
'--------------------------------------------------
' Parameter 1 : (String) "LUMINOUSEFFICACY_Large"
' Parameter 2 : (String) "Default value"
' Parameter 3 : (String) "Unlocked"
' Parameter 4 : (Boolean) False
'--------------------------------------------------

long1737 = settingRepository1.GetAttr("LUMINOUSEFFICACY_ExtraLarge")
'--------------------------------------------------
' Parameter 1 : (String) "LUMINOUSEFFICACY_ExtraLarge"
' Returned value : (Variant) (Long) 1
'--------------------------------------------------

Dim bSTR3473
bSTR3473 = ""
Dim bSTR3474
bSTR3474 = ""
Dim boolean1737
settingRepository1.GetAttrInfo "LUMINOUSEFFICACY_ExtraLarge", bSTR3473, bSTR3474, boolean1737
'--------------------------------------------------
' Parameter 1 : (String) "LUMINOUSEFFICACY_ExtraLarge"
' Parameter 2 : (String) "Default value"
' Parameter 3 : (String) "Unlocked"
' Parameter 4 : (Boolean) False
'--------------------------------------------------

long1738 = settingRepository1.GetAttr("LUMINOUSEFFICACY_Small")
'--------------------------------------------------
' Parameter 1 : (String) "LUMINOUSEFFICACY_Small"
' Returned value : (Variant) (Long) 1
'--------------------------------------------------

Dim bSTR3475
bSTR3475 = ""
Dim bSTR3476
bSTR3476 = ""
Dim boolean1738
settingRepository1.GetAttrInfo "LUMINOUSEFFICACY_Small", bSTR3475, bSTR3476, boolean1738
'--------------------------------------------------
' Parameter 1 : (String) "LUMINOUSEFFICACY_Small"
' Parameter 2 : (String) "Default value"
' Parameter 3 : (String) "Unlocked"
' Parameter 4 : (Boolean) False
'--------------------------------------------------

long1739 = settingRepository1.GetAttr("LUMINOUSEFFICACY_ExtraSmall")
'--------------------------------------------------
' Parameter 1 : (String) "LUMINOUSEFFICACY_ExtraSmall"
' Returned value : (Variant) (Long) 1
'--------------------------------------------------

Dim bSTR3477
bSTR3477 = ""
Dim bSTR3478
bSTR3478 = ""
Dim boolean1739
settingRepository1.GetAttrInfo "LUMINOUSEFFICACY_ExtraSmall", bSTR3477, bSTR3478, boolean1739
'--------------------------------------------------
' Parameter 1 : (String) "LUMINOUSEFFICACY_ExtraSmall"
' Parameter 2 : (String) "Default value"
' Parameter 3 : (String) "Unlocked"
' Parameter 4 : (Boolean) False
'--------------------------------------------------

long1740 = settingRepository1.GetAttr("LUMINOUSEFFICACY_Nanometric")
'--------------------------------------------------
' Parameter 1 : (String) "LUMINOUSEFFICACY_Nanometric"
' Returned value : (Variant) (Long) 1
'--------------------------------------------------

Dim bSTR3479
bSTR3479 = ""
Dim bSTR3480
bSTR3480 = ""
Dim boolean1740
settingRepository1.GetAttrInfo "LUMINOUSEFFICACY_Nanometric", bSTR3479, bSTR3480, boolean1740
'--------------------------------------------------
' Parameter 1 : (String) "LUMINOUSEFFICACY_Nanometric"
' Parameter 2 : (String) "Default value"
' Parameter 3 : (String) "Unlocked"
' Parameter 4 : (Boolean) False
'--------------------------------------------------

long1741 = settingRepository1.GetAttr("MOLARABSORPTIONCOEFFICIENT")
'--------------------------------------------------
' Parameter 1 : (String) "MOLARABSORPTIONCOEFFICIENT"
' Returned value : (Variant) (Long) 1
'--------------------------------------------------

Dim bSTR3481
bSTR3481 = ""
Dim bSTR3482
bSTR3482 = ""
Dim boolean1741
settingRepository1.GetAttrInfo "MOLARABSORPTIONCOEFFICIENT", bSTR3481, bSTR3482, boolean1741
'--------------------------------------------------
' Parameter 1 : (String) "MOLARABSORPTIONCOEFFICIENT"
' Parameter 2 : (String) "Default value"
' Parameter 3 : (String) "Unlocked"
' Parameter 4 : (Boolean) False
'--------------------------------------------------

long1742 = settingRepository1.GetAttr("MOLARABSORPTIONCOEFFICIENT_Large")
'--------------------------------------------------
' Parameter 1 : (String) "MOLARABSORPTIONCOEFFICIENT_Large"
' Returned value : (Variant) (Long) 1
'--------------------------------------------------

Dim bSTR3483
bSTR3483 = ""
Dim bSTR3484
bSTR3484 = ""
Dim boolean1742
settingRepository1.GetAttrInfo "MOLARABSORPTIONCOEFFICIENT_Large", bSTR3483, bSTR3484, boolean1742
'--------------------------------------------------
' Parameter 1 : (String) "MOLARABSORPTIONCOEFFICIENT_Large"
' Parameter 2 : (String) "Default value"
' Parameter 3 : (String) "Unlocked"
' Parameter 4 : (Boolean) False
'--------------------------------------------------

long1743 = settingRepository1.GetAttr("MOLARABSORPTIONCOEFFICIENT_ExtraLarge")
'--------------------------------------------------
' Parameter 1 : (String) "MOLARABSORPTIONCOEFFICIENT_ExtraLarge"
' Returned value : (Variant) (Long) 1
'--------------------------------------------------

Dim bSTR3485
bSTR3485 = ""
Dim bSTR3486
bSTR3486 = ""
Dim boolean1743
settingRepository1.GetAttrInfo "MOLARABSORPTIONCOEFFICIENT_ExtraLarge", bSTR3485, bSTR3486, boolean1743
'--------------------------------------------------
' Parameter 1 : (String) "MOLARABSORPTIONCOEFFICIENT_ExtraLarge"
' Parameter 2 : (String) "Default value"
' Parameter 3 : (String) "Unlocked"
' Parameter 4 : (Boolean) False
'--------------------------------------------------

long1744 = settingRepository1.GetAttr("MOLARABSORPTIONCOEFFICIENT_Small")
'--------------------------------------------------
' Parameter 1 : (String) "MOLARABSORPTIONCOEFFICIENT_Small"
' Returned value : (Variant) (Long) 1
'--------------------------------------------------

Dim bSTR3487
bSTR3487 = ""
Dim bSTR3488
bSTR3488 = ""
Dim boolean1744
settingRepository1.GetAttrInfo "MOLARABSORPTIONCOEFFICIENT_Small", bSTR3487, bSTR3488, boolean1744
'--------------------------------------------------
' Parameter 1 : (String) "MOLARABSORPTIONCOEFFICIENT_Small"
' Parameter 2 : (String) "Default value"
' Parameter 3 : (String) "Unlocked"
' Parameter 4 : (Boolean) False
'--------------------------------------------------

long1745 = settingRepository1.GetAttr("MOLARABSORPTIONCOEFFICIENT_ExtraSmall")
'--------------------------------------------------
' Parameter 1 : (String) "MOLARABSORPTIONCOEFFICIENT_ExtraSmall"
' Returned value : (Variant) (Long) 1
'--------------------------------------------------

Dim bSTR3489
bSTR3489 = ""
Dim bSTR3490
bSTR3490 = ""
Dim boolean1745
settingRepository1.GetAttrInfo "MOLARABSORPTIONCOEFFICIENT_ExtraSmall", bSTR3489, bSTR3490, boolean1745
'--------------------------------------------------
' Parameter 1 : (String) "MOLARABSORPTIONCOEFFICIENT_ExtraSmall"
' Parameter 2 : (String) "Default value"
' Parameter 3 : (String) "Unlocked"
' Parameter 4 : (Boolean) False
'--------------------------------------------------

long1746 = settingRepository1.GetAttr("MOLARABSORPTIONCOEFFICIENT_Nanometric")
'--------------------------------------------------
' Parameter 1 : (String) "MOLARABSORPTIONCOEFFICIENT_Nanometric"
' Returned value : (Variant) (Long) 1
'--------------------------------------------------

Dim bSTR3491
bSTR3491 = ""
Dim bSTR3492
bSTR3492 = ""
Dim boolean1746
settingRepository1.GetAttrInfo "MOLARABSORPTIONCOEFFICIENT_Nanometric", bSTR3491, bSTR3492, boolean1746
'--------------------------------------------------
' Parameter 1 : (String) "MOLARABSORPTIONCOEFFICIENT_Nanometric"
' Parameter 2 : (String) "Default value"
' Parameter 3 : (String) "Unlocked"
' Parameter 4 : (Boolean) False
'--------------------------------------------------

long1747 = settingRepository1.GetAttr("ACOUSTICIMPEDANCE")
'--------------------------------------------------
' Parameter 1 : (String) "ACOUSTICIMPEDANCE"
' Returned value : (Variant) (Long) 1
'--------------------------------------------------

Dim bSTR3493
bSTR3493 = ""
Dim bSTR3494
bSTR3494 = ""
Dim boolean1747
settingRepository1.GetAttrInfo "ACOUSTICIMPEDANCE", bSTR3493, bSTR3494, boolean1747
'--------------------------------------------------
' Parameter 1 : (String) "ACOUSTICIMPEDANCE"
' Parameter 2 : (String) "Default value"
' Parameter 3 : (String) "Unlocked"
' Parameter 4 : (Boolean) False
'--------------------------------------------------

long1748 = settingRepository1.GetAttr("ACOUSTICIMPEDANCE_Large")
'--------------------------------------------------
' Parameter 1 : (String) "ACOUSTICIMPEDANCE_Large"
' Returned value : (Variant) (Long) 1
'--------------------------------------------------

Dim bSTR3495
bSTR3495 = ""
Dim bSTR3496
bSTR3496 = ""
Dim boolean1748
settingRepository1.GetAttrInfo "ACOUSTICIMPEDANCE_Large", bSTR3495, bSTR3496, boolean1748
'--------------------------------------------------
' Parameter 1 : (String) "ACOUSTICIMPEDANCE_Large"
' Parameter 2 : (String) "Default value"
' Parameter 3 : (String) "Unlocked"
' Parameter 4 : (Boolean) False
'--------------------------------------------------

long1749 = settingRepository1.GetAttr("ACOUSTICIMPEDANCE_ExtraLarge")
'--------------------------------------------------
' Parameter 1 : (String) "ACOUSTICIMPEDANCE_ExtraLarge"
' Returned value : (Variant) (Long) 1
'--------------------------------------------------

Dim bSTR3497
bSTR3497 = ""
Dim bSTR3498
bSTR3498 = ""
Dim boolean1749
settingRepository1.GetAttrInfo "ACOUSTICIMPEDANCE_ExtraLarge", bSTR3497, bSTR3498, boolean1749
'--------------------------------------------------
' Parameter 1 : (String) "ACOUSTICIMPEDANCE_ExtraLarge"
' Parameter 2 : (String) "Default value"
' Parameter 3 : (String) "Unlocked"
' Parameter 4 : (Boolean) False
'--------------------------------------------------

long1750 = settingRepository1.GetAttr("ACOUSTICIMPEDANCE_Small")
'--------------------------------------------------
' Parameter 1 : (String) "ACOUSTICIMPEDANCE_Small"
' Returned value : (Variant) (Long) 1
'--------------------------------------------------

Dim bSTR3499
bSTR3499 = ""
Dim bSTR3500
bSTR3500 = ""
Dim boolean1750
settingRepository1.GetAttrInfo "ACOUSTICIMPEDANCE_Small", bSTR3499, bSTR3500, boolean1750
'--------------------------------------------------
' Parameter 1 : (String) "ACOUSTICIMPEDANCE_Small"
' Parameter 2 : (String) "Default value"
' Parameter 3 : (String) "Unlocked"
' Parameter 4 : (Boolean) False
'--------------------------------------------------

long1751 = settingRepository1.GetAttr("ACOUSTICIMPEDANCE_ExtraSmall")
'--------------------------------------------------
' Parameter 1 : (String) "ACOUSTICIMPEDANCE_ExtraSmall"
' Returned value : (Variant) (Long) 1
'--------------------------------------------------

Dim bSTR3501
bSTR3501 = ""
Dim bSTR3502
bSTR3502 = ""
Dim boolean1751
settingRepository1.GetAttrInfo "ACOUSTICIMPEDANCE_ExtraSmall", bSTR3501, bSTR3502, boolean1751
'--------------------------------------------------
' Parameter 1 : (String) "ACOUSTICIMPEDANCE_ExtraSmall"
' Parameter 2 : (String) "Default value"
' Parameter 3 : (String) "Unlocked"
' Parameter 4 : (Boolean) False
'--------------------------------------------------

long1752 = settingRepository1.GetAttr("ACOUSTICIMPEDANCE_Nanometric")
'--------------------------------------------------
' Parameter 1 : (String) "ACOUSTICIMPEDANCE_Nanometric"
' Returned value : (Variant) (Long) 1
'--------------------------------------------------

Dim bSTR3503
bSTR3503 = ""
Dim bSTR3504
bSTR3504 = ""
Dim boolean1752
settingRepository1.GetAttrInfo "ACOUSTICIMPEDANCE_Nanometric", bSTR3503, bSTR3504, boolean1752
'--------------------------------------------------
' Parameter 1 : (String) "ACOUSTICIMPEDANCE_Nanometric"
' Parameter 2 : (String) "Default value"
' Parameter 3 : (String) "Unlocked"
' Parameter 4 : (Boolean) False
'--------------------------------------------------

long1753 = settingRepository1.GetAttr("SPECIFICACOUSTICIMPEDANCE")
'--------------------------------------------------
' Parameter 1 : (String) "SPECIFICACOUSTICIMPEDANCE"
' Returned value : (Variant) (Long) 1
'--------------------------------------------------

Dim bSTR3505
bSTR3505 = ""
Dim bSTR3506
bSTR3506 = ""
Dim boolean1753
settingRepository1.GetAttrInfo "SPECIFICACOUSTICIMPEDANCE", bSTR3505, bSTR3506, boolean1753
'--------------------------------------------------
' Parameter 1 : (String) "SPECIFICACOUSTICIMPEDANCE"
' Parameter 2 : (String) "Default value"
' Parameter 3 : (String) "Unlocked"
' Parameter 4 : (Boolean) False
'--------------------------------------------------

long1754 = settingRepository1.GetAttr("SPECIFICACOUSTICIMPEDANCE_Large")
'--------------------------------------------------
' Parameter 1 : (String) "SPECIFICACOUSTICIMPEDANCE_Large"
' Returned value : (Variant) (Long) 1
'--------------------------------------------------

Dim bSTR3507
bSTR3507 = ""
Dim bSTR3508
bSTR3508 = ""
Dim boolean1754
settingRepository1.GetAttrInfo "SPECIFICACOUSTICIMPEDANCE_Large", bSTR3507, bSTR3508, boolean1754
'--------------------------------------------------
' Parameter 1 : (String) "SPECIFICACOUSTICIMPEDANCE_Large"
' Parameter 2 : (String) "Default value"
' Parameter 3 : (String) "Unlocked"
' Parameter 4 : (Boolean) False
'--------------------------------------------------

long1755 = settingRepository1.GetAttr("SPECIFICACOUSTICIMPEDANCE_ExtraLarge")
'--------------------------------------------------
' Parameter 1 : (String) "SPECIFICACOUSTICIMPEDANCE_ExtraLarge"
' Returned value : (Variant) (Long) 1
'--------------------------------------------------

Dim bSTR3509
bSTR3509 = ""
Dim bSTR3510
bSTR3510 = ""
Dim boolean1755
settingRepository1.GetAttrInfo "SPECIFICACOUSTICIMPEDANCE_ExtraLarge", bSTR3509, bSTR3510, boolean1755
'--------------------------------------------------
' Parameter 1 : (String) "SPECIFICACOUSTICIMPEDANCE_ExtraLarge"
' Parameter 2 : (String) "Default value"
' Parameter 3 : (String) "Unlocked"
' Parameter 4 : (Boolean) False
'--------------------------------------------------

long1756 = settingRepository1.GetAttr("SPECIFICACOUSTICIMPEDANCE_Small")
'--------------------------------------------------
' Parameter 1 : (String) "SPECIFICACOUSTICIMPEDANCE_Small"
' Returned value : (Variant) (Long) 1
'--------------------------------------------------

Dim bSTR3511
bSTR3511 = ""
Dim bSTR3512
bSTR3512 = ""
Dim boolean1756
settingRepository1.GetAttrInfo "SPECIFICACOUSTICIMPEDANCE_Small", bSTR3511, bSTR3512, boolean1756
'--------------------------------------------------
' Parameter 1 : (String) "SPECIFICACOUSTICIMPEDANCE_Small"
' Parameter 2 : (String) "Default value"
' Parameter 3 : (String) "Unlocked"
' Parameter 4 : (Boolean) False
'--------------------------------------------------

long1757 = settingRepository1.GetAttr("SPECIFICACOUSTICIMPEDANCE_ExtraSmall")
'--------------------------------------------------
' Parameter 1 : (String) "SPECIFICACOUSTICIMPEDANCE_ExtraSmall"
' Returned value : (Variant) (Long) 1
'--------------------------------------------------

Dim bSTR3513
bSTR3513 = ""
Dim bSTR3514
bSTR3514 = ""
Dim boolean1757
settingRepository1.GetAttrInfo "SPECIFICACOUSTICIMPEDANCE_ExtraSmall", bSTR3513, bSTR3514, boolean1757
'--------------------------------------------------
' Parameter 1 : (String) "SPECIFICACOUSTICIMPEDANCE_ExtraSmall"
' Parameter 2 : (String) "Default value"
' Parameter 3 : (String) "Unlocked"
' Parameter 4 : (Boolean) False
'--------------------------------------------------

long1758 = settingRepository1.GetAttr("SPECIFICACOUSTICIMPEDANCE_Nanometric")
'--------------------------------------------------
' Parameter 1 : (String) "SPECIFICACOUSTICIMPEDANCE_Nanometric"
' Returned value : (Variant) (Long) 1
'--------------------------------------------------

Dim bSTR3515
bSTR3515 = ""
Dim bSTR3516
bSTR3516 = ""
Dim boolean1758
settingRepository1.GetAttrInfo "SPECIFICACOUSTICIMPEDANCE_Nanometric", bSTR3515, bSTR3516, boolean1758
'--------------------------------------------------
' Parameter 1 : (String) "SPECIFICACOUSTICIMPEDANCE_Nanometric"
' Parameter 2 : (String) "Default value"
' Parameter 3 : (String) "Unlocked"
' Parameter 4 : (Boolean) False
'--------------------------------------------------

long1759 = settingRepository1.GetAttr("MECHANICALIMPEDANCE")
'--------------------------------------------------
' Parameter 1 : (String) "MECHANICALIMPEDANCE"
' Returned value : (Variant) (Long) 1
'--------------------------------------------------

Dim bSTR3517
bSTR3517 = ""
Dim bSTR3518
bSTR3518 = ""
Dim boolean1759
settingRepository1.GetAttrInfo "MECHANICALIMPEDANCE", bSTR3517, bSTR3518, boolean1759
'--------------------------------------------------
' Parameter 1 : (String) "MECHANICALIMPEDANCE"
' Parameter 2 : (String) "Default value"
' Parameter 3 : (String) "Unlocked"
' Parameter 4 : (Boolean) False
'--------------------------------------------------

long1760 = settingRepository1.GetAttr("MECHANICALIMPEDANCE_Large")
'--------------------------------------------------
' Parameter 1 : (String) "MECHANICALIMPEDANCE_Large"
' Returned value : (Variant) (Long) 1
'--------------------------------------------------

Dim bSTR3519
bSTR3519 = ""
Dim bSTR3520
bSTR3520 = ""
Dim boolean1760
settingRepository1.GetAttrInfo "MECHANICALIMPEDANCE_Large", bSTR3519, bSTR3520, boolean1760
'--------------------------------------------------
' Parameter 1 : (String) "MECHANICALIMPEDANCE_Large"
' Parameter 2 : (String) "Default value"
' Parameter 3 : (String) "Unlocked"
' Parameter 4 : (Boolean) False
'--------------------------------------------------

long1761 = settingRepository1.GetAttr("MECHANICALIMPEDANCE_ExtraLarge")
'--------------------------------------------------
' Parameter 1 : (String) "MECHANICALIMPEDANCE_ExtraLarge"
' Returned value : (Variant) (Long) 1
'--------------------------------------------------

Dim bSTR3521
bSTR3521 = ""
Dim bSTR3522
bSTR3522 = ""
Dim boolean1761
settingRepository1.GetAttrInfo "MECHANICALIMPEDANCE_ExtraLarge", bSTR3521, bSTR3522, boolean1761
'--------------------------------------------------
' Parameter 1 : (String) "MECHANICALIMPEDANCE_ExtraLarge"
' Parameter 2 : (String) "Default value"
' Parameter 3 : (String) "Unlocked"
' Parameter 4 : (Boolean) False
'--------------------------------------------------

long1762 = settingRepository1.GetAttr("MECHANICALIMPEDANCE_Small")
'--------------------------------------------------
' Parameter 1 : (String) "MECHANICALIMPEDANCE_Small"
' Returned value : (Variant) (Long) 1
'--------------------------------------------------

Dim bSTR3523
bSTR3523 = ""
Dim bSTR3524
bSTR3524 = ""
Dim boolean1762
settingRepository1.GetAttrInfo "MECHANICALIMPEDANCE_Small", bSTR3523, bSTR3524, boolean1762
'--------------------------------------------------
' Parameter 1 : (String) "MECHANICALIMPEDANCE_Small"
' Parameter 2 : (String) "Default value"
' Parameter 3 : (String) "Unlocked"
' Parameter 4 : (Boolean) False
'--------------------------------------------------

long1763 = settingRepository1.GetAttr("MECHANICALIMPEDANCE_ExtraSmall")
'--------------------------------------------------
' Parameter 1 : (String) "MECHANICALIMPEDANCE_ExtraSmall"
' Returned value : (Variant) (Long) 1
'--------------------------------------------------

Dim bSTR3525
bSTR3525 = ""
Dim bSTR3526
bSTR3526 = ""
Dim boolean1763
settingRepository1.GetAttrInfo "MECHANICALIMPEDANCE_ExtraSmall", bSTR3525, bSTR3526, boolean1763
'--------------------------------------------------
' Parameter 1 : (String) "MECHANICALIMPEDANCE_ExtraSmall"
' Parameter 2 : (String) "Default value"
' Parameter 3 : (String) "Unlocked"
' Parameter 4 : (Boolean) False
'--------------------------------------------------

long1764 = settingRepository1.GetAttr("MECHANICALIMPEDANCE_Nanometric")
'--------------------------------------------------
' Parameter 1 : (String) "MECHANICALIMPEDANCE_Nanometric"
' Returned value : (Variant) (Long) 1
'--------------------------------------------------

Dim bSTR3527
bSTR3527 = ""
Dim bSTR3528
bSTR3528 = ""
Dim boolean1764
settingRepository1.GetAttrInfo "MECHANICALIMPEDANCE_Nanometric", bSTR3527, bSTR3528, boolean1764
'--------------------------------------------------
' Parameter 1 : (String) "MECHANICALIMPEDANCE_Nanometric"
' Parameter 2 : (String) "Default value"
' Parameter 3 : (String) "Unlocked"
' Parameter 4 : (Boolean) False
'--------------------------------------------------

long1765 = settingRepository1.GetAttr("SOUNDPOWERLEVEL")
'--------------------------------------------------
' Parameter 1 : (String) "SOUNDPOWERLEVEL"
' Returned value : (Variant) (Long) 1
'--------------------------------------------------

Dim bSTR3529
bSTR3529 = ""
Dim bSTR3530
bSTR3530 = ""
Dim boolean1765
settingRepository1.GetAttrInfo "SOUNDPOWERLEVEL", bSTR3529, bSTR3530, boolean1765
'--------------------------------------------------
' Parameter 1 : (String) "SOUNDPOWERLEVEL"
' Parameter 2 : (String) "Default value"
' Parameter 3 : (String) "Unlocked"
' Parameter 4 : (Boolean) False
'--------------------------------------------------

long1766 = settingRepository1.GetAttr("SOUNDPOWERLEVEL_Large")
'--------------------------------------------------
' Parameter 1 : (String) "SOUNDPOWERLEVEL_Large"
' Returned value : (Variant) (Long) 1
'--------------------------------------------------

Dim bSTR3531
bSTR3531 = ""
Dim bSTR3532
bSTR3532 = ""
Dim boolean1766
settingRepository1.GetAttrInfo "SOUNDPOWERLEVEL_Large", bSTR3531, bSTR3532, boolean1766
'--------------------------------------------------
' Parameter 1 : (String) "SOUNDPOWERLEVEL_Large"
' Parameter 2 : (String) "Default value"
' Parameter 3 : (String) "Unlocked"
' Parameter 4 : (Boolean) False
'--------------------------------------------------

long1767 = settingRepository1.GetAttr("SOUNDPOWERLEVEL_ExtraLarge")
'--------------------------------------------------
' Parameter 1 : (String) "SOUNDPOWERLEVEL_ExtraLarge"
' Returned value : (Variant) (Long) 1
'--------------------------------------------------

Dim bSTR3533
bSTR3533 = ""
Dim bSTR3534
bSTR3534 = ""
Dim boolean1767
settingRepository1.GetAttrInfo "SOUNDPOWERLEVEL_ExtraLarge", bSTR3533, bSTR3534, boolean1767
'--------------------------------------------------
' Parameter 1 : (String) "SOUNDPOWERLEVEL_ExtraLarge"
' Parameter 2 : (String) "Default value"
' Parameter 3 : (String) "Unlocked"
' Parameter 4 : (Boolean) False
'--------------------------------------------------

long1768 = settingRepository1.GetAttr("SOUNDPOWERLEVEL_Small")
'--------------------------------------------------
' Parameter 1 : (String) "SOUNDPOWERLEVEL_Small"
' Returned value : (Variant) (Long) 1
'--------------------------------------------------

Dim bSTR3535
bSTR3535 = ""
Dim bSTR3536
bSTR3536 = ""
Dim boolean1768
settingRepository1.GetAttrInfo "SOUNDPOWERLEVEL_Small", bSTR3535, bSTR3536, boolean1768
'--------------------------------------------------
' Parameter 1 : (String) "SOUNDPOWERLEVEL_Small"
' Parameter 2 : (String) "Default value"
' Parameter 3 : (String) "Unlocked"
' Parameter 4 : (Boolean) False
'--------------------------------------------------

long1769 = settingRepository1.GetAttr("SOUNDPOWERLEVEL_ExtraSmall")
'--------------------------------------------------
' Parameter 1 : (String) "SOUNDPOWERLEVEL_ExtraSmall"
' Returned value : (Variant) (Long) 1
'--------------------------------------------------

Dim bSTR3537
bSTR3537 = ""
Dim bSTR3538
bSTR3538 = ""
Dim boolean1769
settingRepository1.GetAttrInfo "SOUNDPOWERLEVEL_ExtraSmall", bSTR3537, bSTR3538, boolean1769
'--------------------------------------------------
' Parameter 1 : (String) "SOUNDPOWERLEVEL_ExtraSmall"
' Parameter 2 : (String) "Default value"
' Parameter 3 : (String) "Unlocked"
' Parameter 4 : (Boolean) False
'--------------------------------------------------

long1770 = settingRepository1.GetAttr("SOUNDPOWERLEVEL_Nanometric")
'--------------------------------------------------
' Parameter 1 : (String) "SOUNDPOWERLEVEL_Nanometric"
' Returned value : (Variant) (Long) 1
'--------------------------------------------------

Dim bSTR3539
bSTR3539 = ""
Dim bSTR3540
bSTR3540 = ""
Dim boolean1770
settingRepository1.GetAttrInfo "SOUNDPOWERLEVEL_Nanometric", bSTR3539, bSTR3540, boolean1770
'--------------------------------------------------
' Parameter 1 : (String) "SOUNDPOWERLEVEL_Nanometric"
' Parameter 2 : (String) "Default value"
' Parameter 3 : (String) "Unlocked"
' Parameter 4 : (Boolean) False
'--------------------------------------------------

long1771 = settingRepository1.GetAttr("LOUNDNESSLEVEL")
'--------------------------------------------------
' Parameter 1 : (String) "LOUNDNESSLEVEL"
' Returned value : (Variant) (Long) 1
'--------------------------------------------------

Dim bSTR3541
bSTR3541 = ""
Dim bSTR3542
bSTR3542 = ""
Dim boolean1771
settingRepository1.GetAttrInfo "LOUNDNESSLEVEL", bSTR3541, bSTR3542, boolean1771
'--------------------------------------------------
' Parameter 1 : (String) "LOUNDNESSLEVEL"
' Parameter 2 : (String) "Default value"
' Parameter 3 : (String) "Unlocked"
' Parameter 4 : (Boolean) False
'--------------------------------------------------

long1772 = settingRepository1.GetAttr("LOUNDNESSLEVEL_Large")
'--------------------------------------------------
' Parameter 1 : (String) "LOUNDNESSLEVEL_Large"
' Returned value : (Variant) (Long) 1
'--------------------------------------------------

Dim bSTR3543
bSTR3543 = ""
Dim bSTR3544
bSTR3544 = ""
Dim boolean1772
settingRepository1.GetAttrInfo "LOUNDNESSLEVEL_Large", bSTR3543, bSTR3544, boolean1772
'--------------------------------------------------
' Parameter 1 : (String) "LOUNDNESSLEVEL_Large"
' Parameter 2 : (String) "Default value"
' Parameter 3 : (String) "Unlocked"
' Parameter 4 : (Boolean) False
'--------------------------------------------------

long1773 = settingRepository1.GetAttr("LOUNDNESSLEVEL_ExtraLarge")
'--------------------------------------------------
' Parameter 1 : (String) "LOUNDNESSLEVEL_ExtraLarge"
' Returned value : (Variant) (Long) 1
'--------------------------------------------------

Dim bSTR3545
bSTR3545 = ""
Dim bSTR3546
bSTR3546 = ""
Dim boolean1773
settingRepository1.GetAttrInfo "LOUNDNESSLEVEL_ExtraLarge", bSTR3545, bSTR3546, boolean1773
'--------------------------------------------------
' Parameter 1 : (String) "LOUNDNESSLEVEL_ExtraLarge"
' Parameter 2 : (String) "Default value"
' Parameter 3 : (String) "Unlocked"
' Parameter 4 : (Boolean) False
'--------------------------------------------------

long1774 = settingRepository1.GetAttr("LOUNDNESSLEVEL_Small")
'--------------------------------------------------
' Parameter 1 : (String) "LOUNDNESSLEVEL_Small"
' Returned value : (Variant) (Long) 1
'--------------------------------------------------

Dim bSTR3547
bSTR3547 = ""
Dim bSTR3548
bSTR3548 = ""
Dim boolean1774
settingRepository1.GetAttrInfo "LOUNDNESSLEVEL_Small", bSTR3547, bSTR3548, boolean1774
'--------------------------------------------------
' Parameter 1 : (String) "LOUNDNESSLEVEL_Small"
' Parameter 2 : (String) "Default value"
' Parameter 3 : (String) "Unlocked"
' Parameter 4 : (Boolean) False
'--------------------------------------------------

long1775 = settingRepository1.GetAttr("LOUNDNESSLEVEL_ExtraSmall")
'--------------------------------------------------
' Parameter 1 : (String) "LOUNDNESSLEVEL_ExtraSmall"
' Returned value : (Variant) (Long) 1
'--------------------------------------------------

Dim bSTR3549
bSTR3549 = ""
Dim bSTR3550
bSTR3550 = ""
Dim boolean1775
settingRepository1.GetAttrInfo "LOUNDNESSLEVEL_ExtraSmall", bSTR3549, bSTR3550, boolean1775
'--------------------------------------------------
' Parameter 1 : (String) "LOUNDNESSLEVEL_ExtraSmall"
' Parameter 2 : (String) "Default value"
' Parameter 3 : (String) "Unlocked"
' Parameter 4 : (Boolean) False
'--------------------------------------------------

long1776 = settingRepository1.GetAttr("LOUNDNESSLEVEL_Nanometric")
'--------------------------------------------------
' Parameter 1 : (String) "LOUNDNESSLEVEL_Nanometric"
' Returned value : (Variant) (Long) 1
'--------------------------------------------------

Dim bSTR3551
bSTR3551 = ""
Dim bSTR3552
bSTR3552 = ""
Dim boolean1776
settingRepository1.GetAttrInfo "LOUNDNESSLEVEL_Nanometric", bSTR3551, bSTR3552, boolean1776
'--------------------------------------------------
' Parameter 1 : (String) "LOUNDNESSLEVEL_Nanometric"
' Parameter 2 : (String) "Default value"
' Parameter 3 : (String) "Unlocked"
' Parameter 4 : (Boolean) False
'--------------------------------------------------

long1777 = settingRepository1.GetAttr("LOUNDNESS")
'--------------------------------------------------
' Parameter 1 : (String) "LOUNDNESS"
' Returned value : (Variant) (Long) 1
'--------------------------------------------------

Dim bSTR3553
bSTR3553 = ""
Dim bSTR3554
bSTR3554 = ""
Dim boolean1777
settingRepository1.GetAttrInfo "LOUNDNESS", bSTR3553, bSTR3554, boolean1777
'--------------------------------------------------
' Parameter 1 : (String) "LOUNDNESS"
' Parameter 2 : (String) "Default value"
' Parameter 3 : (String) "Unlocked"
' Parameter 4 : (Boolean) False
'--------------------------------------------------

long1778 = settingRepository1.GetAttr("LOUNDNESS_Large")
'--------------------------------------------------
' Parameter 1 : (String) "LOUNDNESS_Large"
' Returned value : (Variant) (Long) 1
'--------------------------------------------------

Dim bSTR3555
bSTR3555 = ""
Dim bSTR3556
bSTR3556 = ""
Dim boolean1778
settingRepository1.GetAttrInfo "LOUNDNESS_Large", bSTR3555, bSTR3556, boolean1778
'--------------------------------------------------
' Parameter 1 : (String) "LOUNDNESS_Large"
' Parameter 2 : (String) "Default value"
' Parameter 3 : (String) "Unlocked"
' Parameter 4 : (Boolean) False
'--------------------------------------------------

long1779 = settingRepository1.GetAttr("LOUNDNESS_ExtraLarge")
'--------------------------------------------------
' Parameter 1 : (String) "LOUNDNESS_ExtraLarge"
' Returned value : (Variant) (Long) 1
'--------------------------------------------------

Dim bSTR3557
bSTR3557 = ""
Dim bSTR3558
bSTR3558 = ""
Dim boolean1779
settingRepository1.GetAttrInfo "LOUNDNESS_ExtraLarge", bSTR3557, bSTR3558, boolean1779
'--------------------------------------------------
' Parameter 1 : (String) "LOUNDNESS_ExtraLarge"
' Parameter 2 : (String) "Default value"
' Parameter 3 : (String) "Unlocked"
' Parameter 4 : (Boolean) False
'--------------------------------------------------

long1780 = settingRepository1.GetAttr("LOUNDNESS_Small")
'--------------------------------------------------
' Parameter 1 : (String) "LOUNDNESS_Small"
' Returned value : (Variant) (Long) 1
'--------------------------------------------------

Dim bSTR3559
bSTR3559 = ""
Dim bSTR3560
bSTR3560 = ""
Dim boolean1780
settingRepository1.GetAttrInfo "LOUNDNESS_Small", bSTR3559, bSTR3560, boolean1780
'--------------------------------------------------
' Parameter 1 : (String) "LOUNDNESS_Small"
' Parameter 2 : (String) "Default value"
' Parameter 3 : (String) "Unlocked"
' Parameter 4 : (Boolean) False
'--------------------------------------------------

long1781 = settingRepository1.GetAttr("LOUNDNESS_ExtraSmall")
'--------------------------------------------------
' Parameter 1 : (String) "LOUNDNESS_ExtraSmall"
' Returned value : (Variant) (Long) 1
'--------------------------------------------------

Dim bSTR3561
bSTR3561 = ""
Dim bSTR3562
bSTR3562 = ""
Dim boolean1781
settingRepository1.GetAttrInfo "LOUNDNESS_ExtraSmall", bSTR3561, bSTR3562, boolean1781
'--------------------------------------------------
' Parameter 1 : (String) "LOUNDNESS_ExtraSmall"
' Parameter 2 : (String) "Default value"
' Parameter 3 : (String) "Unlocked"
' Parameter 4 : (Boolean) False
'--------------------------------------------------

long1782 = settingRepository1.GetAttr("LOUNDNESS_Nanometric")
'--------------------------------------------------
' Parameter 1 : (String) "LOUNDNESS_Nanometric"
' Returned value : (Variant) (Long) 1
'--------------------------------------------------

Dim bSTR3563
bSTR3563 = ""
Dim bSTR3564
bSTR3564 = ""
Dim boolean1782
settingRepository1.GetAttrInfo "LOUNDNESS_Nanometric", bSTR3563, bSTR3564, boolean1782
'--------------------------------------------------
' Parameter 1 : (String) "LOUNDNESS_Nanometric"
' Parameter 2 : (String) "Default value"
' Parameter 3 : (String) "Unlocked"
' Parameter 4 : (Boolean) False
'--------------------------------------------------

long1783 = settingRepository1.GetAttr("NUMBEROFMOLECULES")
'--------------------------------------------------
' Parameter 1 : (String) "NUMBEROFMOLECULES"
' Returned value : (Variant) (Long) 1
'--------------------------------------------------

Dim bSTR3565
bSTR3565 = ""
Dim bSTR3566
bSTR3566 = ""
Dim boolean1783
settingRepository1.GetAttrInfo "NUMBEROFMOLECULES", bSTR3565, bSTR3566, boolean1783
'--------------------------------------------------
' Parameter 1 : (String) "NUMBEROFMOLECULES"
' Parameter 2 : (String) "Default value"
' Parameter 3 : (String) "Unlocked"
' Parameter 4 : (Boolean) False
'--------------------------------------------------

long1784 = settingRepository1.GetAttr("NUMBEROFMOLECULES_Large")
'--------------------------------------------------
' Parameter 1 : (String) "NUMBEROFMOLECULES_Large"
' Returned value : (Variant) (Long) 1
'--------------------------------------------------

Dim bSTR3567
bSTR3567 = ""
Dim bSTR3568
bSTR3568 = ""
Dim boolean1784
settingRepository1.GetAttrInfo "NUMBEROFMOLECULES_Large", bSTR3567, bSTR3568, boolean1784
'--------------------------------------------------
' Parameter 1 : (String) "NUMBEROFMOLECULES_Large"
' Parameter 2 : (String) "Default value"
' Parameter 3 : (String) "Unlocked"
' Parameter 4 : (Boolean) False
'--------------------------------------------------

long1785 = settingRepository1.GetAttr("NUMBEROFMOLECULES_ExtraLarge")
'--------------------------------------------------
' Parameter 1 : (String) "NUMBEROFMOLECULES_ExtraLarge"
' Returned value : (Variant) (Long) 1
'--------------------------------------------------

Dim bSTR3569
bSTR3569 = ""
Dim bSTR3570
bSTR3570 = ""
Dim boolean1785
settingRepository1.GetAttrInfo "NUMBEROFMOLECULES_ExtraLarge", bSTR3569, bSTR3570, boolean1785
'--------------------------------------------------
' Parameter 1 : (String) "NUMBEROFMOLECULES_ExtraLarge"
' Parameter 2 : (String) "Default value"
' Parameter 3 : (String) "Unlocked"
' Parameter 4 : (Boolean) False
'--------------------------------------------------

long1786 = settingRepository1.GetAttr("NUMBEROFMOLECULES_Small")
'--------------------------------------------------
' Parameter 1 : (String) "NUMBEROFMOLECULES_Small"
' Returned value : (Variant) (Long) 1
'--------------------------------------------------

Dim bSTR3571
bSTR3571 = ""
Dim bSTR3572
bSTR3572 = ""
Dim boolean1786
settingRepository1.GetAttrInfo "NUMBEROFMOLECULES_Small", bSTR3571, bSTR3572, boolean1786
'--------------------------------------------------
' Parameter 1 : (String) "NUMBEROFMOLECULES_Small"
' Parameter 2 : (String) "Default value"
' Parameter 3 : (String) "Unlocked"
' Parameter 4 : (Boolean) False
'--------------------------------------------------

long1787 = settingRepository1.GetAttr("NUMBEROFMOLECULES_ExtraSmall")
'--------------------------------------------------
' Parameter 1 : (String) "NUMBEROFMOLECULES_ExtraSmall"
' Returned value : (Variant) (Long) 1
'--------------------------------------------------

Dim bSTR3573
bSTR3573 = ""
Dim bSTR3574
bSTR3574 = ""
Dim boolean1787
settingRepository1.GetAttrInfo "NUMBEROFMOLECULES_ExtraSmall", bSTR3573, bSTR3574, boolean1787
'--------------------------------------------------
' Parameter 1 : (String) "NUMBEROFMOLECULES_ExtraSmall"
' Parameter 2 : (String) "Default value"
' Parameter 3 : (String) "Unlocked"
' Parameter 4 : (Boolean) False
'--------------------------------------------------

long1788 = settingRepository1.GetAttr("NUMBEROFMOLECULES_Nanometric")
'--------------------------------------------------
' Parameter 1 : (String) "NUMBEROFMOLECULES_Nanometric"
' Returned value : (Variant) (Long) 1
'--------------------------------------------------

Dim bSTR3575
bSTR3575 = ""
Dim bSTR3576
bSTR3576 = ""
Dim boolean1788
settingRepository1.GetAttrInfo "NUMBEROFMOLECULES_Nanometric", bSTR3575, bSTR3576, boolean1788
'--------------------------------------------------
' Parameter 1 : (String) "NUMBEROFMOLECULES_Nanometric"
' Parameter 2 : (String) "Default value"
' Parameter 3 : (String) "Unlocked"
' Parameter 4 : (Boolean) False
'--------------------------------------------------

long1789 = settingRepository1.GetAttr("MOLARVOLUME")
'--------------------------------------------------
' Parameter 1 : (String) "MOLARVOLUME"
' Returned value : (Variant) (Long) 1
'--------------------------------------------------

Dim bSTR3577
bSTR3577 = ""
Dim bSTR3578
bSTR3578 = ""
Dim boolean1789
settingRepository1.GetAttrInfo "MOLARVOLUME", bSTR3577, bSTR3578, boolean1789
'--------------------------------------------------
' Parameter 1 : (String) "MOLARVOLUME"
' Parameter 2 : (String) "Default value"
' Parameter 3 : (String) "Unlocked"
' Parameter 4 : (Boolean) False
'--------------------------------------------------

long1790 = settingRepository1.GetAttr("MOLARVOLUME_Large")
'--------------------------------------------------
' Parameter 1 : (String) "MOLARVOLUME_Large"
' Returned value : (Variant) (Long) 1
'--------------------------------------------------

Dim bSTR3579
bSTR3579 = ""
Dim bSTR3580
bSTR3580 = ""
Dim boolean1790
settingRepository1.GetAttrInfo "MOLARVOLUME_Large", bSTR3579, bSTR3580, boolean1790
'--------------------------------------------------
' Parameter 1 : (String) "MOLARVOLUME_Large"
' Parameter 2 : (String) "Default value"
' Parameter 3 : (String) "Unlocked"
' Parameter 4 : (Boolean) False
'--------------------------------------------------

long1791 = settingRepository1.GetAttr("MOLARVOLUME_ExtraLarge")
'--------------------------------------------------
' Parameter 1 : (String) "MOLARVOLUME_ExtraLarge"
' Returned value : (Variant) (Long) 1
'--------------------------------------------------

Dim bSTR3581
bSTR3581 = ""
Dim bSTR3582
bSTR3582 = ""
Dim boolean1791
settingRepository1.GetAttrInfo "MOLARVOLUME_ExtraLarge", bSTR3581, bSTR3582, boolean1791
'--------------------------------------------------
' Parameter 1 : (String) "MOLARVOLUME_ExtraLarge"
' Parameter 2 : (String) "Default value"
' Parameter 3 : (String) "Unlocked"
' Parameter 4 : (Boolean) False
'--------------------------------------------------

long1792 = settingRepository1.GetAttr("MOLARVOLUME_Small")
'--------------------------------------------------
' Parameter 1 : (String) "MOLARVOLUME_Small"
' Returned value : (Variant) (Long) 1
'--------------------------------------------------

Dim bSTR3583
bSTR3583 = ""
Dim bSTR3584
bSTR3584 = ""
Dim boolean1792
settingRepository1.GetAttrInfo "MOLARVOLUME_Small", bSTR3583, bSTR3584, boolean1792
'--------------------------------------------------
' Parameter 1 : (String) "MOLARVOLUME_Small"
' Parameter 2 : (String) "Default value"
' Parameter 3 : (String) "Unlocked"
' Parameter 4 : (Boolean) False
'--------------------------------------------------

long1793 = settingRepository1.GetAttr("MOLARVOLUME_ExtraSmall")
'--------------------------------------------------
' Parameter 1 : (String) "MOLARVOLUME_ExtraSmall"
' Returned value : (Variant) (Long) 1
'--------------------------------------------------

Dim bSTR3585
bSTR3585 = ""
Dim bSTR3586
bSTR3586 = ""
Dim boolean1793
settingRepository1.GetAttrInfo "MOLARVOLUME_ExtraSmall", bSTR3585, bSTR3586, boolean1793
'--------------------------------------------------
' Parameter 1 : (String) "MOLARVOLUME_ExtraSmall"
' Parameter 2 : (String) "Default value"
' Parameter 3 : (String) "Unlocked"
' Parameter 4 : (Boolean) False
'--------------------------------------------------

long1794 = settingRepository1.GetAttr("MOLARVOLUME_Nanometric")
'--------------------------------------------------
' Parameter 1 : (String) "MOLARVOLUME_Nanometric"
' Returned value : (Variant) (Long) 1
'--------------------------------------------------

Dim bSTR3587
bSTR3587 = ""
Dim bSTR3588
bSTR3588 = ""
Dim boolean1794
settingRepository1.GetAttrInfo "MOLARVOLUME_Nanometric", bSTR3587, bSTR3588, boolean1794
'--------------------------------------------------
' Parameter 1 : (String) "MOLARVOLUME_Nanometric"
' Parameter 2 : (String) "Default value"
' Parameter 3 : (String) "Unlocked"
' Parameter 4 : (Boolean) False
'--------------------------------------------------

long1795 = settingRepository1.GetAttr("MOLARINTERNALENERGY")
'--------------------------------------------------
' Parameter 1 : (String) "MOLARINTERNALENERGY"
' Returned value : (Variant) (Long) 1
'--------------------------------------------------

Dim bSTR3589
bSTR3589 = ""
Dim bSTR3590
bSTR3590 = ""
Dim boolean1795
settingRepository1.GetAttrInfo "MOLARINTERNALENERGY", bSTR3589, bSTR3590, boolean1795
'--------------------------------------------------
' Parameter 1 : (String) "MOLARINTERNALENERGY"
' Parameter 2 : (String) "Default value"
' Parameter 3 : (String) "Unlocked"
' Parameter 4 : (Boolean) False
'--------------------------------------------------

long1796 = settingRepository1.GetAttr("MOLARINTERNALENERGY_Large")
'--------------------------------------------------
' Parameter 1 : (String) "MOLARINTERNALENERGY_Large"
' Returned value : (Variant) (Long) 1
'--------------------------------------------------

Dim bSTR3591
bSTR3591 = ""
Dim bSTR3592
bSTR3592 = ""
Dim boolean1796
settingRepository1.GetAttrInfo "MOLARINTERNALENERGY_Large", bSTR3591, bSTR3592, boolean1796
'--------------------------------------------------
' Parameter 1 : (String) "MOLARINTERNALENERGY_Large"
' Parameter 2 : (String) "Default value"
' Parameter 3 : (String) "Unlocked"
' Parameter 4 : (Boolean) False
'--------------------------------------------------

long1797 = settingRepository1.GetAttr("MOLARINTERNALENERGY_ExtraLarge")
'--------------------------------------------------
' Parameter 1 : (String) "MOLARINTERNALENERGY_ExtraLarge"
' Returned value : (Variant) (Long) 1
'--------------------------------------------------

Dim bSTR3593
bSTR3593 = ""
Dim bSTR3594
bSTR3594 = ""
Dim boolean1797
settingRepository1.GetAttrInfo "MOLARINTERNALENERGY_ExtraLarge", bSTR3593, bSTR3594, boolean1797
'--------------------------------------------------
' Parameter 1 : (String) "MOLARINTERNALENERGY_ExtraLarge"
' Parameter 2 : (String) "Default value"
' Parameter 3 : (String) "Unlocked"
' Parameter 4 : (Boolean) False
'--------------------------------------------------

long1798 = settingRepository1.GetAttr("MOLARINTERNALENERGY_Small")
'--------------------------------------------------
' Parameter 1 : (String) "MOLARINTERNALENERGY_Small"
' Returned value : (Variant) (Long) 1
'--------------------------------------------------

Dim bSTR3595
bSTR3595 = ""
Dim bSTR3596
bSTR3596 = ""
Dim boolean1798
settingRepository1.GetAttrInfo "MOLARINTERNALENERGY_Small", bSTR3595, bSTR3596, boolean1798
'--------------------------------------------------
' Parameter 1 : (String) "MOLARINTERNALENERGY_Small"
' Parameter 2 : (String) "Default value"
' Parameter 3 : (String) "Unlocked"
' Parameter 4 : (Boolean) False
'--------------------------------------------------

long1799 = settingRepository1.GetAttr("MOLARINTERNALENERGY_ExtraSmall")
'--------------------------------------------------
' Parameter 1 : (String) "MOLARINTERNALENERGY_ExtraSmall"
' Returned value : (Variant) (Long) 1
'--------------------------------------------------

Dim bSTR3597
bSTR3597 = ""
Dim bSTR3598
bSTR3598 = ""
Dim boolean1799
settingRepository1.GetAttrInfo "MOLARINTERNALENERGY_ExtraSmall", bSTR3597, bSTR3598, boolean1799
'--------------------------------------------------
' Parameter 1 : (String) "MOLARINTERNALENERGY_ExtraSmall"
' Parameter 2 : (String) "Default value"
' Parameter 3 : (String) "Unlocked"
' Parameter 4 : (Boolean) False
'--------------------------------------------------

long1800 = settingRepository1.GetAttr("MOLARINTERNALENERGY_Nanometric")
'--------------------------------------------------
' Parameter 1 : (String) "MOLARINTERNALENERGY_Nanometric"
' Returned value : (Variant) (Long) 1
'--------------------------------------------------

Dim bSTR3599
bSTR3599 = ""
Dim bSTR3600
bSTR3600 = ""
Dim boolean1800
settingRepository1.GetAttrInfo "MOLARINTERNALENERGY_Nanometric", bSTR3599, bSTR3600, boolean1800
'--------------------------------------------------
' Parameter 1 : (String) "MOLARINTERNALENERGY_Nanometric"
' Parameter 2 : (String) "Default value"
' Parameter 3 : (String) "Unlocked"
' Parameter 4 : (Boolean) False
'--------------------------------------------------

long1801 = settingRepository1.GetAttr("MOLARHEATCAPACITY")
'--------------------------------------------------
' Parameter 1 : (String) "MOLARHEATCAPACITY"
' Returned value : (Variant) (Long) 1
'--------------------------------------------------

Dim bSTR3601
bSTR3601 = ""
Dim bSTR3602
bSTR3602 = ""
Dim boolean1801
settingRepository1.GetAttrInfo "MOLARHEATCAPACITY", bSTR3601, bSTR3602, boolean1801
'--------------------------------------------------
' Parameter 1 : (String) "MOLARHEATCAPACITY"
' Parameter 2 : (String) "Default value"
' Parameter 3 : (String) "Unlocked"
' Parameter 4 : (Boolean) False
'--------------------------------------------------

long1802 = settingRepository1.GetAttr("MOLARHEATCAPACITY_Large")
'--------------------------------------------------
' Parameter 1 : (String) "MOLARHEATCAPACITY_Large"
' Returned value : (Variant) (Long) 1
'--------------------------------------------------

Dim bSTR3603
bSTR3603 = ""
Dim bSTR3604
bSTR3604 = ""
Dim boolean1802
settingRepository1.GetAttrInfo "MOLARHEATCAPACITY_Large", bSTR3603, bSTR3604, boolean1802
'--------------------------------------------------
' Parameter 1 : (String) "MOLARHEATCAPACITY_Large"
' Parameter 2 : (String) "Default value"
' Parameter 3 : (String) "Unlocked"
' Parameter 4 : (Boolean) False
'--------------------------------------------------

long1803 = settingRepository1.GetAttr("MOLARHEATCAPACITY_ExtraLarge")
'--------------------------------------------------
' Parameter 1 : (String) "MOLARHEATCAPACITY_ExtraLarge"
' Returned value : (Variant) (Long) 1
'--------------------------------------------------

Dim bSTR3605
bSTR3605 = ""
Dim bSTR3606
bSTR3606 = ""
Dim boolean1803
settingRepository1.GetAttrInfo "MOLARHEATCAPACITY_ExtraLarge", bSTR3605, bSTR3606, boolean1803
'--------------------------------------------------
' Parameter 1 : (String) "MOLARHEATCAPACITY_ExtraLarge"
' Parameter 2 : (String) "Default value"
' Parameter 3 : (String) "Unlocked"
' Parameter 4 : (Boolean) False
'--------------------------------------------------

long1804 = settingRepository1.GetAttr("MOLARHEATCAPACITY_Small")
'--------------------------------------------------
' Parameter 1 : (String) "MOLARHEATCAPACITY_Small"
' Returned value : (Variant) (Long) 1
'--------------------------------------------------

Dim bSTR3607
bSTR3607 = ""
Dim bSTR3608
bSTR3608 = ""
Dim boolean1804
settingRepository1.GetAttrInfo "MOLARHEATCAPACITY_Small", bSTR3607, bSTR3608, boolean1804
'--------------------------------------------------
' Parameter 1 : (String) "MOLARHEATCAPACITY_Small"
' Parameter 2 : (String) "Default value"
' Parameter 3 : (String) "Unlocked"
' Parameter 4 : (Boolean) False
'--------------------------------------------------

long1805 = settingRepository1.GetAttr("MOLARHEATCAPACITY_ExtraSmall")
'--------------------------------------------------
' Parameter 1 : (String) "MOLARHEATCAPACITY_ExtraSmall"
' Returned value : (Variant) (Long) 1
'--------------------------------------------------

Dim bSTR3609
bSTR3609 = ""
Dim bSTR3610
bSTR3610 = ""
Dim boolean1805
settingRepository1.GetAttrInfo "MOLARHEATCAPACITY_ExtraSmall", bSTR3609, bSTR3610, boolean1805
'--------------------------------------------------
' Parameter 1 : (String) "MOLARHEATCAPACITY_ExtraSmall"
' Parameter 2 : (String) "Default value"
' Parameter 3 : (String) "Unlocked"
' Parameter 4 : (Boolean) False
'--------------------------------------------------

long1806 = settingRepository1.GetAttr("MOLARHEATCAPACITY_Nanometric")
'--------------------------------------------------
' Parameter 1 : (String) "MOLARHEATCAPACITY_Nanometric"
' Returned value : (Variant) (Long) 1
'--------------------------------------------------

Dim bSTR3611
bSTR3611 = ""
Dim bSTR3612
bSTR3612 = ""
Dim boolean1806
settingRepository1.GetAttrInfo "MOLARHEATCAPACITY_Nanometric", bSTR3611, bSTR3612, boolean1806
'--------------------------------------------------
' Parameter 1 : (String) "MOLARHEATCAPACITY_Nanometric"
' Parameter 2 : (String) "Default value"
' Parameter 3 : (String) "Unlocked"
' Parameter 4 : (Boolean) False
'--------------------------------------------------

long1807 = settingRepository1.GetAttr("NUMBERDENSITY")
'--------------------------------------------------
' Parameter 1 : (String) "NUMBERDENSITY"
' Returned value : (Variant) (Long) 1
'--------------------------------------------------

Dim bSTR3613
bSTR3613 = ""
Dim bSTR3614
bSTR3614 = ""
Dim boolean1807
settingRepository1.GetAttrInfo "NUMBERDENSITY", bSTR3613, bSTR3614, boolean1807
'--------------------------------------------------
' Parameter 1 : (String) "NUMBERDENSITY"
' Parameter 2 : (String) "Default value"
' Parameter 3 : (String) "Unlocked"
' Parameter 4 : (Boolean) False
'--------------------------------------------------

long1808 = settingRepository1.GetAttr("NUMBERDENSITY_Large")
'--------------------------------------------------
' Parameter 1 : (String) "NUMBERDENSITY_Large"
' Returned value : (Variant) (Long) 1
'--------------------------------------------------

Dim bSTR3615
bSTR3615 = ""
Dim bSTR3616
bSTR3616 = ""
Dim boolean1808
settingRepository1.GetAttrInfo "NUMBERDENSITY_Large", bSTR3615, bSTR3616, boolean1808
'--------------------------------------------------
' Parameter 1 : (String) "NUMBERDENSITY_Large"
' Parameter 2 : (String) "Default value"
' Parameter 3 : (String) "Unlocked"
' Parameter 4 : (Boolean) False
'--------------------------------------------------

long1809 = settingRepository1.GetAttr("NUMBERDENSITY_ExtraLarge")
'--------------------------------------------------
' Parameter 1 : (String) "NUMBERDENSITY_ExtraLarge"
' Returned value : (Variant) (Long) 1
'--------------------------------------------------

Dim bSTR3617
bSTR3617 = ""
Dim bSTR3618
bSTR3618 = ""
Dim boolean1809
settingRepository1.GetAttrInfo "NUMBERDENSITY_ExtraLarge", bSTR3617, bSTR3618, boolean1809
'--------------------------------------------------
' Parameter 1 : (String) "NUMBERDENSITY_ExtraLarge"
' Parameter 2 : (String) "Default value"
' Parameter 3 : (String) "Unlocked"
' Parameter 4 : (Boolean) False
'--------------------------------------------------

long1810 = settingRepository1.GetAttr("NUMBERDENSITY_Small")
'--------------------------------------------------
' Parameter 1 : (String) "NUMBERDENSITY_Small"
' Returned value : (Variant) (Long) 1
'--------------------------------------------------

Dim bSTR3619
bSTR3619 = ""
Dim bSTR3620
bSTR3620 = ""
Dim boolean1810
settingRepository1.GetAttrInfo "NUMBERDENSITY_Small", bSTR3619, bSTR3620, boolean1810
'--------------------------------------------------
' Parameter 1 : (String) "NUMBERDENSITY_Small"
' Parameter 2 : (String) "Default value"
' Parameter 3 : (String) "Unlocked"
' Parameter 4 : (Boolean) False
'--------------------------------------------------

long1811 = settingRepository1.GetAttr("NUMBERDENSITY_ExtraSmall")
'--------------------------------------------------
' Parameter 1 : (String) "NUMBERDENSITY_ExtraSmall"
' Returned value : (Variant) (Long) 1
'--------------------------------------------------

Dim bSTR3621
bSTR3621 = ""
Dim bSTR3622
bSTR3622 = ""
Dim boolean1811
settingRepository1.GetAttrInfo "NUMBERDENSITY_ExtraSmall", bSTR3621, bSTR3622, boolean1811
'--------------------------------------------------
' Parameter 1 : (String) "NUMBERDENSITY_ExtraSmall"
' Parameter 2 : (String) "Default value"
' Parameter 3 : (String) "Unlocked"
' Parameter 4 : (Boolean) False
'--------------------------------------------------

long1812 = settingRepository1.GetAttr("NUMBERDENSITY_Nanometric")
'--------------------------------------------------
' Parameter 1 : (String) "NUMBERDENSITY_Nanometric"
' Returned value : (Variant) (Long) 1
'--------------------------------------------------

Dim bSTR3623
bSTR3623 = ""
Dim bSTR3624
bSTR3624 = ""
Dim boolean1812
settingRepository1.GetAttrInfo "NUMBERDENSITY_Nanometric", bSTR3623, bSTR3624, boolean1812
'--------------------------------------------------
' Parameter 1 : (String) "NUMBERDENSITY_Nanometric"
' Parameter 2 : (String) "Default value"
' Parameter 3 : (String) "Unlocked"
' Parameter 4 : (Boolean) False
'--------------------------------------------------

long1813 = settingRepository1.GetAttr("CHEMICALPOTENTIAL")
'--------------------------------------------------
' Parameter 1 : (String) "CHEMICALPOTENTIAL"
' Returned value : (Variant) (Long) 1
'--------------------------------------------------

Dim bSTR3625
bSTR3625 = ""
Dim bSTR3626
bSTR3626 = ""
Dim boolean1813
settingRepository1.GetAttrInfo "CHEMICALPOTENTIAL", bSTR3625, bSTR3626, boolean1813
'--------------------------------------------------
' Parameter 1 : (String) "CHEMICALPOTENTIAL"
' Parameter 2 : (String) "Default value"
' Parameter 3 : (String) "Unlocked"
' Parameter 4 : (Boolean) False
'--------------------------------------------------

long1814 = settingRepository1.GetAttr("CHEMICALPOTENTIAL_Large")
'--------------------------------------------------
' Parameter 1 : (String) "CHEMICALPOTENTIAL_Large"
' Returned value : (Variant) (Long) 1
'--------------------------------------------------

Dim bSTR3627
bSTR3627 = ""
Dim bSTR3628
bSTR3628 = ""
Dim boolean1814
settingRepository1.GetAttrInfo "CHEMICALPOTENTIAL_Large", bSTR3627, bSTR3628, boolean1814
'--------------------------------------------------
' Parameter 1 : (String) "CHEMICALPOTENTIAL_Large"
' Parameter 2 : (String) "Default value"
' Parameter 3 : (String) "Unlocked"
' Parameter 4 : (Boolean) False
'--------------------------------------------------

long1815 = settingRepository1.GetAttr("CHEMICALPOTENTIAL_ExtraLarge")
'--------------------------------------------------
' Parameter 1 : (String) "CHEMICALPOTENTIAL_ExtraLarge"
' Returned value : (Variant) (Long) 1
'--------------------------------------------------

Dim bSTR3629
bSTR3629 = ""
Dim bSTR3630
bSTR3630 = ""
Dim boolean1815
settingRepository1.GetAttrInfo "CHEMICALPOTENTIAL_ExtraLarge", bSTR3629, bSTR3630, boolean1815
'--------------------------------------------------
' Parameter 1 : (String) "CHEMICALPOTENTIAL_ExtraLarge"
' Parameter 2 : (String) "Default value"
' Parameter 3 : (String) "Unlocked"
' Parameter 4 : (Boolean) False
'--------------------------------------------------

long1816 = settingRepository1.GetAttr("CHEMICALPOTENTIAL_Small")
'--------------------------------------------------
' Parameter 1 : (String) "CHEMICALPOTENTIAL_Small"
' Returned value : (Variant) (Long) 1
'--------------------------------------------------

Dim bSTR3631
bSTR3631 = ""
Dim bSTR3632
bSTR3632 = ""
Dim boolean1816
settingRepository1.GetAttrInfo "CHEMICALPOTENTIAL_Small", bSTR3631, bSTR3632, boolean1816
'--------------------------------------------------
' Parameter 1 : (String) "CHEMICALPOTENTIAL_Small"
' Parameter 2 : (String) "Default value"
' Parameter 3 : (String) "Unlocked"
' Parameter 4 : (Boolean) False
'--------------------------------------------------

long1817 = settingRepository1.GetAttr("CHEMICALPOTENTIAL_ExtraSmall")
'--------------------------------------------------
' Parameter 1 : (String) "CHEMICALPOTENTIAL_ExtraSmall"
' Returned value : (Variant) (Long) 1
'--------------------------------------------------

Dim bSTR3633
bSTR3633 = ""
Dim bSTR3634
bSTR3634 = ""
Dim boolean1817
settingRepository1.GetAttrInfo "CHEMICALPOTENTIAL_ExtraSmall", bSTR3633, bSTR3634, boolean1817
'--------------------------------------------------
' Parameter 1 : (String) "CHEMICALPOTENTIAL_ExtraSmall"
' Parameter 2 : (String) "Default value"
' Parameter 3 : (String) "Unlocked"
' Parameter 4 : (Boolean) False
'--------------------------------------------------

long1818 = settingRepository1.GetAttr("CHEMICALPOTENTIAL_Nanometric")
'--------------------------------------------------
' Parameter 1 : (String) "CHEMICALPOTENTIAL_Nanometric"
' Returned value : (Variant) (Long) 1
'--------------------------------------------------

Dim bSTR3635
bSTR3635 = ""
Dim bSTR3636
bSTR3636 = ""
Dim boolean1818
settingRepository1.GetAttrInfo "CHEMICALPOTENTIAL_Nanometric", bSTR3635, bSTR3636, boolean1818
'--------------------------------------------------
' Parameter 1 : (String) "CHEMICALPOTENTIAL_Nanometric"
' Parameter 2 : (String) "Default value"
' Parameter 3 : (String) "Unlocked"
' Parameter 4 : (Boolean) False
'--------------------------------------------------

long1819 = settingRepository1.GetAttr("FUGACITY")
'--------------------------------------------------
' Parameter 1 : (String) "FUGACITY"
' Returned value : (Variant) (Long) 1
'--------------------------------------------------

Dim bSTR3637
bSTR3637 = ""
Dim bSTR3638
bSTR3638 = ""
Dim boolean1819
settingRepository1.GetAttrInfo "FUGACITY", bSTR3637, bSTR3638, boolean1819
'--------------------------------------------------
' Parameter 1 : (String) "FUGACITY"
' Parameter 2 : (String) "Default value"
' Parameter 3 : (String) "Unlocked"
' Parameter 4 : (Boolean) False
'--------------------------------------------------

long1820 = settingRepository1.GetAttr("FUGACITY_Large")
'--------------------------------------------------
' Parameter 1 : (String) "FUGACITY_Large"
' Returned value : (Variant) (Long) 1
'--------------------------------------------------

Dim bSTR3639
bSTR3639 = ""
Dim bSTR3640
bSTR3640 = ""
Dim boolean1820
settingRepository1.GetAttrInfo "FUGACITY_Large", bSTR3639, bSTR3640, boolean1820
'--------------------------------------------------
' Parameter 1 : (String) "FUGACITY_Large"
' Parameter 2 : (String) "Default value"
' Parameter 3 : (String) "Unlocked"
' Parameter 4 : (Boolean) False
'--------------------------------------------------

long1821 = settingRepository1.GetAttr("FUGACITY_ExtraLarge")
'--------------------------------------------------
' Parameter 1 : (String) "FUGACITY_ExtraLarge"
' Returned value : (Variant) (Long) 1
'--------------------------------------------------

Dim bSTR3641
bSTR3641 = ""
Dim bSTR3642
bSTR3642 = ""
Dim boolean1821
settingRepository1.GetAttrInfo "FUGACITY_ExtraLarge", bSTR3641, bSTR3642, boolean1821
'--------------------------------------------------
' Parameter 1 : (String) "FUGACITY_ExtraLarge"
' Parameter 2 : (String) "Default value"
' Parameter 3 : (String) "Unlocked"
' Parameter 4 : (Boolean) False
'--------------------------------------------------

long1822 = settingRepository1.GetAttr("FUGACITY_Small")
'--------------------------------------------------
' Parameter 1 : (String) "FUGACITY_Small"
' Returned value : (Variant) (Long) 1
'--------------------------------------------------

Dim bSTR3643
bSTR3643 = ""
Dim bSTR3644
bSTR3644 = ""
Dim boolean1822
settingRepository1.GetAttrInfo "FUGACITY_Small", bSTR3643, bSTR3644, boolean1822
'--------------------------------------------------
' Parameter 1 : (String) "FUGACITY_Small"
' Parameter 2 : (String) "Default value"
' Parameter 3 : (String) "Unlocked"
' Parameter 4 : (Boolean) False
'--------------------------------------------------

long1823 = settingRepository1.GetAttr("FUGACITY_ExtraSmall")
'--------------------------------------------------
' Parameter 1 : (String) "FUGACITY_ExtraSmall"
' Returned value : (Variant) (Long) 1
'--------------------------------------------------

Dim bSTR3645
bSTR3645 = ""
Dim bSTR3646
bSTR3646 = ""
Dim boolean1823
settingRepository1.GetAttrInfo "FUGACITY_ExtraSmall", bSTR3645, bSTR3646, boolean1823
'--------------------------------------------------
' Parameter 1 : (String) "FUGACITY_ExtraSmall"
' Parameter 2 : (String) "Default value"
' Parameter 3 : (String) "Unlocked"
' Parameter 4 : (Boolean) False
'--------------------------------------------------

long1824 = settingRepository1.GetAttr("FUGACITY_Nanometric")
'--------------------------------------------------
' Parameter 1 : (String) "FUGACITY_Nanometric"
' Returned value : (Variant) (Long) 1
'--------------------------------------------------

Dim bSTR3647
bSTR3647 = ""
Dim bSTR3648
bSTR3648 = ""
Dim boolean1824
settingRepository1.GetAttrInfo "FUGACITY_Nanometric", bSTR3647, bSTR3648, boolean1824
'--------------------------------------------------
' Parameter 1 : (String) "FUGACITY_Nanometric"
' Parameter 2 : (String) "Default value"
' Parameter 3 : (String) "Unlocked"
' Parameter 4 : (Boolean) False
'--------------------------------------------------

long1825 = settingRepository1.GetAttr("OSMOTICPRESSURE")
'--------------------------------------------------
' Parameter 1 : (String) "OSMOTICPRESSURE"
' Returned value : (Variant) (Long) 1
'--------------------------------------------------

Dim bSTR3649
bSTR3649 = ""
Dim bSTR3650
bSTR3650 = ""
Dim boolean1825
settingRepository1.GetAttrInfo "OSMOTICPRESSURE", bSTR3649, bSTR3650, boolean1825
'--------------------------------------------------
' Parameter 1 : (String) "OSMOTICPRESSURE"
' Parameter 2 : (String) "Default value"
' Parameter 3 : (String) "Unlocked"
' Parameter 4 : (Boolean) False
'--------------------------------------------------

long1826 = settingRepository1.GetAttr("OSMOTICPRESSURE_Large")
'--------------------------------------------------
' Parameter 1 : (String) "OSMOTICPRESSURE_Large"
' Returned value : (Variant) (Long) 1
'--------------------------------------------------

Dim bSTR3651
bSTR3651 = ""
Dim bSTR3652
bSTR3652 = ""
Dim boolean1826
settingRepository1.GetAttrInfo "OSMOTICPRESSURE_Large", bSTR3651, bSTR3652, boolean1826
'--------------------------------------------------
' Parameter 1 : (String) "OSMOTICPRESSURE_Large"
' Parameter 2 : (String) "Default value"
' Parameter 3 : (String) "Unlocked"
' Parameter 4 : (Boolean) False
'--------------------------------------------------

long1827 = settingRepository1.GetAttr("OSMOTICPRESSURE_ExtraLarge")
'--------------------------------------------------
' Parameter 1 : (String) "OSMOTICPRESSURE_ExtraLarge"
' Returned value : (Variant) (Long) 1
'--------------------------------------------------

Dim bSTR3653
bSTR3653 = ""
Dim bSTR3654
bSTR3654 = ""
Dim boolean1827
settingRepository1.GetAttrInfo "OSMOTICPRESSURE_ExtraLarge", bSTR3653, bSTR3654, boolean1827
'--------------------------------------------------
' Parameter 1 : (String) "OSMOTICPRESSURE_ExtraLarge"
' Parameter 2 : (String) "Default value"
' Parameter 3 : (String) "Unlocked"
' Parameter 4 : (Boolean) False
'--------------------------------------------------

long1828 = settingRepository1.GetAttr("OSMOTICPRESSURE_Small")
'--------------------------------------------------
' Parameter 1 : (String) "OSMOTICPRESSURE_Small"
' Returned value : (Variant) (Long) 1
'--------------------------------------------------

Dim bSTR3655
bSTR3655 = ""
Dim bSTR3656
bSTR3656 = ""
Dim boolean1828
settingRepository1.GetAttrInfo "OSMOTICPRESSURE_Small", bSTR3655, bSTR3656, boolean1828
'--------------------------------------------------
' Parameter 1 : (String) "OSMOTICPRESSURE_Small"
' Parameter 2 : (String) "Default value"
' Parameter 3 : (String) "Unlocked"
' Parameter 4 : (Boolean) False
'--------------------------------------------------

long1829 = settingRepository1.GetAttr("OSMOTICPRESSURE_ExtraSmall")
'--------------------------------------------------
' Parameter 1 : (String) "OSMOTICPRESSURE_ExtraSmall"
' Returned value : (Variant) (Long) 1
'--------------------------------------------------

Dim bSTR3657
bSTR3657 = ""
Dim bSTR3658
bSTR3658 = ""
Dim boolean1829
settingRepository1.GetAttrInfo "OSMOTICPRESSURE_ExtraSmall", bSTR3657, bSTR3658, boolean1829
'--------------------------------------------------
' Parameter 1 : (String) "OSMOTICPRESSURE_ExtraSmall"
' Parameter 2 : (String) "Default value"
' Parameter 3 : (String) "Unlocked"
' Parameter 4 : (Boolean) False
'--------------------------------------------------

long1830 = settingRepository1.GetAttr("OSMOTICPRESSURE_Nanometric")
'--------------------------------------------------
' Parameter 1 : (String) "OSMOTICPRESSURE_Nanometric"
' Returned value : (Variant) (Long) 1
'--------------------------------------------------

Dim bSTR3659
bSTR3659 = ""
Dim bSTR3660
bSTR3660 = ""
Dim boolean1830
settingRepository1.GetAttrInfo "OSMOTICPRESSURE_Nanometric", bSTR3659, bSTR3660, boolean1830
'--------------------------------------------------
' Parameter 1 : (String) "OSMOTICPRESSURE_Nanometric"
' Parameter 2 : (String) "Default value"
' Parameter 3 : (String) "Unlocked"
' Parameter 4 : (Boolean) False
'--------------------------------------------------

long1831 = settingRepository1.GetAttr("AFFINITY")
'--------------------------------------------------
' Parameter 1 : (String) "AFFINITY"
' Returned value : (Variant) (Long) 1
'--------------------------------------------------

Dim bSTR3661
bSTR3661 = ""
Dim bSTR3662
bSTR3662 = ""
Dim boolean1831
settingRepository1.GetAttrInfo "AFFINITY", bSTR3661, bSTR3662, boolean1831
'--------------------------------------------------
' Parameter 1 : (String) "AFFINITY"
' Parameter 2 : (String) "Default value"
' Parameter 3 : (String) "Unlocked"
' Parameter 4 : (Boolean) False
'--------------------------------------------------

long1832 = settingRepository1.GetAttr("AFFINITY_Large")
'--------------------------------------------------
' Parameter 1 : (String) "AFFINITY_Large"
' Returned value : (Variant) (Long) 1
'--------------------------------------------------

Dim bSTR3663
bSTR3663 = ""
Dim bSTR3664
bSTR3664 = ""
Dim boolean1832
settingRepository1.GetAttrInfo "AFFINITY_Large", bSTR3663, bSTR3664, boolean1832
'--------------------------------------------------
' Parameter 1 : (String) "AFFINITY_Large"
' Parameter 2 : (String) "Default value"
' Parameter 3 : (String) "Unlocked"
' Parameter 4 : (Boolean) False
'--------------------------------------------------

long1833 = settingRepository1.GetAttr("AFFINITY_ExtraLarge")
'--------------------------------------------------
' Parameter 1 : (String) "AFFINITY_ExtraLarge"
' Returned value : (Variant) (Long) 1
'--------------------------------------------------

Dim bSTR3665
bSTR3665 = ""
Dim bSTR3666
bSTR3666 = ""
Dim boolean1833
settingRepository1.GetAttrInfo "AFFINITY_ExtraLarge", bSTR3665, bSTR3666, boolean1833
'--------------------------------------------------
' Parameter 1 : (String) "AFFINITY_ExtraLarge"
' Parameter 2 : (String) "Default value"
' Parameter 3 : (String) "Unlocked"
' Parameter 4 : (Boolean) False
'--------------------------------------------------

long1834 = settingRepository1.GetAttr("AFFINITY_Small")
'--------------------------------------------------
' Parameter 1 : (String) "AFFINITY_Small"
' Returned value : (Variant) (Long) 1
'--------------------------------------------------

Dim bSTR3667
bSTR3667 = ""
Dim bSTR3668
bSTR3668 = ""
Dim boolean1834
settingRepository1.GetAttrInfo "AFFINITY_Small", bSTR3667, bSTR3668, boolean1834
'--------------------------------------------------
' Parameter 1 : (String) "AFFINITY_Small"
' Parameter 2 : (String) "Default value"
' Parameter 3 : (String) "Unlocked"
' Parameter 4 : (Boolean) False
'--------------------------------------------------

long1835 = settingRepository1.GetAttr("AFFINITY_ExtraSmall")
'--------------------------------------------------
' Parameter 1 : (String) "AFFINITY_ExtraSmall"
' Returned value : (Variant) (Long) 1
'--------------------------------------------------

Dim bSTR3669
bSTR3669 = ""
Dim bSTR3670
bSTR3670 = ""
Dim boolean1835
settingRepository1.GetAttrInfo "AFFINITY_ExtraSmall", bSTR3669, bSTR3670, boolean1835
'--------------------------------------------------
' Parameter 1 : (String) "AFFINITY_ExtraSmall"
' Parameter 2 : (String) "Default value"
' Parameter 3 : (String) "Unlocked"
' Parameter 4 : (Boolean) False
'--------------------------------------------------

long1836 = settingRepository1.GetAttr("AFFINITY_Nanometric")
'--------------------------------------------------
' Parameter 1 : (String) "AFFINITY_Nanometric"
' Returned value : (Variant) (Long) 1
'--------------------------------------------------

Dim bSTR3671
bSTR3671 = ""
Dim bSTR3672
bSTR3672 = ""
Dim boolean1836
settingRepository1.GetAttrInfo "AFFINITY_Nanometric", bSTR3671, bSTR3672, boolean1836
'--------------------------------------------------
' Parameter 1 : (String) "AFFINITY_Nanometric"
' Parameter 2 : (String) "Default value"
' Parameter 3 : (String) "Unlocked"
' Parameter 4 : (Boolean) False
'--------------------------------------------------

long1837 = settingRepository1.GetAttr("ELECTRICPOLARIZABILITYOFAMOLECULE")
'--------------------------------------------------
' Parameter 1 : (String) "ELECTRICPOLARIZABILITYOFAMOLECULE"
' Returned value : (Variant) (Long) 1
'--------------------------------------------------

Dim bSTR3673
bSTR3673 = ""
Dim bSTR3674
bSTR3674 = ""
Dim boolean1837
settingRepository1.GetAttrInfo "ELECTRICPOLARIZABILITYOFAMOLECULE", bSTR3673, bSTR3674, boolean1837
'--------------------------------------------------
' Parameter 1 : (String) "ELECTRICPOLARIZABILITYOFAMOLECULE"
' Parameter 2 : (String) "Default value"
' Parameter 3 : (String) "Unlocked"
' Parameter 4 : (Boolean) False
'--------------------------------------------------

long1838 = settingRepository1.GetAttr("ELECTRICPOLARIZABILITYOFAMOLECULE_Large")
'--------------------------------------------------
' Parameter 1 : (String) "ELECTRICPOLARIZABILITYOFAMOLECULE_Large"
' Returned value : (Variant) (Long) 1
'--------------------------------------------------

Dim bSTR3675
bSTR3675 = ""
Dim bSTR3676
bSTR3676 = ""
Dim boolean1838
settingRepository1.GetAttrInfo "ELECTRICPOLARIZABILITYOFAMOLECULE_Large", bSTR3675, bSTR3676, boolean1838
'--------------------------------------------------
' Parameter 1 : (String) "ELECTRICPOLARIZABILITYOFAMOLECULE_Large"
' Parameter 2 : (String) "Default value"
' Parameter 3 : (String) "Unlocked"
' Parameter 4 : (Boolean) False
'--------------------------------------------------

long1839 = settingRepository1.GetAttr("ELECTRICPOLARIZABILITYOFAMOLECULE_ExtraLarge")
'--------------------------------------------------
' Parameter 1 : (String) "ELECTRICPOLARIZABILITYOFAMOLECULE_ExtraLarge"
' Returned value : (Variant) (Long) 1
'--------------------------------------------------

Dim bSTR3677
bSTR3677 = ""
Dim bSTR3678
bSTR3678 = ""
Dim boolean1839
settingRepository1.GetAttrInfo "ELECTRICPOLARIZABILITYOFAMOLECULE_ExtraLarge", bSTR3677, bSTR3678, boolean1839
'--------------------------------------------------
' Parameter 1 : (String) "ELECTRICPOLARIZABILITYOFAMOLECULE_ExtraLarge"
' Parameter 2 : (String) "Default value"
' Parameter 3 : (String) "Unlocked"
' Parameter 4 : (Boolean) False
'--------------------------------------------------

long1840 = settingRepository1.GetAttr("ELECTRICPOLARIZABILITYOFAMOLECULE_Small")
'--------------------------------------------------
' Parameter 1 : (String) "ELECTRICPOLARIZABILITYOFAMOLECULE_Small"
' Returned value : (Variant) (Long) 1
'--------------------------------------------------

Dim bSTR3679
bSTR3679 = ""
Dim bSTR3680
bSTR3680 = ""
Dim boolean1840
settingRepository1.GetAttrInfo "ELECTRICPOLARIZABILITYOFAMOLECULE_Small", bSTR3679, bSTR3680, boolean1840
'--------------------------------------------------
' Parameter 1 : (String) "ELECTRICPOLARIZABILITYOFAMOLECULE_Small"
' Parameter 2 : (String) "Default value"
' Parameter 3 : (String) "Unlocked"
' Parameter 4 : (Boolean) False
'--------------------------------------------------

long1841 = settingRepository1.GetAttr("ELECTRICPOLARIZABILITYOFAMOLECULE_ExtraSmall")
'--------------------------------------------------
' Parameter 1 : (String) "ELECTRICPOLARIZABILITYOFAMOLECULE_ExtraSmall"
' Returned value : (Variant) (Long) 1
'--------------------------------------------------

Dim bSTR3681
bSTR3681 = ""
Dim bSTR3682
bSTR3682 = ""
Dim boolean1841
settingRepository1.GetAttrInfo "ELECTRICPOLARIZABILITYOFAMOLECULE_ExtraSmall", bSTR3681, bSTR3682, boolean1841
'--------------------------------------------------
' Parameter 1 : (String) "ELECTRICPOLARIZABILITYOFAMOLECULE_ExtraSmall"
' Parameter 2 : (String) "Default value"
' Parameter 3 : (String) "Unlocked"
' Parameter 4 : (Boolean) False
'--------------------------------------------------

long1842 = settingRepository1.GetAttr("ELECTRICPOLARIZABILITYOFAMOLECULE_Nanometric")
'--------------------------------------------------
' Parameter 1 : (String) "ELECTRICPOLARIZABILITYOFAMOLECULE_Nanometric"
' Returned value : (Variant) (Long) 1
'--------------------------------------------------

Dim bSTR3683
bSTR3683 = ""
Dim bSTR3684
bSTR3684 = ""
Dim boolean1842
settingRepository1.GetAttrInfo "ELECTRICPOLARIZABILITYOFAMOLECULE_Nanometric", bSTR3683, bSTR3684, boolean1842
'--------------------------------------------------
' Parameter 1 : (String) "ELECTRICPOLARIZABILITYOFAMOLECULE_Nanometric"
' Parameter 2 : (String) "Default value"
' Parameter 3 : (String) "Unlocked"
' Parameter 4 : (Boolean) False
'--------------------------------------------------

long1843 = settingRepository1.GetAttr("FARADAYCONSTANT")
'--------------------------------------------------
' Parameter 1 : (String) "FARADAYCONSTANT"
' Returned value : (Variant) (Long) 1
'--------------------------------------------------

Dim bSTR3685
bSTR3685 = ""
Dim bSTR3686
bSTR3686 = ""
Dim boolean1843
settingRepository1.GetAttrInfo "FARADAYCONSTANT", bSTR3685, bSTR3686, boolean1843
'--------------------------------------------------
' Parameter 1 : (String) "FARADAYCONSTANT"
' Parameter 2 : (String) "Default value"
' Parameter 3 : (String) "Unlocked"
' Parameter 4 : (Boolean) False
'--------------------------------------------------

long1844 = settingRepository1.GetAttr("FARADAYCONSTANT_Large")
'--------------------------------------------------
' Parameter 1 : (String) "FARADAYCONSTANT_Large"
' Returned value : (Variant) (Long) 1
'--------------------------------------------------

Dim bSTR3687
bSTR3687 = ""
Dim bSTR3688
bSTR3688 = ""
Dim boolean1844
settingRepository1.GetAttrInfo "FARADAYCONSTANT_Large", bSTR3687, bSTR3688, boolean1844
'--------------------------------------------------
' Parameter 1 : (String) "FARADAYCONSTANT_Large"
' Parameter 2 : (String) "Default value"
' Parameter 3 : (String) "Unlocked"
' Parameter 4 : (Boolean) False
'--------------------------------------------------

long1845 = settingRepository1.GetAttr("FARADAYCONSTANT_ExtraLarge")
'--------------------------------------------------
' Parameter 1 : (String) "FARADAYCONSTANT_ExtraLarge"
' Returned value : (Variant) (Long) 1
'--------------------------------------------------

Dim bSTR3689
bSTR3689 = ""
Dim bSTR3690
bSTR3690 = ""
Dim boolean1845
settingRepository1.GetAttrInfo "FARADAYCONSTANT_ExtraLarge", bSTR3689, bSTR3690, boolean1845
'--------------------------------------------------
' Parameter 1 : (String) "FARADAYCONSTANT_ExtraLarge"
' Parameter 2 : (String) "Default value"
' Parameter 3 : (String) "Unlocked"
' Parameter 4 : (Boolean) False
'--------------------------------------------------

long1846 = settingRepository1.GetAttr("FARADAYCONSTANT_Small")
'--------------------------------------------------
' Parameter 1 : (String) "FARADAYCONSTANT_Small"
' Returned value : (Variant) (Long) 1
'--------------------------------------------------

Dim bSTR3691
bSTR3691 = ""
Dim bSTR3692
bSTR3692 = ""
Dim boolean1846
settingRepository1.GetAttrInfo "FARADAYCONSTANT_Small", bSTR3691, bSTR3692, boolean1846
'--------------------------------------------------
' Parameter 1 : (String) "FARADAYCONSTANT_Small"
' Parameter 2 : (String) "Default value"
' Parameter 3 : (String) "Unlocked"
' Parameter 4 : (Boolean) False
'--------------------------------------------------

long1847 = settingRepository1.GetAttr("FARADAYCONSTANT_ExtraSmall")
'--------------------------------------------------
' Parameter 1 : (String) "FARADAYCONSTANT_ExtraSmall"
' Returned value : (Variant) (Long) 1
'--------------------------------------------------

Dim bSTR3693
bSTR3693 = ""
Dim bSTR3694
bSTR3694 = ""
Dim boolean1847
settingRepository1.GetAttrInfo "FARADAYCONSTANT_ExtraSmall", bSTR3693, bSTR3694, boolean1847
'--------------------------------------------------
' Parameter 1 : (String) "FARADAYCONSTANT_ExtraSmall"
' Parameter 2 : (String) "Default value"
' Parameter 3 : (String) "Unlocked"
' Parameter 4 : (Boolean) False
'--------------------------------------------------

long1848 = settingRepository1.GetAttr("FARADAYCONSTANT_Nanometric")
'--------------------------------------------------
' Parameter 1 : (String) "FARADAYCONSTANT_Nanometric"
' Returned value : (Variant) (Long) 1
'--------------------------------------------------

Dim bSTR3695
bSTR3695 = ""
Dim bSTR3696
bSTR3696 = ""
Dim boolean1848
settingRepository1.GetAttrInfo "FARADAYCONSTANT_Nanometric", bSTR3695, bSTR3696, boolean1848
'--------------------------------------------------
' Parameter 1 : (String) "FARADAYCONSTANT_Nanometric"
' Parameter 2 : (String) "Default value"
' Parameter 3 : (String) "Unlocked"
' Parameter 4 : (Boolean) False
'--------------------------------------------------

long1849 = settingRepository1.GetAttr("IONICSTRENGTH")
'--------------------------------------------------
' Parameter 1 : (String) "IONICSTRENGTH"
' Returned value : (Variant) (Long) 1
'--------------------------------------------------

Dim bSTR3697
bSTR3697 = ""
Dim bSTR3698
bSTR3698 = ""
Dim boolean1849
settingRepository1.GetAttrInfo "IONICSTRENGTH", bSTR3697, bSTR3698, boolean1849
'--------------------------------------------------
' Parameter 1 : (String) "IONICSTRENGTH"
' Parameter 2 : (String) "Default value"
' Parameter 3 : (String) "Unlocked"
' Parameter 4 : (Boolean) False
'--------------------------------------------------

long1850 = settingRepository1.GetAttr("IONICSTRENGTH_Large")
'--------------------------------------------------
' Parameter 1 : (String) "IONICSTRENGTH_Large"
' Returned value : (Variant) (Long) 1
'--------------------------------------------------

Dim bSTR3699
bSTR3699 = ""
Dim bSTR3700
bSTR3700 = ""
Dim boolean1850
settingRepository1.GetAttrInfo "IONICSTRENGTH_Large", bSTR3699, bSTR3700, boolean1850
'--------------------------------------------------
' Parameter 1 : (String) "IONICSTRENGTH_Large"
' Parameter 2 : (String) "Default value"
' Parameter 3 : (String) "Unlocked"
' Parameter 4 : (Boolean) False
'--------------------------------------------------

long1851 = settingRepository1.GetAttr("IONICSTRENGTH_ExtraLarge")
'--------------------------------------------------
' Parameter 1 : (String) "IONICSTRENGTH_ExtraLarge"
' Returned value : (Variant) (Long) 1
'--------------------------------------------------

Dim bSTR3701
bSTR3701 = ""
Dim bSTR3702
bSTR3702 = ""
Dim boolean1851
settingRepository1.GetAttrInfo "IONICSTRENGTH_ExtraLarge", bSTR3701, bSTR3702, boolean1851
'--------------------------------------------------
' Parameter 1 : (String) "IONICSTRENGTH_ExtraLarge"
' Parameter 2 : (String) "Default value"
' Parameter 3 : (String) "Unlocked"
' Parameter 4 : (Boolean) False
'--------------------------------------------------

long1852 = settingRepository1.GetAttr("IONICSTRENGTH_Small")
'--------------------------------------------------
' Parameter 1 : (String) "IONICSTRENGTH_Small"
' Returned value : (Variant) (Long) 1
'--------------------------------------------------

Dim bSTR3703
bSTR3703 = ""
Dim bSTR3704
bSTR3704 = ""
Dim boolean1852
settingRepository1.GetAttrInfo "IONICSTRENGTH_Small", bSTR3703, bSTR3704, boolean1852
'--------------------------------------------------
' Parameter 1 : (String) "IONICSTRENGTH_Small"
' Parameter 2 : (String) "Default value"
' Parameter 3 : (String) "Unlocked"
' Parameter 4 : (Boolean) False
'--------------------------------------------------

long1853 = settingRepository1.GetAttr("IONICSTRENGTH_ExtraSmall")
'--------------------------------------------------
' Parameter 1 : (String) "IONICSTRENGTH_ExtraSmall"
' Returned value : (Variant) (Long) 1
'--------------------------------------------------

Dim bSTR3705
bSTR3705 = ""
Dim bSTR3706
bSTR3706 = ""
Dim boolean1853
settingRepository1.GetAttrInfo "IONICSTRENGTH_ExtraSmall", bSTR3705, bSTR3706, boolean1853
'--------------------------------------------------
' Parameter 1 : (String) "IONICSTRENGTH_ExtraSmall"
' Parameter 2 : (String) "Default value"
' Parameter 3 : (String) "Unlocked"
' Parameter 4 : (Boolean) False
'--------------------------------------------------

long1854 = settingRepository1.GetAttr("IONICSTRENGTH_Nanometric")
'--------------------------------------------------
' Parameter 1 : (String) "IONICSTRENGTH_Nanometric"
' Returned value : (Variant) (Long) 1
'--------------------------------------------------

Dim bSTR3707
bSTR3707 = ""
Dim bSTR3708
bSTR3708 = ""
Dim boolean1854
settingRepository1.GetAttrInfo "IONICSTRENGTH_Nanometric", bSTR3707, bSTR3708, boolean1854
'--------------------------------------------------
' Parameter 1 : (String) "IONICSTRENGTH_Nanometric"
' Parameter 2 : (String) "Default value"
' Parameter 3 : (String) "Unlocked"
' Parameter 4 : (Boolean) False
'--------------------------------------------------

long1855 = settingRepository1.GetAttr("MOLARCONDUCTIVITY")
'--------------------------------------------------
' Parameter 1 : (String) "MOLARCONDUCTIVITY"
' Returned value : (Variant) (Long) 1
'--------------------------------------------------

Dim bSTR3709
bSTR3709 = ""
Dim bSTR3710
bSTR3710 = ""
Dim boolean1855
settingRepository1.GetAttrInfo "MOLARCONDUCTIVITY", bSTR3709, bSTR3710, boolean1855
'--------------------------------------------------
' Parameter 1 : (String) "MOLARCONDUCTIVITY"
' Parameter 2 : (String) "Default value"
' Parameter 3 : (String) "Unlocked"
' Parameter 4 : (Boolean) False
'--------------------------------------------------

long1856 = settingRepository1.GetAttr("MOLARCONDUCTIVITY_Large")
'--------------------------------------------------
' Parameter 1 : (String) "MOLARCONDUCTIVITY_Large"
' Returned value : (Variant) (Long) 1
'--------------------------------------------------

Dim bSTR3711
bSTR3711 = ""
Dim bSTR3712
bSTR3712 = ""
Dim boolean1856
settingRepository1.GetAttrInfo "MOLARCONDUCTIVITY_Large", bSTR3711, bSTR3712, boolean1856
'--------------------------------------------------
' Parameter 1 : (String) "MOLARCONDUCTIVITY_Large"
' Parameter 2 : (String) "Default value"
' Parameter 3 : (String) "Unlocked"
' Parameter 4 : (Boolean) False
'--------------------------------------------------

long1857 = settingRepository1.GetAttr("MOLARCONDUCTIVITY_ExtraLarge")
'--------------------------------------------------
' Parameter 1 : (String) "MOLARCONDUCTIVITY_ExtraLarge"
' Returned value : (Variant) (Long) 1
'--------------------------------------------------

Dim bSTR3713
bSTR3713 = ""
Dim bSTR3714
bSTR3714 = ""
Dim boolean1857
settingRepository1.GetAttrInfo "MOLARCONDUCTIVITY_ExtraLarge", bSTR3713, bSTR3714, boolean1857
'--------------------------------------------------
' Parameter 1 : (String) "MOLARCONDUCTIVITY_ExtraLarge"
' Parameter 2 : (String) "Default value"
' Parameter 3 : (String) "Unlocked"
' Parameter 4 : (Boolean) False
'--------------------------------------------------

long1858 = settingRepository1.GetAttr("MOLARCONDUCTIVITY_Small")
'--------------------------------------------------
' Parameter 1 : (String) "MOLARCONDUCTIVITY_Small"
' Returned value : (Variant) (Long) 1
'--------------------------------------------------

Dim bSTR3715
bSTR3715 = ""
Dim bSTR3716
bSTR3716 = ""
Dim boolean1858
settingRepository1.GetAttrInfo "MOLARCONDUCTIVITY_Small", bSTR3715, bSTR3716, boolean1858
'--------------------------------------------------
' Parameter 1 : (String) "MOLARCONDUCTIVITY_Small"
' Parameter 2 : (String) "Default value"
' Parameter 3 : (String) "Unlocked"
' Parameter 4 : (Boolean) False
'--------------------------------------------------

long1859 = settingRepository1.GetAttr("MOLARCONDUCTIVITY_ExtraSmall")
'--------------------------------------------------
' Parameter 1 : (String) "MOLARCONDUCTIVITY_ExtraSmall"
' Returned value : (Variant) (Long) 1
'--------------------------------------------------

Dim bSTR3717
bSTR3717 = ""
Dim bSTR3718
bSTR3718 = ""
Dim boolean1859
settingRepository1.GetAttrInfo "MOLARCONDUCTIVITY_ExtraSmall", bSTR3717, bSTR3718, boolean1859
'--------------------------------------------------
' Parameter 1 : (String) "MOLARCONDUCTIVITY_ExtraSmall"
' Parameter 2 : (String) "Default value"
' Parameter 3 : (String) "Unlocked"
' Parameter 4 : (Boolean) False
'--------------------------------------------------

long1860 = settingRepository1.GetAttr("MOLARCONDUCTIVITY_Nanometric")
'--------------------------------------------------
' Parameter 1 : (String) "MOLARCONDUCTIVITY_Nanometric"
' Returned value : (Variant) (Long) 1
'--------------------------------------------------

Dim bSTR3719
bSTR3719 = ""
Dim bSTR3720
bSTR3720 = ""
Dim boolean1860
settingRepository1.GetAttrInfo "MOLARCONDUCTIVITY_Nanometric", bSTR3719, bSTR3720, boolean1860
'--------------------------------------------------
' Parameter 1 : (String) "MOLARCONDUCTIVITY_Nanometric"
' Parameter 2 : (String) "Default value"
' Parameter 3 : (String) "Unlocked"
' Parameter 4 : (Boolean) False
'--------------------------------------------------

long1861 = settingRepository1.GetAttr("BOHRMAGNETON")
'--------------------------------------------------
' Parameter 1 : (String) "BOHRMAGNETON"
' Returned value : (Variant) (Long) 1
'--------------------------------------------------

Dim bSTR3721
bSTR3721 = ""
Dim bSTR3722
bSTR3722 = ""
Dim boolean1861
settingRepository1.GetAttrInfo "BOHRMAGNETON", bSTR3721, bSTR3722, boolean1861
'--------------------------------------------------
' Parameter 1 : (String) "BOHRMAGNETON"
' Parameter 2 : (String) "Default value"
' Parameter 3 : (String) "Unlocked"
' Parameter 4 : (Boolean) False
'--------------------------------------------------

long1862 = settingRepository1.GetAttr("BOHRMAGNETON_Large")
'--------------------------------------------------
' Parameter 1 : (String) "BOHRMAGNETON_Large"
' Returned value : (Variant) (Long) 1
'--------------------------------------------------

Dim bSTR3723
bSTR3723 = ""
Dim bSTR3724
bSTR3724 = ""
Dim boolean1862
settingRepository1.GetAttrInfo "BOHRMAGNETON_Large", bSTR3723, bSTR3724, boolean1862
'--------------------------------------------------
' Parameter 1 : (String) "BOHRMAGNETON_Large"
' Parameter 2 : (String) "Default value"
' Parameter 3 : (String) "Unlocked"
' Parameter 4 : (Boolean) False
'--------------------------------------------------

long1863 = settingRepository1.GetAttr("BOHRMAGNETON_ExtraLarge")
'--------------------------------------------------
' Parameter 1 : (String) "BOHRMAGNETON_ExtraLarge"
' Returned value : (Variant) (Long) 1
'--------------------------------------------------

Dim bSTR3725
bSTR3725 = ""
Dim bSTR3726
bSTR3726 = ""
Dim boolean1863
settingRepository1.GetAttrInfo "BOHRMAGNETON_ExtraLarge", bSTR3725, bSTR3726, boolean1863
'--------------------------------------------------
' Parameter 1 : (String) "BOHRMAGNETON_ExtraLarge"
' Parameter 2 : (String) "Default value"
' Parameter 3 : (String) "Unlocked"
' Parameter 4 : (Boolean) False
'--------------------------------------------------

long1864 = settingRepository1.GetAttr("BOHRMAGNETON_Small")
'--------------------------------------------------
' Parameter 1 : (String) "BOHRMAGNETON_Small"
' Returned value : (Variant) (Long) 1
'--------------------------------------------------

Dim bSTR3727
bSTR3727 = ""
Dim bSTR3728
bSTR3728 = ""
Dim boolean1864
settingRepository1.GetAttrInfo "BOHRMAGNETON_Small", bSTR3727, bSTR3728, boolean1864
'--------------------------------------------------
' Parameter 1 : (String) "BOHRMAGNETON_Small"
' Parameter 2 : (String) "Default value"
' Parameter 3 : (String) "Unlocked"
' Parameter 4 : (Boolean) False
'--------------------------------------------------

long1865 = settingRepository1.GetAttr("BOHRMAGNETON_ExtraSmall")
'--------------------------------------------------
' Parameter 1 : (String) "BOHRMAGNETON_ExtraSmall"
' Returned value : (Variant) (Long) 1
'--------------------------------------------------

Dim bSTR3729
bSTR3729 = ""
Dim bSTR3730
bSTR3730 = ""
Dim boolean1865
settingRepository1.GetAttrInfo "BOHRMAGNETON_ExtraSmall", bSTR3729, bSTR3730, boolean1865
'--------------------------------------------------
' Parameter 1 : (String) "BOHRMAGNETON_ExtraSmall"
' Parameter 2 : (String) "Default value"
' Parameter 3 : (String) "Unlocked"
' Parameter 4 : (Boolean) False
'--------------------------------------------------

long1866 = settingRepository1.GetAttr("BOHRMAGNETON_Nanometric")
'--------------------------------------------------
' Parameter 1 : (String) "BOHRMAGNETON_Nanometric"
' Returned value : (Variant) (Long) 1
'--------------------------------------------------

Dim bSTR3731
bSTR3731 = ""
Dim bSTR3732
bSTR3732 = ""
Dim boolean1866
settingRepository1.GetAttrInfo "BOHRMAGNETON_Nanometric", bSTR3731, bSTR3732, boolean1866
'--------------------------------------------------
' Parameter 1 : (String) "BOHRMAGNETON_Nanometric"
' Parameter 2 : (String) "Default value"
' Parameter 3 : (String) "Unlocked"
' Parameter 4 : (Boolean) False
'--------------------------------------------------

long1867 = settingRepository1.GetAttr("NUCLEARMAGNETON")
'--------------------------------------------------
' Parameter 1 : (String) "NUCLEARMAGNETON"
' Returned value : (Variant) (Long) 1
'--------------------------------------------------

Dim bSTR3733
bSTR3733 = ""
Dim bSTR3734
bSTR3734 = ""
Dim boolean1867
settingRepository1.GetAttrInfo "NUCLEARMAGNETON", bSTR3733, bSTR3734, boolean1867
'--------------------------------------------------
' Parameter 1 : (String) "NUCLEARMAGNETON"
' Parameter 2 : (String) "Default value"
' Parameter 3 : (String) "Unlocked"
' Parameter 4 : (Boolean) False
'--------------------------------------------------

long1868 = settingRepository1.GetAttr("NUCLEARMAGNETON_Large")
'--------------------------------------------------
' Parameter 1 : (String) "NUCLEARMAGNETON_Large"
' Returned value : (Variant) (Long) 1
'--------------------------------------------------

Dim bSTR3735
bSTR3735 = ""
Dim bSTR3736
bSTR3736 = ""
Dim boolean1868
settingRepository1.GetAttrInfo "NUCLEARMAGNETON_Large", bSTR3735, bSTR3736, boolean1868
'--------------------------------------------------
' Parameter 1 : (String) "NUCLEARMAGNETON_Large"
' Parameter 2 : (String) "Default value"
' Parameter 3 : (String) "Unlocked"
' Parameter 4 : (Boolean) False
'--------------------------------------------------

long1869 = settingRepository1.GetAttr("NUCLEARMAGNETON_ExtraLarge")
'--------------------------------------------------
' Parameter 1 : (String) "NUCLEARMAGNETON_ExtraLarge"
' Returned value : (Variant) (Long) 1
'--------------------------------------------------

Dim bSTR3737
bSTR3737 = ""
Dim bSTR3738
bSTR3738 = ""
Dim boolean1869
settingRepository1.GetAttrInfo "NUCLEARMAGNETON_ExtraLarge", bSTR3737, bSTR3738, boolean1869
'--------------------------------------------------
' Parameter 1 : (String) "NUCLEARMAGNETON_ExtraLarge"
' Parameter 2 : (String) "Default value"
' Parameter 3 : (String) "Unlocked"
' Parameter 4 : (Boolean) False
'--------------------------------------------------

long1870 = settingRepository1.GetAttr("NUCLEARMAGNETON_Small")
'--------------------------------------------------
' Parameter 1 : (String) "NUCLEARMAGNETON_Small"
' Returned value : (Variant) (Long) 1
'--------------------------------------------------

Dim bSTR3739
bSTR3739 = ""
Dim bSTR3740
bSTR3740 = ""
Dim boolean1870
settingRepository1.GetAttrInfo "NUCLEARMAGNETON_Small", bSTR3739, bSTR3740, boolean1870
'--------------------------------------------------
' Parameter 1 : (String) "NUCLEARMAGNETON_Small"
' Parameter 2 : (String) "Default value"
' Parameter 3 : (String) "Unlocked"
' Parameter 4 : (Boolean) False
'--------------------------------------------------

long1871 = settingRepository1.GetAttr("NUCLEARMAGNETON_ExtraSmall")
'--------------------------------------------------
' Parameter 1 : (String) "NUCLEARMAGNETON_ExtraSmall"
' Returned value : (Variant) (Long) 1
'--------------------------------------------------

Dim bSTR3741
bSTR3741 = ""
Dim bSTR3742
bSTR3742 = ""
Dim boolean1871
settingRepository1.GetAttrInfo "NUCLEARMAGNETON_ExtraSmall", bSTR3741, bSTR3742, boolean1871
'--------------------------------------------------
' Parameter 1 : (String) "NUCLEARMAGNETON_ExtraSmall"
' Parameter 2 : (String) "Default value"
' Parameter 3 : (String) "Unlocked"
' Parameter 4 : (Boolean) False
'--------------------------------------------------

long1872 = settingRepository1.GetAttr("NUCLEARMAGNETON_Nanometric")
'--------------------------------------------------
' Parameter 1 : (String) "NUCLEARMAGNETON_Nanometric"
' Returned value : (Variant) (Long) 1
'--------------------------------------------------

Dim bSTR3743
bSTR3743 = ""
Dim bSTR3744
bSTR3744 = ""
Dim boolean1872
settingRepository1.GetAttrInfo "NUCLEARMAGNETON_Nanometric", bSTR3743, bSTR3744, boolean1872
'--------------------------------------------------
' Parameter 1 : (String) "NUCLEARMAGNETON_Nanometric"
' Parameter 2 : (String) "Default value"
' Parameter 3 : (String) "Unlocked"
' Parameter 4 : (Boolean) False
'--------------------------------------------------

long1873 = settingRepository1.GetAttr("GYROMAGNETICCOEFFICIENT")
'--------------------------------------------------
' Parameter 1 : (String) "GYROMAGNETICCOEFFICIENT"
' Returned value : (Variant) (Long) 1
'--------------------------------------------------

Dim bSTR3745
bSTR3745 = ""
Dim bSTR3746
bSTR3746 = ""
Dim boolean1873
settingRepository1.GetAttrInfo "GYROMAGNETICCOEFFICIENT", bSTR3745, bSTR3746, boolean1873
'--------------------------------------------------
' Parameter 1 : (String) "GYROMAGNETICCOEFFICIENT"
' Parameter 2 : (String) "Default value"
' Parameter 3 : (String) "Unlocked"
' Parameter 4 : (Boolean) False
'--------------------------------------------------

long1874 = settingRepository1.GetAttr("GYROMAGNETICCOEFFICIENT_Large")
'--------------------------------------------------
' Parameter 1 : (String) "GYROMAGNETICCOEFFICIENT_Large"
' Returned value : (Variant) (Long) 1
'--------------------------------------------------

Dim bSTR3747
bSTR3747 = ""
Dim bSTR3748
bSTR3748 = ""
Dim boolean1874
settingRepository1.GetAttrInfo "GYROMAGNETICCOEFFICIENT_Large", bSTR3747, bSTR3748, boolean1874
'--------------------------------------------------
' Parameter 1 : (String) "GYROMAGNETICCOEFFICIENT_Large"
' Parameter 2 : (String) "Default value"
' Parameter 3 : (String) "Unlocked"
' Parameter 4 : (Boolean) False
'--------------------------------------------------

long1875 = settingRepository1.GetAttr("GYROMAGNETICCOEFFICIENT_ExtraLarge")
'--------------------------------------------------
' Parameter 1 : (String) "GYROMAGNETICCOEFFICIENT_ExtraLarge"
' Returned value : (Variant) (Long) 1
'--------------------------------------------------

Dim bSTR3749
bSTR3749 = ""
Dim bSTR3750
bSTR3750 = ""
Dim boolean1875
settingRepository1.GetAttrInfo "GYROMAGNETICCOEFFICIENT_ExtraLarge", bSTR3749, bSTR3750, boolean1875
'--------------------------------------------------
' Parameter 1 : (String) "GYROMAGNETICCOEFFICIENT_ExtraLarge"
' Parameter 2 : (String) "Default value"
' Parameter 3 : (String) "Unlocked"
' Parameter 4 : (Boolean) False
'--------------------------------------------------

long1876 = settingRepository1.GetAttr("GYROMAGNETICCOEFFICIENT_Small")
'--------------------------------------------------
' Parameter 1 : (String) "GYROMAGNETICCOEFFICIENT_Small"
' Returned value : (Variant) (Long) 1
'--------------------------------------------------

Dim bSTR3751
bSTR3751 = ""
Dim bSTR3752
bSTR3752 = ""
Dim boolean1876
settingRepository1.GetAttrInfo "GYROMAGNETICCOEFFICIENT_Small", bSTR3751, bSTR3752, boolean1876
'--------------------------------------------------
' Parameter 1 : (String) "GYROMAGNETICCOEFFICIENT_Small"
' Parameter 2 : (String) "Default value"
' Parameter 3 : (String) "Unlocked"
' Parameter 4 : (Boolean) False
'--------------------------------------------------

long1877 = settingRepository1.GetAttr("GYROMAGNETICCOEFFICIENT_ExtraSmall")
'--------------------------------------------------
' Parameter 1 : (String) "GYROMAGNETICCOEFFICIENT_ExtraSmall"
' Returned value : (Variant) (Long) 1
'--------------------------------------------------

Dim bSTR3753
bSTR3753 = ""
Dim bSTR3754
bSTR3754 = ""
Dim boolean1877
settingRepository1.GetAttrInfo "GYROMAGNETICCOEFFICIENT_ExtraSmall", bSTR3753, bSTR3754, boolean1877
'--------------------------------------------------
' Parameter 1 : (String) "GYROMAGNETICCOEFFICIENT_ExtraSmall"
' Parameter 2 : (String) "Default value"
' Parameter 3 : (String) "Unlocked"
' Parameter 4 : (Boolean) False
'--------------------------------------------------

long1878 = settingRepository1.GetAttr("GYROMAGNETICCOEFFICIENT_Nanometric")
'--------------------------------------------------
' Parameter 1 : (String) "GYROMAGNETICCOEFFICIENT_Nanometric"
' Returned value : (Variant) (Long) 1
'--------------------------------------------------

Dim bSTR3755
bSTR3755 = ""
Dim bSTR3756
bSTR3756 = ""
Dim boolean1878
settingRepository1.GetAttrInfo "GYROMAGNETICCOEFFICIENT_Nanometric", bSTR3755, bSTR3756, boolean1878
'--------------------------------------------------
' Parameter 1 : (String) "GYROMAGNETICCOEFFICIENT_Nanometric"
' Parameter 2 : (String) "Default value"
' Parameter 3 : (String) "Unlocked"
' Parameter 4 : (Boolean) False
'--------------------------------------------------

long1879 = settingRepository1.GetAttr("NUCLEARQUADRUPOLEMOMENT")
'--------------------------------------------------
' Parameter 1 : (String) "NUCLEARQUADRUPOLEMOMENT"
' Returned value : (Variant) (Long) 1
'--------------------------------------------------

Dim bSTR3757
bSTR3757 = ""
Dim bSTR3758
bSTR3758 = ""
Dim boolean1879
settingRepository1.GetAttrInfo "NUCLEARQUADRUPOLEMOMENT", bSTR3757, bSTR3758, boolean1879
'--------------------------------------------------
' Parameter 1 : (String) "NUCLEARQUADRUPOLEMOMENT"
' Parameter 2 : (String) "Default value"
' Parameter 3 : (String) "Unlocked"
' Parameter 4 : (Boolean) False
'--------------------------------------------------

long1880 = settingRepository1.GetAttr("NUCLEARQUADRUPOLEMOMENT_Large")
'--------------------------------------------------
' Parameter 1 : (String) "NUCLEARQUADRUPOLEMOMENT_Large"
' Returned value : (Variant) (Long) 1
'--------------------------------------------------

Dim bSTR3759
bSTR3759 = ""
Dim bSTR3760
bSTR3760 = ""
Dim boolean1880
settingRepository1.GetAttrInfo "NUCLEARQUADRUPOLEMOMENT_Large", bSTR3759, bSTR3760, boolean1880
'--------------------------------------------------
' Parameter 1 : (String) "NUCLEARQUADRUPOLEMOMENT_Large"
' Parameter 2 : (String) "Default value"
' Parameter 3 : (String) "Unlocked"
' Parameter 4 : (Boolean) False
'--------------------------------------------------

long1881 = settingRepository1.GetAttr("NUCLEARQUADRUPOLEMOMENT_ExtraLarge")
'--------------------------------------------------
' Parameter 1 : (String) "NUCLEARQUADRUPOLEMOMENT_ExtraLarge"
' Returned value : (Variant) (Long) 1
'--------------------------------------------------

Dim bSTR3761
bSTR3761 = ""
Dim bSTR3762
bSTR3762 = ""
Dim boolean1881
settingRepository1.GetAttrInfo "NUCLEARQUADRUPOLEMOMENT_ExtraLarge", bSTR3761, bSTR3762, boolean1881
'--------------------------------------------------
' Parameter 1 : (String) "NUCLEARQUADRUPOLEMOMENT_ExtraLarge"
' Parameter 2 : (String) "Default value"
' Parameter 3 : (String) "Unlocked"
' Parameter 4 : (Boolean) False
'--------------------------------------------------

long1882 = settingRepository1.GetAttr("NUCLEARQUADRUPOLEMOMENT_Small")
'--------------------------------------------------
' Parameter 1 : (String) "NUCLEARQUADRUPOLEMOMENT_Small"
' Returned value : (Variant) (Long) 1
'--------------------------------------------------

Dim bSTR3763
bSTR3763 = ""
Dim bSTR3764
bSTR3764 = ""
Dim boolean1882
settingRepository1.GetAttrInfo "NUCLEARQUADRUPOLEMOMENT_Small", bSTR3763, bSTR3764, boolean1882
'--------------------------------------------------
' Parameter 1 : (String) "NUCLEARQUADRUPOLEMOMENT_Small"
' Parameter 2 : (String) "Default value"
' Parameter 3 : (String) "Unlocked"
' Parameter 4 : (Boolean) False
'--------------------------------------------------

long1883 = settingRepository1.GetAttr("NUCLEARQUADRUPOLEMOMENT_ExtraSmall")
'--------------------------------------------------
' Parameter 1 : (String) "NUCLEARQUADRUPOLEMOMENT_ExtraSmall"
' Returned value : (Variant) (Long) 1
'--------------------------------------------------

Dim bSTR3765
bSTR3765 = ""
Dim bSTR3766
bSTR3766 = ""
Dim boolean1883
settingRepository1.GetAttrInfo "NUCLEARQUADRUPOLEMOMENT_ExtraSmall", bSTR3765, bSTR3766, boolean1883
'--------------------------------------------------
' Parameter 1 : (String) "NUCLEARQUADRUPOLEMOMENT_ExtraSmall"
' Parameter 2 : (String) "Default value"
' Parameter 3 : (String) "Unlocked"
' Parameter 4 : (Boolean) False
'--------------------------------------------------

long1884 = settingRepository1.GetAttr("NUCLEARQUADRUPOLEMOMENT_Nanometric")
'--------------------------------------------------
' Parameter 1 : (String) "NUCLEARQUADRUPOLEMOMENT_Nanometric"
' Returned value : (Variant) (Long) 1
'--------------------------------------------------

Dim bSTR3767
bSTR3767 = ""
Dim bSTR3768
bSTR3768 = ""
Dim boolean1884
settingRepository1.GetAttrInfo "NUCLEARQUADRUPOLEMOMENT_Nanometric", bSTR3767, bSTR3768, boolean1884
'--------------------------------------------------
' Parameter 1 : (String) "NUCLEARQUADRUPOLEMOMENT_Nanometric"
' Parameter 2 : (String) "Default value"
' Parameter 3 : (String) "Unlocked"
' Parameter 4 : (Boolean) False
'--------------------------------------------------

long1885 = settingRepository1.GetAttr("LEVELWIDTH")
'--------------------------------------------------
' Parameter 1 : (String) "LEVELWIDTH"
' Returned value : (Variant) (Long) 1
'--------------------------------------------------

Dim bSTR3769
bSTR3769 = ""
Dim bSTR3770
bSTR3770 = ""
Dim boolean1885
settingRepository1.GetAttrInfo "LEVELWIDTH", bSTR3769, bSTR3770, boolean1885
'--------------------------------------------------
' Parameter 1 : (String) "LEVELWIDTH"
' Parameter 2 : (String) "Default value"
' Parameter 3 : (String) "Unlocked"
' Parameter 4 : (Boolean) False
'--------------------------------------------------

long1886 = settingRepository1.GetAttr("LEVELWIDTH_Large")
'--------------------------------------------------
' Parameter 1 : (String) "LEVELWIDTH_Large"
' Returned value : (Variant) (Long) 1
'--------------------------------------------------

Dim bSTR3771
bSTR3771 = ""
Dim bSTR3772
bSTR3772 = ""
Dim boolean1886
settingRepository1.GetAttrInfo "LEVELWIDTH_Large", bSTR3771, bSTR3772, boolean1886
'--------------------------------------------------
' Parameter 1 : (String) "LEVELWIDTH_Large"
' Parameter 2 : (String) "Default value"
' Parameter 3 : (String) "Unlocked"
' Parameter 4 : (Boolean) False
'--------------------------------------------------

long1887 = settingRepository1.GetAttr("LEVELWIDTH_ExtraLarge")
'--------------------------------------------------
' Parameter 1 : (String) "LEVELWIDTH_ExtraLarge"
' Returned value : (Variant) (Long) 1
'--------------------------------------------------

Dim bSTR3773
bSTR3773 = ""
Dim bSTR3774
bSTR3774 = ""
Dim boolean1887
settingRepository1.GetAttrInfo "LEVELWIDTH_ExtraLarge", bSTR3773, bSTR3774, boolean1887
'--------------------------------------------------
' Parameter 1 : (String) "LEVELWIDTH_ExtraLarge"
' Parameter 2 : (String) "Default value"
' Parameter 3 : (String) "Unlocked"
' Parameter 4 : (Boolean) False
'--------------------------------------------------

long1888 = settingRepository1.GetAttr("LEVELWIDTH_Small")
'--------------------------------------------------
' Parameter 1 : (String) "LEVELWIDTH_Small"
' Returned value : (Variant) (Long) 1
'--------------------------------------------------

Dim bSTR3775
bSTR3775 = ""
Dim bSTR3776
bSTR3776 = ""
Dim boolean1888
settingRepository1.GetAttrInfo "LEVELWIDTH_Small", bSTR3775, bSTR3776, boolean1888
'--------------------------------------------------
' Parameter 1 : (String) "LEVELWIDTH_Small"
' Parameter 2 : (String) "Default value"
' Parameter 3 : (String) "Unlocked"
' Parameter 4 : (Boolean) False
'--------------------------------------------------

long1889 = settingRepository1.GetAttr("LEVELWIDTH_ExtraSmall")
'--------------------------------------------------
' Parameter 1 : (String) "LEVELWIDTH_ExtraSmall"
' Returned value : (Variant) (Long) 1
'--------------------------------------------------

Dim bSTR3777
bSTR3777 = ""
Dim bSTR3778
bSTR3778 = ""
Dim boolean1889
settingRepository1.GetAttrInfo "LEVELWIDTH_ExtraSmall", bSTR3777, bSTR3778, boolean1889
'--------------------------------------------------
' Parameter 1 : (String) "LEVELWIDTH_ExtraSmall"
' Parameter 2 : (String) "Default value"
' Parameter 3 : (String) "Unlocked"
' Parameter 4 : (Boolean) False
'--------------------------------------------------

long1890 = settingRepository1.GetAttr("LEVELWIDTH_Nanometric")
'--------------------------------------------------
' Parameter 1 : (String) "LEVELWIDTH_Nanometric"
' Returned value : (Variant) (Long) 1
'--------------------------------------------------

Dim bSTR3779
bSTR3779 = ""
Dim bSTR3780
bSTR3780 = ""
Dim boolean1890
settingRepository1.GetAttrInfo "LEVELWIDTH_Nanometric", bSTR3779, bSTR3780, boolean1890
'--------------------------------------------------
' Parameter 1 : (String) "LEVELWIDTH_Nanometric"
' Parameter 2 : (String) "Default value"
' Parameter 3 : (String) "Unlocked"
' Parameter 4 : (Boolean) False
'--------------------------------------------------

long1891 = settingRepository1.GetAttr("RADIOACTIVITY")
'--------------------------------------------------
' Parameter 1 : (String) "RADIOACTIVITY"
' Returned value : (Variant) (Long) 1
'--------------------------------------------------

Dim bSTR3781
bSTR3781 = ""
Dim bSTR3782
bSTR3782 = ""
Dim boolean1891
settingRepository1.GetAttrInfo "RADIOACTIVITY", bSTR3781, bSTR3782, boolean1891
'--------------------------------------------------
' Parameter 1 : (String) "RADIOACTIVITY"
' Parameter 2 : (String) "Default value"
' Parameter 3 : (String) "Unlocked"
' Parameter 4 : (Boolean) False
'--------------------------------------------------

long1892 = settingRepository1.GetAttr("RADIOACTIVITY_Large")
'--------------------------------------------------
' Parameter 1 : (String) "RADIOACTIVITY_Large"
' Returned value : (Variant) (Long) 1
'--------------------------------------------------

Dim bSTR3783
bSTR3783 = ""
Dim bSTR3784
bSTR3784 = ""
Dim boolean1892
settingRepository1.GetAttrInfo "RADIOACTIVITY_Large", bSTR3783, bSTR3784, boolean1892
'--------------------------------------------------
' Parameter 1 : (String) "RADIOACTIVITY_Large"
' Parameter 2 : (String) "Default value"
' Parameter 3 : (String) "Unlocked"
' Parameter 4 : (Boolean) False
'--------------------------------------------------

long1893 = settingRepository1.GetAttr("RADIOACTIVITY_ExtraLarge")
'--------------------------------------------------
' Parameter 1 : (String) "RADIOACTIVITY_ExtraLarge"
' Returned value : (Variant) (Long) 1
'--------------------------------------------------

Dim bSTR3785
bSTR3785 = ""
Dim bSTR3786
bSTR3786 = ""
Dim boolean1893
settingRepository1.GetAttrInfo "RADIOACTIVITY_ExtraLarge", bSTR3785, bSTR3786, boolean1893
'--------------------------------------------------
' Parameter 1 : (String) "RADIOACTIVITY_ExtraLarge"
' Parameter 2 : (String) "Default value"
' Parameter 3 : (String) "Unlocked"
' Parameter 4 : (Boolean) False
'--------------------------------------------------

long1894 = settingRepository1.GetAttr("RADIOACTIVITY_Small")
'--------------------------------------------------
' Parameter 1 : (String) "RADIOACTIVITY_Small"
' Returned value : (Variant) (Long) 1
'--------------------------------------------------

Dim bSTR3787
bSTR3787 = ""
Dim bSTR3788
bSTR3788 = ""
Dim boolean1894
settingRepository1.GetAttrInfo "RADIOACTIVITY_Small", bSTR3787, bSTR3788, boolean1894
'--------------------------------------------------
' Parameter 1 : (String) "RADIOACTIVITY_Small"
' Parameter 2 : (String) "Default value"
' Parameter 3 : (String) "Unlocked"
' Parameter 4 : (Boolean) False
'--------------------------------------------------

long1895 = settingRepository1.GetAttr("RADIOACTIVITY_ExtraSmall")
'--------------------------------------------------
' Parameter 1 : (String) "RADIOACTIVITY_ExtraSmall"
' Returned value : (Variant) (Long) 1
'--------------------------------------------------

Dim bSTR3789
bSTR3789 = ""
Dim bSTR3790
bSTR3790 = ""
Dim boolean1895
settingRepository1.GetAttrInfo "RADIOACTIVITY_ExtraSmall", bSTR3789, bSTR3790, boolean1895
'--------------------------------------------------
' Parameter 1 : (String) "RADIOACTIVITY_ExtraSmall"
' Parameter 2 : (String) "Default value"
' Parameter 3 : (String) "Unlocked"
' Parameter 4 : (Boolean) False
'--------------------------------------------------

long1896 = settingRepository1.GetAttr("RADIOACTIVITY_Nanometric")
'--------------------------------------------------
' Parameter 1 : (String) "RADIOACTIVITY_Nanometric"
' Returned value : (Variant) (Long) 1
'--------------------------------------------------

Dim bSTR3791
bSTR3791 = ""
Dim bSTR3792
bSTR3792 = ""
Dim boolean1896
settingRepository1.GetAttrInfo "RADIOACTIVITY_Nanometric", bSTR3791, bSTR3792, boolean1896
'--------------------------------------------------
' Parameter 1 : (String) "RADIOACTIVITY_Nanometric"
' Parameter 2 : (String) "Default value"
' Parameter 3 : (String) "Unlocked"
' Parameter 4 : (Boolean) False
'--------------------------------------------------

long1897 = settingRepository1.GetAttr("SPECIFICACTIVITY")
'--------------------------------------------------
' Parameter 1 : (String) "SPECIFICACTIVITY"
' Returned value : (Variant) (Long) 1
'--------------------------------------------------

Dim bSTR3793
bSTR3793 = ""
Dim bSTR3794
bSTR3794 = ""
Dim boolean1897
settingRepository1.GetAttrInfo "SPECIFICACTIVITY", bSTR3793, bSTR3794, boolean1897
'--------------------------------------------------
' Parameter 1 : (String) "SPECIFICACTIVITY"
' Parameter 2 : (String) "Default value"
' Parameter 3 : (String) "Unlocked"
' Parameter 4 : (Boolean) False
'--------------------------------------------------

long1898 = settingRepository1.GetAttr("SPECIFICACTIVITY_Large")
'--------------------------------------------------
' Parameter 1 : (String) "SPECIFICACTIVITY_Large"
' Returned value : (Variant) (Long) 1
'--------------------------------------------------

Dim bSTR3795
bSTR3795 = ""
Dim bSTR3796
bSTR3796 = ""
Dim boolean1898
settingRepository1.GetAttrInfo "SPECIFICACTIVITY_Large", bSTR3795, bSTR3796, boolean1898
'--------------------------------------------------
' Parameter 1 : (String) "SPECIFICACTIVITY_Large"
' Parameter 2 : (String) "Default value"
' Parameter 3 : (String) "Unlocked"
' Parameter 4 : (Boolean) False
'--------------------------------------------------

long1899 = settingRepository1.GetAttr("SPECIFICACTIVITY_ExtraLarge")
'--------------------------------------------------
' Parameter 1 : (String) "SPECIFICACTIVITY_ExtraLarge"
' Returned value : (Variant) (Long) 1
'--------------------------------------------------

Dim bSTR3797
bSTR3797 = ""
Dim bSTR3798
bSTR3798 = ""
Dim boolean1899
settingRepository1.GetAttrInfo "SPECIFICACTIVITY_ExtraLarge", bSTR3797, bSTR3798, boolean1899
'--------------------------------------------------
' Parameter 1 : (String) "SPECIFICACTIVITY_ExtraLarge"
' Parameter 2 : (String) "Default value"
' Parameter 3 : (String) "Unlocked"
' Parameter 4 : (Boolean) False
'--------------------------------------------------

long1900 = settingRepository1.GetAttr("SPECIFICACTIVITY_Small")
'--------------------------------------------------
' Parameter 1 : (String) "SPECIFICACTIVITY_Small"
' Returned value : (Variant) (Long) 1
'--------------------------------------------------

Dim bSTR3799
bSTR3799 = ""
Dim bSTR3800
bSTR3800 = ""
Dim boolean1900
settingRepository1.GetAttrInfo "SPECIFICACTIVITY_Small", bSTR3799, bSTR3800, boolean1900
'--------------------------------------------------
' Parameter 1 : (String) "SPECIFICACTIVITY_Small"
' Parameter 2 : (String) "Default value"
' Parameter 3 : (String) "Unlocked"
' Parameter 4 : (Boolean) False
'--------------------------------------------------

long1901 = settingRepository1.GetAttr("SPECIFICACTIVITY_ExtraSmall")
'--------------------------------------------------
' Parameter 1 : (String) "SPECIFICACTIVITY_ExtraSmall"
' Returned value : (Variant) (Long) 1
'--------------------------------------------------

Dim bSTR3801
bSTR3801 = ""
Dim bSTR3802
bSTR3802 = ""
Dim boolean1901
settingRepository1.GetAttrInfo "SPECIFICACTIVITY_ExtraSmall", bSTR3801, bSTR3802, boolean1901
'--------------------------------------------------
' Parameter 1 : (String) "SPECIFICACTIVITY_ExtraSmall"
' Parameter 2 : (String) "Default value"
' Parameter 3 : (String) "Unlocked"
' Parameter 4 : (Boolean) False
'--------------------------------------------------

long1902 = settingRepository1.GetAttr("SPECIFICACTIVITY_Nanometric")
'--------------------------------------------------
' Parameter 1 : (String) "SPECIFICACTIVITY_Nanometric"
' Returned value : (Variant) (Long) 1
'--------------------------------------------------

Dim bSTR3803
bSTR3803 = ""
Dim bSTR3804
bSTR3804 = ""
Dim boolean1902
settingRepository1.GetAttrInfo "SPECIFICACTIVITY_Nanometric", bSTR3803, bSTR3804, boolean1902
'--------------------------------------------------
' Parameter 1 : (String) "SPECIFICACTIVITY_Nanometric"
' Parameter 2 : (String) "Default value"
' Parameter 3 : (String) "Unlocked"
' Parameter 4 : (Boolean) False
'--------------------------------------------------

long1903 = settingRepository1.GetAttr("DECAYCONSTANT")
'--------------------------------------------------
' Parameter 1 : (String) "DECAYCONSTANT"
' Returned value : (Variant) (Long) 1
'--------------------------------------------------

Dim bSTR3805
bSTR3805 = ""
Dim bSTR3806
bSTR3806 = ""
Dim boolean1903
settingRepository1.GetAttrInfo "DECAYCONSTANT", bSTR3805, bSTR3806, boolean1903
'--------------------------------------------------
' Parameter 1 : (String) "DECAYCONSTANT"
' Parameter 2 : (String) "Default value"
' Parameter 3 : (String) "Unlocked"
' Parameter 4 : (Boolean) False
'--------------------------------------------------

long1904 = settingRepository1.GetAttr("DECAYCONSTANT_Large")
'--------------------------------------------------
' Parameter 1 : (String) "DECAYCONSTANT_Large"
' Returned value : (Variant) (Long) 1
'--------------------------------------------------

Dim bSTR3807
bSTR3807 = ""
Dim bSTR3808
bSTR3808 = ""
Dim boolean1904
settingRepository1.GetAttrInfo "DECAYCONSTANT_Large", bSTR3807, bSTR3808, boolean1904
'--------------------------------------------------
' Parameter 1 : (String) "DECAYCONSTANT_Large"
' Parameter 2 : (String) "Default value"
' Parameter 3 : (String) "Unlocked"
' Parameter 4 : (Boolean) False
'--------------------------------------------------

long1905 = settingRepository1.GetAttr("DECAYCONSTANT_ExtraLarge")
'--------------------------------------------------
' Parameter 1 : (String) "DECAYCONSTANT_ExtraLarge"
' Returned value : (Variant) (Long) 1
'--------------------------------------------------

Dim bSTR3809
bSTR3809 = ""
Dim bSTR3810
bSTR3810 = ""
Dim boolean1905
settingRepository1.GetAttrInfo "DECAYCONSTANT_ExtraLarge", bSTR3809, bSTR3810, boolean1905
'--------------------------------------------------
' Parameter 1 : (String) "DECAYCONSTANT_ExtraLarge"
' Parameter 2 : (String) "Default value"
' Parameter 3 : (String) "Unlocked"
' Parameter 4 : (Boolean) False
'--------------------------------------------------

long1906 = settingRepository1.GetAttr("DECAYCONSTANT_Small")
'--------------------------------------------------
' Parameter 1 : (String) "DECAYCONSTANT_Small"
' Returned value : (Variant) (Long) 1
'--------------------------------------------------

Dim bSTR3811
bSTR3811 = ""
Dim bSTR3812
bSTR3812 = ""
Dim boolean1906
settingRepository1.GetAttrInfo "DECAYCONSTANT_Small", bSTR3811, bSTR3812, boolean1906
'--------------------------------------------------
' Parameter 1 : (String) "DECAYCONSTANT_Small"
' Parameter 2 : (String) "Default value"
' Parameter 3 : (String) "Unlocked"
' Parameter 4 : (Boolean) False
'--------------------------------------------------

long1907 = settingRepository1.GetAttr("DECAYCONSTANT_ExtraSmall")
'--------------------------------------------------
' Parameter 1 : (String) "DECAYCONSTANT_ExtraSmall"
' Returned value : (Variant) (Long) 1
'--------------------------------------------------

Dim bSTR3813
bSTR3813 = ""
Dim bSTR3814
bSTR3814 = ""
Dim boolean1907
settingRepository1.GetAttrInfo "DECAYCONSTANT_ExtraSmall", bSTR3813, bSTR3814, boolean1907
'--------------------------------------------------
' Parameter 1 : (String) "DECAYCONSTANT_ExtraSmall"
' Parameter 2 : (String) "Default value"
' Parameter 3 : (String) "Unlocked"
' Parameter 4 : (Boolean) False
'--------------------------------------------------

long1908 = settingRepository1.GetAttr("DECAYCONSTANT_Nanometric")
'--------------------------------------------------
' Parameter 1 : (String) "DECAYCONSTANT_Nanometric"
' Returned value : (Variant) (Long) 1
'--------------------------------------------------

Dim bSTR3815
bSTR3815 = ""
Dim bSTR3816
bSTR3816 = ""
Dim boolean1908
settingRepository1.GetAttrInfo "DECAYCONSTANT_Nanometric", bSTR3815, bSTR3816, boolean1908
'--------------------------------------------------
' Parameter 1 : (String) "DECAYCONSTANT_Nanometric"
' Parameter 2 : (String) "Default value"
' Parameter 3 : (String) "Unlocked"
' Parameter 4 : (Boolean) False
'--------------------------------------------------

long1909 = settingRepository1.GetAttr("ANGULARCROSSSECTION")
'--------------------------------------------------
' Parameter 1 : (String) "ANGULARCROSSSECTION"
' Returned value : (Variant) (Long) 1
'--------------------------------------------------

Dim bSTR3817
bSTR3817 = ""
Dim bSTR3818
bSTR3818 = ""
Dim boolean1909
settingRepository1.GetAttrInfo "ANGULARCROSSSECTION", bSTR3817, bSTR3818, boolean1909
'--------------------------------------------------
' Parameter 1 : (String) "ANGULARCROSSSECTION"
' Parameter 2 : (String) "Default value"
' Parameter 3 : (String) "Unlocked"
' Parameter 4 : (Boolean) False
'--------------------------------------------------

long1910 = settingRepository1.GetAttr("ANGULARCROSSSECTION_Large")
'--------------------------------------------------
' Parameter 1 : (String) "ANGULARCROSSSECTION_Large"
' Returned value : (Variant) (Long) 1
'--------------------------------------------------

Dim bSTR3819
bSTR3819 = ""
Dim bSTR3820
bSTR3820 = ""
Dim boolean1910
settingRepository1.GetAttrInfo "ANGULARCROSSSECTION_Large", bSTR3819, bSTR3820, boolean1910
'--------------------------------------------------
' Parameter 1 : (String) "ANGULARCROSSSECTION_Large"
' Parameter 2 : (String) "Default value"
' Parameter 3 : (String) "Unlocked"
' Parameter 4 : (Boolean) False
'--------------------------------------------------

long1911 = settingRepository1.GetAttr("ANGULARCROSSSECTION_ExtraLarge")
'--------------------------------------------------
' Parameter 1 : (String) "ANGULARCROSSSECTION_ExtraLarge"
' Returned value : (Variant) (Long) 1
'--------------------------------------------------

Dim bSTR3821
bSTR3821 = ""
Dim bSTR3822
bSTR3822 = ""
Dim boolean1911
settingRepository1.GetAttrInfo "ANGULARCROSSSECTION_ExtraLarge", bSTR3821, bSTR3822, boolean1911
'--------------------------------------------------
' Parameter 1 : (String) "ANGULARCROSSSECTION_ExtraLarge"
' Parameter 2 : (String) "Default value"
' Parameter 3 : (String) "Unlocked"
' Parameter 4 : (Boolean) False
'--------------------------------------------------

long1912 = settingRepository1.GetAttr("ANGULARCROSSSECTION_Small")
'--------------------------------------------------
' Parameter 1 : (String) "ANGULARCROSSSECTION_Small"
' Returned value : (Variant) (Long) 1
'--------------------------------------------------

Dim bSTR3823
bSTR3823 = ""
Dim bSTR3824
bSTR3824 = ""
Dim boolean1912
settingRepository1.GetAttrInfo "ANGULARCROSSSECTION_Small", bSTR3823, bSTR3824, boolean1912
'--------------------------------------------------
' Parameter 1 : (String) "ANGULARCROSSSECTION_Small"
' Parameter 2 : (String) "Default value"
' Parameter 3 : (String) "Unlocked"
' Parameter 4 : (Boolean) False
'--------------------------------------------------

long1913 = settingRepository1.GetAttr("ANGULARCROSSSECTION_ExtraSmall")
'--------------------------------------------------
' Parameter 1 : (String) "ANGULARCROSSSECTION_ExtraSmall"
' Returned value : (Variant) (Long) 1
'--------------------------------------------------

Dim bSTR3825
bSTR3825 = ""
Dim bSTR3826
bSTR3826 = ""
Dim boolean1913
settingRepository1.GetAttrInfo "ANGULARCROSSSECTION_ExtraSmall", bSTR3825, bSTR3826, boolean1913
'--------------------------------------------------
' Parameter 1 : (String) "ANGULARCROSSSECTION_ExtraSmall"
' Parameter 2 : (String) "Default value"
' Parameter 3 : (String) "Unlocked"
' Parameter 4 : (Boolean) False
'--------------------------------------------------

long1914 = settingRepository1.GetAttr("ANGULARCROSSSECTION_Nanometric")
'--------------------------------------------------
' Parameter 1 : (String) "ANGULARCROSSSECTION_Nanometric"
' Returned value : (Variant) (Long) 1
'--------------------------------------------------

Dim bSTR3827
bSTR3827 = ""
Dim bSTR3828
bSTR3828 = ""
Dim boolean1914
settingRepository1.GetAttrInfo "ANGULARCROSSSECTION_Nanometric", bSTR3827, bSTR3828, boolean1914
'--------------------------------------------------
' Parameter 1 : (String) "ANGULARCROSSSECTION_Nanometric"
' Parameter 2 : (String) "Default value"
' Parameter 3 : (String) "Unlocked"
' Parameter 4 : (Boolean) False
'--------------------------------------------------

long1915 = settingRepository1.GetAttr("SPECTRALCROSSSECTION")
'--------------------------------------------------
' Parameter 1 : (String) "SPECTRALCROSSSECTION"
' Returned value : (Variant) (Long) 1
'--------------------------------------------------

Dim bSTR3829
bSTR3829 = ""
Dim bSTR3830
bSTR3830 = ""
Dim boolean1915
settingRepository1.GetAttrInfo "SPECTRALCROSSSECTION", bSTR3829, bSTR3830, boolean1915
'--------------------------------------------------
' Parameter 1 : (String) "SPECTRALCROSSSECTION"
' Parameter 2 : (String) "Default value"
' Parameter 3 : (String) "Unlocked"
' Parameter 4 : (Boolean) False
'--------------------------------------------------

long1916 = settingRepository1.GetAttr("SPECTRALCROSSSECTION_Large")
'--------------------------------------------------
' Parameter 1 : (String) "SPECTRALCROSSSECTION_Large"
' Returned value : (Variant) (Long) 1
'--------------------------------------------------

Dim bSTR3831
bSTR3831 = ""
Dim bSTR3832
bSTR3832 = ""
Dim boolean1916
settingRepository1.GetAttrInfo "SPECTRALCROSSSECTION_Large", bSTR3831, bSTR3832, boolean1916
'--------------------------------------------------
' Parameter 1 : (String) "SPECTRALCROSSSECTION_Large"
' Parameter 2 : (String) "Default value"
' Parameter 3 : (String) "Unlocked"
' Parameter 4 : (Boolean) False
'--------------------------------------------------

long1917 = settingRepository1.GetAttr("SPECTRALCROSSSECTION_ExtraLarge")
'--------------------------------------------------
' Parameter 1 : (String) "SPECTRALCROSSSECTION_ExtraLarge"
' Returned value : (Variant) (Long) 1
'--------------------------------------------------

Dim bSTR3833
bSTR3833 = ""
Dim bSTR3834
bSTR3834 = ""
Dim boolean1917
settingRepository1.GetAttrInfo "SPECTRALCROSSSECTION_ExtraLarge", bSTR3833, bSTR3834, boolean1917
'--------------------------------------------------
' Parameter 1 : (String) "SPECTRALCROSSSECTION_ExtraLarge"
' Parameter 2 : (String) "Default value"
' Parameter 3 : (String) "Unlocked"
' Parameter 4 : (Boolean) False
'--------------------------------------------------

long1918 = settingRepository1.GetAttr("SPECTRALCROSSSECTION_Small")
'--------------------------------------------------
' Parameter 1 : (String) "SPECTRALCROSSSECTION_Small"
' Returned value : (Variant) (Long) 1
'--------------------------------------------------

Dim bSTR3835
bSTR3835 = ""
Dim bSTR3836
bSTR3836 = ""
Dim boolean1918
settingRepository1.GetAttrInfo "SPECTRALCROSSSECTION_Small", bSTR3835, bSTR3836, boolean1918
'--------------------------------------------------
' Parameter 1 : (String) "SPECTRALCROSSSECTION_Small"
' Parameter 2 : (String) "Default value"
' Parameter 3 : (String) "Unlocked"
' Parameter 4 : (Boolean) False
'--------------------------------------------------

long1919 = settingRepository1.GetAttr("SPECTRALCROSSSECTION_ExtraSmall")
'--------------------------------------------------
' Parameter 1 : (String) "SPECTRALCROSSSECTION_ExtraSmall"
' Returned value : (Variant) (Long) 1
'--------------------------------------------------

Dim bSTR3837
bSTR3837 = ""
Dim bSTR3838
bSTR3838 = ""
Dim boolean1919
settingRepository1.GetAttrInfo "SPECTRALCROSSSECTION_ExtraSmall", bSTR3837, bSTR3838, boolean1919
'--------------------------------------------------
' Parameter 1 : (String) "SPECTRALCROSSSECTION_ExtraSmall"
' Parameter 2 : (String) "Default value"
' Parameter 3 : (String) "Unlocked"
' Parameter 4 : (Boolean) False
'--------------------------------------------------

long1920 = settingRepository1.GetAttr("SPECTRALCROSSSECTION_Nanometric")
'--------------------------------------------------
' Parameter 1 : (String) "SPECTRALCROSSSECTION_Nanometric"
' Returned value : (Variant) (Long) 1
'--------------------------------------------------

Dim bSTR3839
bSTR3839 = ""
Dim bSTR3840
bSTR3840 = ""
Dim boolean1920
settingRepository1.GetAttrInfo "SPECTRALCROSSSECTION_Nanometric", bSTR3839, bSTR3840, boolean1920
'--------------------------------------------------
' Parameter 1 : (String) "SPECTRALCROSSSECTION_Nanometric"
' Parameter 2 : (String) "Default value"
' Parameter 3 : (String) "Unlocked"
' Parameter 4 : (Boolean) False
'--------------------------------------------------

long1921 = settingRepository1.GetAttr("SPECTRALANGULARCROSSSECTION")
'--------------------------------------------------
' Parameter 1 : (String) "SPECTRALANGULARCROSSSECTION"
' Returned value : (Variant) (Long) 1
'--------------------------------------------------

Dim bSTR3841
bSTR3841 = ""
Dim bSTR3842
bSTR3842 = ""
Dim boolean1921
settingRepository1.GetAttrInfo "SPECTRALANGULARCROSSSECTION", bSTR3841, bSTR3842, boolean1921
'--------------------------------------------------
' Parameter 1 : (String) "SPECTRALANGULARCROSSSECTION"
' Parameter 2 : (String) "Default value"
' Parameter 3 : (String) "Unlocked"
' Parameter 4 : (Boolean) False
'--------------------------------------------------

long1922 = settingRepository1.GetAttr("SPECTRALANGULARCROSSSECTION_Large")
'--------------------------------------------------
' Parameter 1 : (String) "SPECTRALANGULARCROSSSECTION_Large"
' Returned value : (Variant) (Long) 1
'--------------------------------------------------

Dim bSTR3843
bSTR3843 = ""
Dim bSTR3844
bSTR3844 = ""
Dim boolean1922
settingRepository1.GetAttrInfo "SPECTRALANGULARCROSSSECTION_Large", bSTR3843, bSTR3844, boolean1922
'--------------------------------------------------
' Parameter 1 : (String) "SPECTRALANGULARCROSSSECTION_Large"
' Parameter 2 : (String) "Default value"
' Parameter 3 : (String) "Unlocked"
' Parameter 4 : (Boolean) False
'--------------------------------------------------

long1923 = settingRepository1.GetAttr("SPECTRALANGULARCROSSSECTION_ExtraLarge")
'--------------------------------------------------
' Parameter 1 : (String) "SPECTRALANGULARCROSSSECTION_ExtraLarge"
' Returned value : (Variant) (Long) 1
'--------------------------------------------------

Dim bSTR3845
bSTR3845 = ""
Dim bSTR3846
bSTR3846 = ""
Dim boolean1923
settingRepository1.GetAttrInfo "SPECTRALANGULARCROSSSECTION_ExtraLarge", bSTR3845, bSTR3846, boolean1923
'--------------------------------------------------
' Parameter 1 : (String) "SPECTRALANGULARCROSSSECTION_ExtraLarge"
' Parameter 2 : (String) "Default value"
' Parameter 3 : (String) "Unlocked"
' Parameter 4 : (Boolean) False
'--------------------------------------------------

long1924 = settingRepository1.GetAttr("SPECTRALANGULARCROSSSECTION_Small")
'--------------------------------------------------
' Parameter 1 : (String) "SPECTRALANGULARCROSSSECTION_Small"
' Returned value : (Variant) (Long) 1
'--------------------------------------------------

Dim bSTR3847
bSTR3847 = ""
Dim bSTR3848
bSTR3848 = ""
Dim boolean1924
settingRepository1.GetAttrInfo "SPECTRALANGULARCROSSSECTION_Small", bSTR3847, bSTR3848, boolean1924
'--------------------------------------------------
' Parameter 1 : (String) "SPECTRALANGULARCROSSSECTION_Small"
' Parameter 2 : (String) "Default value"
' Parameter 3 : (String) "Unlocked"
' Parameter 4 : (Boolean) False
'--------------------------------------------------

long1925 = settingRepository1.GetAttr("SPECTRALANGULARCROSSSECTION_ExtraSmall")
'--------------------------------------------------
' Parameter 1 : (String) "SPECTRALANGULARCROSSSECTION_ExtraSmall"
' Returned value : (Variant) (Long) 1
'--------------------------------------------------

Dim bSTR3849
bSTR3849 = ""
Dim bSTR3850
bSTR3850 = ""
Dim boolean1925
settingRepository1.GetAttrInfo "SPECTRALANGULARCROSSSECTION_ExtraSmall", bSTR3849, bSTR3850, boolean1925
'--------------------------------------------------
' Parameter 1 : (String) "SPECTRALANGULARCROSSSECTION_ExtraSmall"
' Parameter 2 : (String) "Default value"
' Parameter 3 : (String) "Unlocked"
' Parameter 4 : (Boolean) False
'--------------------------------------------------

long1926 = settingRepository1.GetAttr("SPECTRALANGULARCROSSSECTION_Nanometric")
'--------------------------------------------------
' Parameter 1 : (String) "SPECTRALANGULARCROSSSECTION_Nanometric"
' Returned value : (Variant) (Long) 1
'--------------------------------------------------

Dim bSTR3851
bSTR3851 = ""
Dim bSTR3852
bSTR3852 = ""
Dim boolean1926
settingRepository1.GetAttrInfo "SPECTRALANGULARCROSSSECTION_Nanometric", bSTR3851, bSTR3852, boolean1926
'--------------------------------------------------
' Parameter 1 : (String) "SPECTRALANGULARCROSSSECTION_Nanometric"
' Parameter 2 : (String) "Default value"
' Parameter 3 : (String) "Unlocked"
' Parameter 4 : (Boolean) False
'--------------------------------------------------

long1927 = settingRepository1.GetAttr("MACROSCOPICCROSSSECTION")
'--------------------------------------------------
' Parameter 1 : (String) "MACROSCOPICCROSSSECTION"
' Returned value : (Variant) (Long) 1
'--------------------------------------------------

Dim bSTR3853
bSTR3853 = ""
Dim bSTR3854
bSTR3854 = ""
Dim boolean1927
settingRepository1.GetAttrInfo "MACROSCOPICCROSSSECTION", bSTR3853, bSTR3854, boolean1927
'--------------------------------------------------
' Parameter 1 : (String) "MACROSCOPICCROSSSECTION"
' Parameter 2 : (String) "Default value"
' Parameter 3 : (String) "Unlocked"
' Parameter 4 : (Boolean) False
'--------------------------------------------------

long1928 = settingRepository1.GetAttr("MACROSCOPICCROSSSECTION_Large")
'--------------------------------------------------
' Parameter 1 : (String) "MACROSCOPICCROSSSECTION_Large"
' Returned value : (Variant) (Long) 1
'--------------------------------------------------

Dim bSTR3855
bSTR3855 = ""
Dim bSTR3856
bSTR3856 = ""
Dim boolean1928
settingRepository1.GetAttrInfo "MACROSCOPICCROSSSECTION_Large", bSTR3855, bSTR3856, boolean1928
'--------------------------------------------------
' Parameter 1 : (String) "MACROSCOPICCROSSSECTION_Large"
' Parameter 2 : (String) "Default value"
' Parameter 3 : (String) "Unlocked"
' Parameter 4 : (Boolean) False
'--------------------------------------------------

long1929 = settingRepository1.GetAttr("MACROSCOPICCROSSSECTION_ExtraLarge")
'--------------------------------------------------
' Parameter 1 : (String) "MACROSCOPICCROSSSECTION_ExtraLarge"
' Returned value : (Variant) (Long) 1
'--------------------------------------------------

Dim bSTR3857
bSTR3857 = ""
Dim bSTR3858
bSTR3858 = ""
Dim boolean1929
settingRepository1.GetAttrInfo "MACROSCOPICCROSSSECTION_ExtraLarge", bSTR3857, bSTR3858, boolean1929
'--------------------------------------------------
' Parameter 1 : (String) "MACROSCOPICCROSSSECTION_ExtraLarge"
' Parameter 2 : (String) "Default value"
' Parameter 3 : (String) "Unlocked"
' Parameter 4 : (Boolean) False
'--------------------------------------------------

long1930 = settingRepository1.GetAttr("MACROSCOPICCROSSSECTION_Small")
'--------------------------------------------------
' Parameter 1 : (String) "MACROSCOPICCROSSSECTION_Small"
' Returned value : (Variant) (Long) 1
'--------------------------------------------------

Dim bSTR3859
bSTR3859 = ""
Dim bSTR3860
bSTR3860 = ""
Dim boolean1930
settingRepository1.GetAttrInfo "MACROSCOPICCROSSSECTION_Small", bSTR3859, bSTR3860, boolean1930
'--------------------------------------------------
' Parameter 1 : (String) "MACROSCOPICCROSSSECTION_Small"
' Parameter 2 : (String) "Default value"
' Parameter 3 : (String) "Unlocked"
' Parameter 4 : (Boolean) False
'--------------------------------------------------

long1931 = settingRepository1.GetAttr("MACROSCOPICCROSSSECTION_ExtraSmall")
'--------------------------------------------------
' Parameter 1 : (String) "MACROSCOPICCROSSSECTION_ExtraSmall"
' Returned value : (Variant) (Long) 1
'--------------------------------------------------

Dim bSTR3861
bSTR3861 = ""
Dim bSTR3862
bSTR3862 = ""
Dim boolean1931
settingRepository1.GetAttrInfo "MACROSCOPICCROSSSECTION_ExtraSmall", bSTR3861, bSTR3862, boolean1931
'--------------------------------------------------
' Parameter 1 : (String) "MACROSCOPICCROSSSECTION_ExtraSmall"
' Parameter 2 : (String) "Default value"
' Parameter 3 : (String) "Unlocked"
' Parameter 4 : (Boolean) False
'--------------------------------------------------

long1932 = settingRepository1.GetAttr("MACROSCOPICCROSSSECTION_Nanometric")
'--------------------------------------------------
' Parameter 1 : (String) "MACROSCOPICCROSSSECTION_Nanometric"
' Returned value : (Variant) (Long) 1
'--------------------------------------------------

Dim bSTR3863
bSTR3863 = ""
Dim bSTR3864
bSTR3864 = ""
Dim boolean1932
settingRepository1.GetAttrInfo "MACROSCOPICCROSSSECTION_Nanometric", bSTR3863, bSTR3864, boolean1932
'--------------------------------------------------
' Parameter 1 : (String) "MACROSCOPICCROSSSECTION_Nanometric"
' Parameter 2 : (String) "Default value"
' Parameter 3 : (String) "Unlocked"
' Parameter 4 : (Boolean) False
'--------------------------------------------------

long1933 = settingRepository1.GetAttr("PARTICLEFLUENCE")
'--------------------------------------------------
' Parameter 1 : (String) "PARTICLEFLUENCE"
' Returned value : (Variant) (Long) 1
'--------------------------------------------------

Dim bSTR3865
bSTR3865 = ""
Dim bSTR3866
bSTR3866 = ""
Dim boolean1933
settingRepository1.GetAttrInfo "PARTICLEFLUENCE", bSTR3865, bSTR3866, boolean1933
'--------------------------------------------------
' Parameter 1 : (String) "PARTICLEFLUENCE"
' Parameter 2 : (String) "Default value"
' Parameter 3 : (String) "Unlocked"
' Parameter 4 : (Boolean) False
'--------------------------------------------------

long1934 = settingRepository1.GetAttr("PARTICLEFLUENCE_Large")
'--------------------------------------------------
' Parameter 1 : (String) "PARTICLEFLUENCE_Large"
' Returned value : (Variant) (Long) 1
'--------------------------------------------------

Dim bSTR3867
bSTR3867 = ""
Dim bSTR3868
bSTR3868 = ""
Dim boolean1934
settingRepository1.GetAttrInfo "PARTICLEFLUENCE_Large", bSTR3867, bSTR3868, boolean1934
'--------------------------------------------------
' Parameter 1 : (String) "PARTICLEFLUENCE_Large"
' Parameter 2 : (String) "Default value"
' Parameter 3 : (String) "Unlocked"
' Parameter 4 : (Boolean) False
'--------------------------------------------------

long1935 = settingRepository1.GetAttr("PARTICLEFLUENCE_ExtraLarge")
'--------------------------------------------------
' Parameter 1 : (String) "PARTICLEFLUENCE_ExtraLarge"
' Returned value : (Variant) (Long) 1
'--------------------------------------------------

Dim bSTR3869
bSTR3869 = ""
Dim bSTR3870
bSTR3870 = ""
Dim boolean1935
settingRepository1.GetAttrInfo "PARTICLEFLUENCE_ExtraLarge", bSTR3869, bSTR3870, boolean1935
'--------------------------------------------------
' Parameter 1 : (String) "PARTICLEFLUENCE_ExtraLarge"
' Parameter 2 : (String) "Default value"
' Parameter 3 : (String) "Unlocked"
' Parameter 4 : (Boolean) False
'--------------------------------------------------

long1936 = settingRepository1.GetAttr("PARTICLEFLUENCE_Small")
'--------------------------------------------------
' Parameter 1 : (String) "PARTICLEFLUENCE_Small"
' Returned value : (Variant) (Long) 1
'--------------------------------------------------

Dim bSTR3871
bSTR3871 = ""
Dim bSTR3872
bSTR3872 = ""
Dim boolean1936
settingRepository1.GetAttrInfo "PARTICLEFLUENCE_Small", bSTR3871, bSTR3872, boolean1936
'--------------------------------------------------
' Parameter 1 : (String) "PARTICLEFLUENCE_Small"
' Parameter 2 : (String) "Default value"
' Parameter 3 : (String) "Unlocked"
' Parameter 4 : (Boolean) False
'--------------------------------------------------

long1937 = settingRepository1.GetAttr("PARTICLEFLUENCE_ExtraSmall")
'--------------------------------------------------
' Parameter 1 : (String) "PARTICLEFLUENCE_ExtraSmall"
' Returned value : (Variant) (Long) 1
'--------------------------------------------------

Dim bSTR3873
bSTR3873 = ""
Dim bSTR3874
bSTR3874 = ""
Dim boolean1937
settingRepository1.GetAttrInfo "PARTICLEFLUENCE_ExtraSmall", bSTR3873, bSTR3874, boolean1937
'--------------------------------------------------
' Parameter 1 : (String) "PARTICLEFLUENCE_ExtraSmall"
' Parameter 2 : (String) "Default value"
' Parameter 3 : (String) "Unlocked"
' Parameter 4 : (Boolean) False
'--------------------------------------------------

long1938 = settingRepository1.GetAttr("PARTICLEFLUENCE_Nanometric")
'--------------------------------------------------
' Parameter 1 : (String) "PARTICLEFLUENCE_Nanometric"
' Returned value : (Variant) (Long) 1
'--------------------------------------------------

Dim bSTR3875
bSTR3875 = ""
Dim bSTR3876
bSTR3876 = ""
Dim boolean1938
settingRepository1.GetAttrInfo "PARTICLEFLUENCE_Nanometric", bSTR3875, bSTR3876, boolean1938
'--------------------------------------------------
' Parameter 1 : (String) "PARTICLEFLUENCE_Nanometric"
' Parameter 2 : (String) "Default value"
' Parameter 3 : (String) "Unlocked"
' Parameter 4 : (Boolean) False
'--------------------------------------------------

long1939 = settingRepository1.GetAttr("PARTICLEFLUENCERATE")
'--------------------------------------------------
' Parameter 1 : (String) "PARTICLEFLUENCERATE"
' Returned value : (Variant) (Long) 1
'--------------------------------------------------

Dim bSTR3877
bSTR3877 = ""
Dim bSTR3878
bSTR3878 = ""
Dim boolean1939
settingRepository1.GetAttrInfo "PARTICLEFLUENCERATE", bSTR3877, bSTR3878, boolean1939
'--------------------------------------------------
' Parameter 1 : (String) "PARTICLEFLUENCERATE"
' Parameter 2 : (String) "Default value"
' Parameter 3 : (String) "Unlocked"
' Parameter 4 : (Boolean) False
'--------------------------------------------------

long1940 = settingRepository1.GetAttr("PARTICLEFLUENCERATE_Large")
'--------------------------------------------------
' Parameter 1 : (String) "PARTICLEFLUENCERATE_Large"
' Returned value : (Variant) (Long) 1
'--------------------------------------------------

Dim bSTR3879
bSTR3879 = ""
Dim bSTR3880
bSTR3880 = ""
Dim boolean1940
settingRepository1.GetAttrInfo "PARTICLEFLUENCERATE_Large", bSTR3879, bSTR3880, boolean1940
'--------------------------------------------------
' Parameter 1 : (String) "PARTICLEFLUENCERATE_Large"
' Parameter 2 : (String) "Default value"
' Parameter 3 : (String) "Unlocked"
' Parameter 4 : (Boolean) False
'--------------------------------------------------

long1941 = settingRepository1.GetAttr("PARTICLEFLUENCERATE_ExtraLarge")
'--------------------------------------------------
' Parameter 1 : (String) "PARTICLEFLUENCERATE_ExtraLarge"
' Returned value : (Variant) (Long) 1
'--------------------------------------------------

Dim bSTR3881
bSTR3881 = ""
Dim bSTR3882
bSTR3882 = ""
Dim boolean1941
settingRepository1.GetAttrInfo "PARTICLEFLUENCERATE_ExtraLarge", bSTR3881, bSTR3882, boolean1941
'--------------------------------------------------
' Parameter 1 : (String) "PARTICLEFLUENCERATE_ExtraLarge"
' Parameter 2 : (String) "Default value"
' Parameter 3 : (String) "Unlocked"
' Parameter 4 : (Boolean) False
'--------------------------------------------------

long1942 = settingRepository1.GetAttr("PARTICLEFLUENCERATE_Small")
'--------------------------------------------------
' Parameter 1 : (String) "PARTICLEFLUENCERATE_Small"
' Returned value : (Variant) (Long) 1
'--------------------------------------------------

Dim bSTR3883
bSTR3883 = ""
Dim bSTR3884
bSTR3884 = ""
Dim boolean1942
settingRepository1.GetAttrInfo "PARTICLEFLUENCERATE_Small", bSTR3883, bSTR3884, boolean1942
'--------------------------------------------------
' Parameter 1 : (String) "PARTICLEFLUENCERATE_Small"
' Parameter 2 : (String) "Default value"
' Parameter 3 : (String) "Unlocked"
' Parameter 4 : (Boolean) False
'--------------------------------------------------

long1943 = settingRepository1.GetAttr("PARTICLEFLUENCERATE_ExtraSmall")
'--------------------------------------------------
' Parameter 1 : (String) "PARTICLEFLUENCERATE_ExtraSmall"
' Returned value : (Variant) (Long) 1
'--------------------------------------------------

Dim bSTR3885
bSTR3885 = ""
Dim bSTR3886
bSTR3886 = ""
Dim boolean1943
settingRepository1.GetAttrInfo "PARTICLEFLUENCERATE_ExtraSmall", bSTR3885, bSTR3886, boolean1943
'--------------------------------------------------
' Parameter 1 : (String) "PARTICLEFLUENCERATE_ExtraSmall"
' Parameter 2 : (String) "Default value"
' Parameter 3 : (String) "Unlocked"
' Parameter 4 : (Boolean) False
'--------------------------------------------------

long1944 = settingRepository1.GetAttr("PARTICLEFLUENCERATE_Nanometric")
'--------------------------------------------------
' Parameter 1 : (String) "PARTICLEFLUENCERATE_Nanometric"
' Returned value : (Variant) (Long) 1
'--------------------------------------------------

Dim bSTR3887
bSTR3887 = ""
Dim bSTR3888
bSTR3888 = ""
Dim boolean1944
settingRepository1.GetAttrInfo "PARTICLEFLUENCERATE_Nanometric", bSTR3887, bSTR3888, boolean1944
'--------------------------------------------------
' Parameter 1 : (String) "PARTICLEFLUENCERATE_Nanometric"
' Parameter 2 : (String) "Default value"
' Parameter 3 : (String) "Unlocked"
' Parameter 4 : (Boolean) False
'--------------------------------------------------

long1945 = settingRepository1.GetAttr("ENERGYFLUENCE")
'--------------------------------------------------
' Parameter 1 : (String) "ENERGYFLUENCE"
' Returned value : (Variant) (Long) 1
'--------------------------------------------------

Dim bSTR3889
bSTR3889 = ""
Dim bSTR3890
bSTR3890 = ""
Dim boolean1945
settingRepository1.GetAttrInfo "ENERGYFLUENCE", bSTR3889, bSTR3890, boolean1945
'--------------------------------------------------
' Parameter 1 : (String) "ENERGYFLUENCE"
' Parameter 2 : (String) "Default value"
' Parameter 3 : (String) "Unlocked"
' Parameter 4 : (Boolean) False
'--------------------------------------------------

long1946 = settingRepository1.GetAttr("ENERGYFLUENCE_Large")
'--------------------------------------------------
' Parameter 1 : (String) "ENERGYFLUENCE_Large"
' Returned value : (Variant) (Long) 1
'--------------------------------------------------

Dim bSTR3891
bSTR3891 = ""
Dim bSTR3892
bSTR3892 = ""
Dim boolean1946
settingRepository1.GetAttrInfo "ENERGYFLUENCE_Large", bSTR3891, bSTR3892, boolean1946
'--------------------------------------------------
' Parameter 1 : (String) "ENERGYFLUENCE_Large"
' Parameter 2 : (String) "Default value"
' Parameter 3 : (String) "Unlocked"
' Parameter 4 : (Boolean) False
'--------------------------------------------------

long1947 = settingRepository1.GetAttr("ENERGYFLUENCE_ExtraLarge")
'--------------------------------------------------
' Parameter 1 : (String) "ENERGYFLUENCE_ExtraLarge"
' Returned value : (Variant) (Long) 1
'--------------------------------------------------

Dim bSTR3893
bSTR3893 = ""
Dim bSTR3894
bSTR3894 = ""
Dim boolean1947
settingRepository1.GetAttrInfo "ENERGYFLUENCE_ExtraLarge", bSTR3893, bSTR3894, boolean1947
'--------------------------------------------------
' Parameter 1 : (String) "ENERGYFLUENCE_ExtraLarge"
' Parameter 2 : (String) "Default value"
' Parameter 3 : (String) "Unlocked"
' Parameter 4 : (Boolean) False
'--------------------------------------------------

long1948 = settingRepository1.GetAttr("ENERGYFLUENCE_Small")
'--------------------------------------------------
' Parameter 1 : (String) "ENERGYFLUENCE_Small"
' Returned value : (Variant) (Long) 1
'--------------------------------------------------

Dim bSTR3895
bSTR3895 = ""
Dim bSTR3896
bSTR3896 = ""
Dim boolean1948
settingRepository1.GetAttrInfo "ENERGYFLUENCE_Small", bSTR3895, bSTR3896, boolean1948
'--------------------------------------------------
' Parameter 1 : (String) "ENERGYFLUENCE_Small"
' Parameter 2 : (String) "Default value"
' Parameter 3 : (String) "Unlocked"
' Parameter 4 : (Boolean) False
'--------------------------------------------------

long1949 = settingRepository1.GetAttr("ENERGYFLUENCE_ExtraSmall")
'--------------------------------------------------
' Parameter 1 : (String) "ENERGYFLUENCE_ExtraSmall"
' Returned value : (Variant) (Long) 1
'--------------------------------------------------

Dim bSTR3897
bSTR3897 = ""
Dim bSTR3898
bSTR3898 = ""
Dim boolean1949
settingRepository1.GetAttrInfo "ENERGYFLUENCE_ExtraSmall", bSTR3897, bSTR3898, boolean1949
'--------------------------------------------------
' Parameter 1 : (String) "ENERGYFLUENCE_ExtraSmall"
' Parameter 2 : (String) "Default value"
' Parameter 3 : (String) "Unlocked"
' Parameter 4 : (Boolean) False
'--------------------------------------------------

long1950 = settingRepository1.GetAttr("ENERGYFLUENCE_Nanometric")
'--------------------------------------------------
' Parameter 1 : (String) "ENERGYFLUENCE_Nanometric"
' Returned value : (Variant) (Long) 1
'--------------------------------------------------

Dim bSTR3899
bSTR3899 = ""
Dim bSTR3900
bSTR3900 = ""
Dim boolean1950
settingRepository1.GetAttrInfo "ENERGYFLUENCE_Nanometric", bSTR3899, bSTR3900, boolean1950
'--------------------------------------------------
' Parameter 1 : (String) "ENERGYFLUENCE_Nanometric"
' Parameter 2 : (String) "Default value"
' Parameter 3 : (String) "Unlocked"
' Parameter 4 : (Boolean) False
'--------------------------------------------------

long1951 = settingRepository1.GetAttr("CURRENTDENSITYOFPARTICLES")
'--------------------------------------------------
' Parameter 1 : (String) "CURRENTDENSITYOFPARTICLES"
' Returned value : (Variant) (Long) 1
'--------------------------------------------------

Dim bSTR3901
bSTR3901 = ""
Dim bSTR3902
bSTR3902 = ""
Dim boolean1951
settingRepository1.GetAttrInfo "CURRENTDENSITYOFPARTICLES", bSTR3901, bSTR3902, boolean1951
'--------------------------------------------------
' Parameter 1 : (String) "CURRENTDENSITYOFPARTICLES"
' Parameter 2 : (String) "Default value"
' Parameter 3 : (String) "Unlocked"
' Parameter 4 : (Boolean) False
'--------------------------------------------------

long1952 = settingRepository1.GetAttr("CURRENTDENSITYOFPARTICLES_Large")
'--------------------------------------------------
' Parameter 1 : (String) "CURRENTDENSITYOFPARTICLES_Large"
' Returned value : (Variant) (Long) 1
'--------------------------------------------------

Dim bSTR3903
bSTR3903 = ""
Dim bSTR3904
bSTR3904 = ""
Dim boolean1952
settingRepository1.GetAttrInfo "CURRENTDENSITYOFPARTICLES_Large", bSTR3903, bSTR3904, boolean1952
'--------------------------------------------------
' Parameter 1 : (String) "CURRENTDENSITYOFPARTICLES_Large"
' Parameter 2 : (String) "Default value"
' Parameter 3 : (String) "Unlocked"
' Parameter 4 : (Boolean) False
'--------------------------------------------------

long1953 = settingRepository1.GetAttr("CURRENTDENSITYOFPARTICLES_ExtraLarge")
'--------------------------------------------------
' Parameter 1 : (String) "CURRENTDENSITYOFPARTICLES_ExtraLarge"
' Returned value : (Variant) (Long) 1
'--------------------------------------------------

Dim bSTR3905
bSTR3905 = ""
Dim bSTR3906
bSTR3906 = ""
Dim boolean1953
settingRepository1.GetAttrInfo "CURRENTDENSITYOFPARTICLES_ExtraLarge", bSTR3905, bSTR3906, boolean1953
'--------------------------------------------------
' Parameter 1 : (String) "CURRENTDENSITYOFPARTICLES_ExtraLarge"
' Parameter 2 : (String) "Default value"
' Parameter 3 : (String) "Unlocked"
' Parameter 4 : (Boolean) False
'--------------------------------------------------

long1954 = settingRepository1.GetAttr("CURRENTDENSITYOFPARTICLES_Small")
'--------------------------------------------------
' Parameter 1 : (String) "CURRENTDENSITYOFPARTICLES_Small"
' Returned value : (Variant) (Long) 1
'--------------------------------------------------

Dim bSTR3907
bSTR3907 = ""
Dim bSTR3908
bSTR3908 = ""
Dim boolean1954
settingRepository1.GetAttrInfo "CURRENTDENSITYOFPARTICLES_Small", bSTR3907, bSTR3908, boolean1954
'--------------------------------------------------
' Parameter 1 : (String) "CURRENTDENSITYOFPARTICLES_Small"
' Parameter 2 : (String) "Default value"
' Parameter 3 : (String) "Unlocked"
' Parameter 4 : (Boolean) False
'--------------------------------------------------

long1955 = settingRepository1.GetAttr("CURRENTDENSITYOFPARTICLES_ExtraSmall")
'--------------------------------------------------
' Parameter 1 : (String) "CURRENTDENSITYOFPARTICLES_ExtraSmall"
' Returned value : (Variant) (Long) 1
'--------------------------------------------------

Dim bSTR3909
bSTR3909 = ""
Dim bSTR3910
bSTR3910 = ""
Dim boolean1955
settingRepository1.GetAttrInfo "CURRENTDENSITYOFPARTICLES_ExtraSmall", bSTR3909, bSTR3910, boolean1955
'--------------------------------------------------
' Parameter 1 : (String) "CURRENTDENSITYOFPARTICLES_ExtraSmall"
' Parameter 2 : (String) "Default value"
' Parameter 3 : (String) "Unlocked"
' Parameter 4 : (Boolean) False
'--------------------------------------------------

long1956 = settingRepository1.GetAttr("CURRENTDENSITYOFPARTICLES_Nanometric")
'--------------------------------------------------
' Parameter 1 : (String) "CURRENTDENSITYOFPARTICLES_Nanometric"
' Returned value : (Variant) (Long) 1
'--------------------------------------------------

Dim bSTR3911
bSTR3911 = ""
Dim bSTR3912
bSTR3912 = ""
Dim boolean1956
settingRepository1.GetAttrInfo "CURRENTDENSITYOFPARTICLES_Nanometric", bSTR3911, bSTR3912, boolean1956
'--------------------------------------------------
' Parameter 1 : (String) "CURRENTDENSITYOFPARTICLES_Nanometric"
' Parameter 2 : (String) "Default value"
' Parameter 3 : (String) "Unlocked"
' Parameter 4 : (Boolean) False
'--------------------------------------------------

long1957 = settingRepository1.GetAttr("MASSATTENUATIONCOEFFICIENT")
'--------------------------------------------------
' Parameter 1 : (String) "MASSATTENUATIONCOEFFICIENT"
' Returned value : (Variant) (Long) 1
'--------------------------------------------------

Dim bSTR3913
bSTR3913 = ""
Dim bSTR3914
bSTR3914 = ""
Dim boolean1957
settingRepository1.GetAttrInfo "MASSATTENUATIONCOEFFICIENT", bSTR3913, bSTR3914, boolean1957
'--------------------------------------------------
' Parameter 1 : (String) "MASSATTENUATIONCOEFFICIENT"
' Parameter 2 : (String) "Default value"
' Parameter 3 : (String) "Unlocked"
' Parameter 4 : (Boolean) False
'--------------------------------------------------

long1958 = settingRepository1.GetAttr("MASSATTENUATIONCOEFFICIENT_Large")
'--------------------------------------------------
' Parameter 1 : (String) "MASSATTENUATIONCOEFFICIENT_Large"
' Returned value : (Variant) (Long) 1
'--------------------------------------------------

Dim bSTR3915
bSTR3915 = ""
Dim bSTR3916
bSTR3916 = ""
Dim boolean1958
settingRepository1.GetAttrInfo "MASSATTENUATIONCOEFFICIENT_Large", bSTR3915, bSTR3916, boolean1958
'--------------------------------------------------
' Parameter 1 : (String) "MASSATTENUATIONCOEFFICIENT_Large"
' Parameter 2 : (String) "Default value"
' Parameter 3 : (String) "Unlocked"
' Parameter 4 : (Boolean) False
'--------------------------------------------------

long1959 = settingRepository1.GetAttr("MASSATTENUATIONCOEFFICIENT_ExtraLarge")
'--------------------------------------------------
' Parameter 1 : (String) "MASSATTENUATIONCOEFFICIENT_ExtraLarge"
' Returned value : (Variant) (Long) 1
'--------------------------------------------------

Dim bSTR3917
bSTR3917 = ""
Dim bSTR3918
bSTR3918 = ""
Dim boolean1959
settingRepository1.GetAttrInfo "MASSATTENUATIONCOEFFICIENT_ExtraLarge", bSTR3917, bSTR3918, boolean1959
'--------------------------------------------------
' Parameter 1 : (String) "MASSATTENUATIONCOEFFICIENT_ExtraLarge"
' Parameter 2 : (String) "Default value"
' Parameter 3 : (String) "Unlocked"
' Parameter 4 : (Boolean) False
'--------------------------------------------------

long1960 = settingRepository1.GetAttr("MASSATTENUATIONCOEFFICIENT_Small")
'--------------------------------------------------
' Parameter 1 : (String) "MASSATTENUATIONCOEFFICIENT_Small"
' Returned value : (Variant) (Long) 1
'--------------------------------------------------

Dim bSTR3919
bSTR3919 = ""
Dim bSTR3920
bSTR3920 = ""
Dim boolean1960
settingRepository1.GetAttrInfo "MASSATTENUATIONCOEFFICIENT_Small", bSTR3919, bSTR3920, boolean1960
'--------------------------------------------------
' Parameter 1 : (String) "MASSATTENUATIONCOEFFICIENT_Small"
' Parameter 2 : (String) "Default value"
' Parameter 3 : (String) "Unlocked"
' Parameter 4 : (Boolean) False
'--------------------------------------------------

long1961 = settingRepository1.GetAttr("MASSATTENUATIONCOEFFICIENT_ExtraSmall")
'--------------------------------------------------
' Parameter 1 : (String) "MASSATTENUATIONCOEFFICIENT_ExtraSmall"
' Returned value : (Variant) (Long) 1
'--------------------------------------------------

Dim bSTR3921
bSTR3921 = ""
Dim bSTR3922
bSTR3922 = ""
Dim boolean1961
settingRepository1.GetAttrInfo "MASSATTENUATIONCOEFFICIENT_ExtraSmall", bSTR3921, bSTR3922, boolean1961
'--------------------------------------------------
' Parameter 1 : (String) "MASSATTENUATIONCOEFFICIENT_ExtraSmall"
' Parameter 2 : (String) "Default value"
' Parameter 3 : (String) "Unlocked"
' Parameter 4 : (Boolean) False
'--------------------------------------------------

long1962 = settingRepository1.GetAttr("MASSATTENUATIONCOEFFICIENT_Nanometric")
'--------------------------------------------------
' Parameter 1 : (String) "MASSATTENUATIONCOEFFICIENT_Nanometric"
' Returned value : (Variant) (Long) 1
'--------------------------------------------------

Dim bSTR3923
bSTR3923 = ""
Dim bSTR3924
bSTR3924 = ""
Dim boolean1962
settingRepository1.GetAttrInfo "MASSATTENUATIONCOEFFICIENT_Nanometric", bSTR3923, bSTR3924, boolean1962
'--------------------------------------------------
' Parameter 1 : (String) "MASSATTENUATIONCOEFFICIENT_Nanometric"
' Parameter 2 : (String) "Default value"
' Parameter 3 : (String) "Unlocked"
' Parameter 4 : (Boolean) False
'--------------------------------------------------

long1963 = settingRepository1.GetAttr("ATOMICATTENUATIONCOEFFICIENT")
'--------------------------------------------------
' Parameter 1 : (String) "ATOMICATTENUATIONCOEFFICIENT"
' Returned value : (Variant) (Long) 1
'--------------------------------------------------

Dim bSTR3925
bSTR3925 = ""
Dim bSTR3926
bSTR3926 = ""
Dim boolean1963
settingRepository1.GetAttrInfo "ATOMICATTENUATIONCOEFFICIENT", bSTR3925, bSTR3926, boolean1963
'--------------------------------------------------
' Parameter 1 : (String) "ATOMICATTENUATIONCOEFFICIENT"
' Parameter 2 : (String) "Default value"
' Parameter 3 : (String) "Unlocked"
' Parameter 4 : (Boolean) False
'--------------------------------------------------

long1964 = settingRepository1.GetAttr("ATOMICATTENUATIONCOEFFICIENT_Large")
'--------------------------------------------------
' Parameter 1 : (String) "ATOMICATTENUATIONCOEFFICIENT_Large"
' Returned value : (Variant) (Long) 1
'--------------------------------------------------

Dim bSTR3927
bSTR3927 = ""
Dim bSTR3928
bSTR3928 = ""
Dim boolean1964
settingRepository1.GetAttrInfo "ATOMICATTENUATIONCOEFFICIENT_Large", bSTR3927, bSTR3928, boolean1964
'--------------------------------------------------
' Parameter 1 : (String) "ATOMICATTENUATIONCOEFFICIENT_Large"
' Parameter 2 : (String) "Default value"
' Parameter 3 : (String) "Unlocked"
' Parameter 4 : (Boolean) False
'--------------------------------------------------

long1965 = settingRepository1.GetAttr("ATOMICATTENUATIONCOEFFICIENT_ExtraLarge")
'--------------------------------------------------
' Parameter 1 : (String) "ATOMICATTENUATIONCOEFFICIENT_ExtraLarge"
' Returned value : (Variant) (Long) 1
'--------------------------------------------------

Dim bSTR3929
bSTR3929 = ""
Dim bSTR3930
bSTR3930 = ""
Dim boolean1965
settingRepository1.GetAttrInfo "ATOMICATTENUATIONCOEFFICIENT_ExtraLarge", bSTR3929, bSTR3930, boolean1965
'--------------------------------------------------
' Parameter 1 : (String) "ATOMICATTENUATIONCOEFFICIENT_ExtraLarge"
' Parameter 2 : (String) "Default value"
' Parameter 3 : (String) "Unlocked"
' Parameter 4 : (Boolean) False
'--------------------------------------------------

long1966 = settingRepository1.GetAttr("ATOMICATTENUATIONCOEFFICIENT_Small")
'--------------------------------------------------
' Parameter 1 : (String) "ATOMICATTENUATIONCOEFFICIENT_Small"
' Returned value : (Variant) (Long) 1
'--------------------------------------------------

Dim bSTR3931
bSTR3931 = ""
Dim bSTR3932
bSTR3932 = ""
Dim boolean1966
settingRepository1.GetAttrInfo "ATOMICATTENUATIONCOEFFICIENT_Small", bSTR3931, bSTR3932, boolean1966
'--------------------------------------------------
' Parameter 1 : (String) "ATOMICATTENUATIONCOEFFICIENT_Small"
' Parameter 2 : (String) "Default value"
' Parameter 3 : (String) "Unlocked"
' Parameter 4 : (Boolean) False
'--------------------------------------------------

long1967 = settingRepository1.GetAttr("ATOMICATTENUATIONCOEFFICIENT_ExtraSmall")
'--------------------------------------------------
' Parameter 1 : (String) "ATOMICATTENUATIONCOEFFICIENT_ExtraSmall"
' Returned value : (Variant) (Long) 1
'--------------------------------------------------

Dim bSTR3933
bSTR3933 = ""
Dim bSTR3934
bSTR3934 = ""
Dim boolean1967
settingRepository1.GetAttrInfo "ATOMICATTENUATIONCOEFFICIENT_ExtraSmall", bSTR3933, bSTR3934, boolean1967
'--------------------------------------------------
' Parameter 1 : (String) "ATOMICATTENUATIONCOEFFICIENT_ExtraSmall"
' Parameter 2 : (String) "Default value"
' Parameter 3 : (String) "Unlocked"
' Parameter 4 : (Boolean) False
'--------------------------------------------------

long1968 = settingRepository1.GetAttr("ATOMICATTENUATIONCOEFFICIENT_Nanometric")
'--------------------------------------------------
' Parameter 1 : (String) "ATOMICATTENUATIONCOEFFICIENT_Nanometric"
' Returned value : (Variant) (Long) 1
'--------------------------------------------------

Dim bSTR3935
bSTR3935 = ""
Dim bSTR3936
bSTR3936 = ""
Dim boolean1968
settingRepository1.GetAttrInfo "ATOMICATTENUATIONCOEFFICIENT_Nanometric", bSTR3935, bSTR3936, boolean1968
'--------------------------------------------------
' Parameter 1 : (String) "ATOMICATTENUATIONCOEFFICIENT_Nanometric"
' Parameter 2 : (String) "Default value"
' Parameter 3 : (String) "Unlocked"
' Parameter 4 : (Boolean) False
'--------------------------------------------------

long1969 = settingRepository1.GetAttr("TOTALLINEARSTOPPINGPOWER")
'--------------------------------------------------
' Parameter 1 : (String) "TOTALLINEARSTOPPINGPOWER"
' Returned value : (Variant) (Long) 1
'--------------------------------------------------

Dim bSTR3937
bSTR3937 = ""
Dim bSTR3938
bSTR3938 = ""
Dim boolean1969
settingRepository1.GetAttrInfo "TOTALLINEARSTOPPINGPOWER", bSTR3937, bSTR3938, boolean1969
'--------------------------------------------------
' Parameter 1 : (String) "TOTALLINEARSTOPPINGPOWER"
' Parameter 2 : (String) "Default value"
' Parameter 3 : (String) "Unlocked"
' Parameter 4 : (Boolean) False
'--------------------------------------------------

long1970 = settingRepository1.GetAttr("TOTALLINEARSTOPPINGPOWER_Large")
'--------------------------------------------------
' Parameter 1 : (String) "TOTALLINEARSTOPPINGPOWER_Large"
' Returned value : (Variant) (Long) 1
'--------------------------------------------------

Dim bSTR3939
bSTR3939 = ""
Dim bSTR3940
bSTR3940 = ""
Dim boolean1970
settingRepository1.GetAttrInfo "TOTALLINEARSTOPPINGPOWER_Large", bSTR3939, bSTR3940, boolean1970
'--------------------------------------------------
' Parameter 1 : (String) "TOTALLINEARSTOPPINGPOWER_Large"
' Parameter 2 : (String) "Default value"
' Parameter 3 : (String) "Unlocked"
' Parameter 4 : (Boolean) False
'--------------------------------------------------

long1971 = settingRepository1.GetAttr("TOTALLINEARSTOPPINGPOWER_ExtraLarge")
'--------------------------------------------------
' Parameter 1 : (String) "TOTALLINEARSTOPPINGPOWER_ExtraLarge"
' Returned value : (Variant) (Long) 1
'--------------------------------------------------

Dim bSTR3941
bSTR3941 = ""
Dim bSTR3942
bSTR3942 = ""
Dim boolean1971
settingRepository1.GetAttrInfo "TOTALLINEARSTOPPINGPOWER_ExtraLarge", bSTR3941, bSTR3942, boolean1971
'--------------------------------------------------
' Parameter 1 : (String) "TOTALLINEARSTOPPINGPOWER_ExtraLarge"
' Parameter 2 : (String) "Default value"
' Parameter 3 : (String) "Unlocked"
' Parameter 4 : (Boolean) False
'--------------------------------------------------

long1972 = settingRepository1.GetAttr("TOTALLINEARSTOPPINGPOWER_Small")
'--------------------------------------------------
' Parameter 1 : (String) "TOTALLINEARSTOPPINGPOWER_Small"
' Returned value : (Variant) (Long) 1
'--------------------------------------------------

Dim bSTR3943
bSTR3943 = ""
Dim bSTR3944
bSTR3944 = ""
Dim boolean1972
settingRepository1.GetAttrInfo "TOTALLINEARSTOPPINGPOWER_Small", bSTR3943, bSTR3944, boolean1972
'--------------------------------------------------
' Parameter 1 : (String) "TOTALLINEARSTOPPINGPOWER_Small"
' Parameter 2 : (String) "Default value"
' Parameter 3 : (String) "Unlocked"
' Parameter 4 : (Boolean) False
'--------------------------------------------------

long1973 = settingRepository1.GetAttr("TOTALLINEARSTOPPINGPOWER_ExtraSmall")
'--------------------------------------------------
' Parameter 1 : (String) "TOTALLINEARSTOPPINGPOWER_ExtraSmall"
' Returned value : (Variant) (Long) 1
'--------------------------------------------------

Dim bSTR3945
bSTR3945 = ""
Dim bSTR3946
bSTR3946 = ""
Dim boolean1973
settingRepository1.GetAttrInfo "TOTALLINEARSTOPPINGPOWER_ExtraSmall", bSTR3945, bSTR3946, boolean1973
'--------------------------------------------------
' Parameter 1 : (String) "TOTALLINEARSTOPPINGPOWER_ExtraSmall"
' Parameter 2 : (String) "Default value"
' Parameter 3 : (String) "Unlocked"
' Parameter 4 : (Boolean) False
'--------------------------------------------------

long1974 = settingRepository1.GetAttr("TOTALLINEARSTOPPINGPOWER_Nanometric")
'--------------------------------------------------
' Parameter 1 : (String) "TOTALLINEARSTOPPINGPOWER_Nanometric"
' Returned value : (Variant) (Long) 1
'--------------------------------------------------

Dim bSTR3947
bSTR3947 = ""
Dim bSTR3948
bSTR3948 = ""
Dim boolean1974
settingRepository1.GetAttrInfo "TOTALLINEARSTOPPINGPOWER_Nanometric", bSTR3947, bSTR3948, boolean1974
'--------------------------------------------------
' Parameter 1 : (String) "TOTALLINEARSTOPPINGPOWER_Nanometric"
' Parameter 2 : (String) "Default value"
' Parameter 3 : (String) "Unlocked"
' Parameter 4 : (Boolean) False
'--------------------------------------------------

long1975 = settingRepository1.GetAttr("TOTALATOMICSTOPPINGPOWER")
'--------------------------------------------------
' Parameter 1 : (String) "TOTALATOMICSTOPPINGPOWER"
' Returned value : (Variant) (Long) 1
'--------------------------------------------------

Dim bSTR3949
bSTR3949 = ""
Dim bSTR3950
bSTR3950 = ""
Dim boolean1975
settingRepository1.GetAttrInfo "TOTALATOMICSTOPPINGPOWER", bSTR3949, bSTR3950, boolean1975
'--------------------------------------------------
' Parameter 1 : (String) "TOTALATOMICSTOPPINGPOWER"
' Parameter 2 : (String) "Default value"
' Parameter 3 : (String) "Unlocked"
' Parameter 4 : (Boolean) False
'--------------------------------------------------

long1976 = settingRepository1.GetAttr("TOTALATOMICSTOPPINGPOWER_Large")
'--------------------------------------------------
' Parameter 1 : (String) "TOTALATOMICSTOPPINGPOWER_Large"
' Returned value : (Variant) (Long) 1
'--------------------------------------------------

Dim bSTR3951
bSTR3951 = ""
Dim bSTR3952
bSTR3952 = ""
Dim boolean1976
settingRepository1.GetAttrInfo "TOTALATOMICSTOPPINGPOWER_Large", bSTR3951, bSTR3952, boolean1976
'--------------------------------------------------
' Parameter 1 : (String) "TOTALATOMICSTOPPINGPOWER_Large"
' Parameter 2 : (String) "Default value"
' Parameter 3 : (String) "Unlocked"
' Parameter 4 : (Boolean) False
'--------------------------------------------------

long1977 = settingRepository1.GetAttr("TOTALATOMICSTOPPINGPOWER_ExtraLarge")
'--------------------------------------------------
' Parameter 1 : (String) "TOTALATOMICSTOPPINGPOWER_ExtraLarge"
' Returned value : (Variant) (Long) 1
'--------------------------------------------------

Dim bSTR3953
bSTR3953 = ""
Dim bSTR3954
bSTR3954 = ""
Dim boolean1977
settingRepository1.GetAttrInfo "TOTALATOMICSTOPPINGPOWER_ExtraLarge", bSTR3953, bSTR3954, boolean1977
'--------------------------------------------------
' Parameter 1 : (String) "TOTALATOMICSTOPPINGPOWER_ExtraLarge"
' Parameter 2 : (String) "Default value"
' Parameter 3 : (String) "Unlocked"
' Parameter 4 : (Boolean) False
'--------------------------------------------------

long1978 = settingRepository1.GetAttr("TOTALATOMICSTOPPINGPOWER_Small")
'--------------------------------------------------
' Parameter 1 : (String) "TOTALATOMICSTOPPINGPOWER_Small"
' Returned value : (Variant) (Long) 1
'--------------------------------------------------

Dim bSTR3955
bSTR3955 = ""
Dim bSTR3956
bSTR3956 = ""
Dim boolean1978
settingRepository1.GetAttrInfo "TOTALATOMICSTOPPINGPOWER_Small", bSTR3955, bSTR3956, boolean1978
'--------------------------------------------------
' Parameter 1 : (String) "TOTALATOMICSTOPPINGPOWER_Small"
' Parameter 2 : (String) "Default value"
' Parameter 3 : (String) "Unlocked"
' Parameter 4 : (Boolean) False
'--------------------------------------------------

long1979 = settingRepository1.GetAttr("TOTALATOMICSTOPPINGPOWER_ExtraSmall")
'--------------------------------------------------
' Parameter 1 : (String) "TOTALATOMICSTOPPINGPOWER_ExtraSmall"
' Returned value : (Variant) (Long) 1
'--------------------------------------------------

Dim bSTR3957
bSTR3957 = ""
Dim bSTR3958
bSTR3958 = ""
Dim boolean1979
settingRepository1.GetAttrInfo "TOTALATOMICSTOPPINGPOWER_ExtraSmall", bSTR3957, bSTR3958, boolean1979
'--------------------------------------------------
' Parameter 1 : (String) "TOTALATOMICSTOPPINGPOWER_ExtraSmall"
' Parameter 2 : (String) "Default value"
' Parameter 3 : (String) "Unlocked"
' Parameter 4 : (Boolean) False
'--------------------------------------------------

long1980 = settingRepository1.GetAttr("TOTALATOMICSTOPPINGPOWER_Nanometric")
'--------------------------------------------------
' Parameter 1 : (String) "TOTALATOMICSTOPPINGPOWER_Nanometric"
' Returned value : (Variant) (Long) 1
'--------------------------------------------------

Dim bSTR3959
bSTR3959 = ""
Dim bSTR3960
bSTR3960 = ""
Dim boolean1980
settingRepository1.GetAttrInfo "TOTALATOMICSTOPPINGPOWER_Nanometric", bSTR3959, bSTR3960, boolean1980
'--------------------------------------------------
' Parameter 1 : (String) "TOTALATOMICSTOPPINGPOWER_Nanometric"
' Parameter 2 : (String) "Default value"
' Parameter 3 : (String) "Unlocked"
' Parameter 4 : (Boolean) False
'--------------------------------------------------

long1981 = settingRepository1.GetAttr("TOTALMASSSTOPPINGPOWER")
'--------------------------------------------------
' Parameter 1 : (String) "TOTALMASSSTOPPINGPOWER"
' Returned value : (Variant) (Long) 1
'--------------------------------------------------

Dim bSTR3961
bSTR3961 = ""
Dim bSTR3962
bSTR3962 = ""
Dim boolean1981
settingRepository1.GetAttrInfo "TOTALMASSSTOPPINGPOWER", bSTR3961, bSTR3962, boolean1981
'--------------------------------------------------
' Parameter 1 : (String) "TOTALMASSSTOPPINGPOWER"
' Parameter 2 : (String) "Default value"
' Parameter 3 : (String) "Unlocked"
' Parameter 4 : (Boolean) False
'--------------------------------------------------

long1982 = settingRepository1.GetAttr("TOTALMASSSTOPPINGPOWER_Large")
'--------------------------------------------------
' Parameter 1 : (String) "TOTALMASSSTOPPINGPOWER_Large"
' Returned value : (Variant) (Long) 1
'--------------------------------------------------

Dim bSTR3963
bSTR3963 = ""
Dim bSTR3964
bSTR3964 = ""
Dim boolean1982
settingRepository1.GetAttrInfo "TOTALMASSSTOPPINGPOWER_Large", bSTR3963, bSTR3964, boolean1982
'--------------------------------------------------
' Parameter 1 : (String) "TOTALMASSSTOPPINGPOWER_Large"
' Parameter 2 : (String) "Default value"
' Parameter 3 : (String) "Unlocked"
' Parameter 4 : (Boolean) False
'--------------------------------------------------

long1983 = settingRepository1.GetAttr("TOTALMASSSTOPPINGPOWER_ExtraLarge")
'--------------------------------------------------
' Parameter 1 : (String) "TOTALMASSSTOPPINGPOWER_ExtraLarge"
' Returned value : (Variant) (Long) 1
'--------------------------------------------------

Dim bSTR3965
bSTR3965 = ""
Dim bSTR3966
bSTR3966 = ""
Dim boolean1983
settingRepository1.GetAttrInfo "TOTALMASSSTOPPINGPOWER_ExtraLarge", bSTR3965, bSTR3966, boolean1983
'--------------------------------------------------
' Parameter 1 : (String) "TOTALMASSSTOPPINGPOWER_ExtraLarge"
' Parameter 2 : (String) "Default value"
' Parameter 3 : (String) "Unlocked"
' Parameter 4 : (Boolean) False
'--------------------------------------------------

long1984 = settingRepository1.GetAttr("TOTALMASSSTOPPINGPOWER_Small")
'--------------------------------------------------
' Parameter 1 : (String) "TOTALMASSSTOPPINGPOWER_Small"
' Returned value : (Variant) (Long) 1
'--------------------------------------------------

Dim bSTR3967
bSTR3967 = ""
Dim bSTR3968
bSTR3968 = ""
Dim boolean1984
settingRepository1.GetAttrInfo "TOTALMASSSTOPPINGPOWER_Small", bSTR3967, bSTR3968, boolean1984
'--------------------------------------------------
' Parameter 1 : (String) "TOTALMASSSTOPPINGPOWER_Small"
' Parameter 2 : (String) "Default value"
' Parameter 3 : (String) "Unlocked"
' Parameter 4 : (Boolean) False
'--------------------------------------------------

long1985 = settingRepository1.GetAttr("TOTALMASSSTOPPINGPOWER_ExtraSmall")
'--------------------------------------------------
' Parameter 1 : (String) "TOTALMASSSTOPPINGPOWER_ExtraSmall"
' Returned value : (Variant) (Long) 1
'--------------------------------------------------

Dim bSTR3969
bSTR3969 = ""
Dim bSTR3970
bSTR3970 = ""
Dim boolean1985
settingRepository1.GetAttrInfo "TOTALMASSSTOPPINGPOWER_ExtraSmall", bSTR3969, bSTR3970, boolean1985
'--------------------------------------------------
' Parameter 1 : (String) "TOTALMASSSTOPPINGPOWER_ExtraSmall"
' Parameter 2 : (String) "Default value"
' Parameter 3 : (String) "Unlocked"
' Parameter 4 : (Boolean) False
'--------------------------------------------------

long1986 = settingRepository1.GetAttr("TOTALMASSSTOPPINGPOWER_Nanometric")
'--------------------------------------------------
' Parameter 1 : (String) "TOTALMASSSTOPPINGPOWER_Nanometric"
' Returned value : (Variant) (Long) 1
'--------------------------------------------------

Dim bSTR3971
bSTR3971 = ""
Dim bSTR3972
bSTR3972 = ""
Dim boolean1986
settingRepository1.GetAttrInfo "TOTALMASSSTOPPINGPOWER_Nanometric", bSTR3971, bSTR3972, boolean1986
'--------------------------------------------------
' Parameter 1 : (String) "TOTALMASSSTOPPINGPOWER_Nanometric"
' Parameter 2 : (String) "Default value"
' Parameter 3 : (String) "Unlocked"
' Parameter 4 : (Boolean) False
'--------------------------------------------------

long1987 = settingRepository1.GetAttr("MEANMASSRANGE")
'--------------------------------------------------
' Parameter 1 : (String) "MEANMASSRANGE"
' Returned value : (Variant) (Long) 1
'--------------------------------------------------

Dim bSTR3973
bSTR3973 = ""
Dim bSTR3974
bSTR3974 = ""
Dim boolean1987
settingRepository1.GetAttrInfo "MEANMASSRANGE", bSTR3973, bSTR3974, boolean1987
'--------------------------------------------------
' Parameter 1 : (String) "MEANMASSRANGE"
' Parameter 2 : (String) "Default value"
' Parameter 3 : (String) "Unlocked"
' Parameter 4 : (Boolean) False
'--------------------------------------------------

long1988 = settingRepository1.GetAttr("MEANMASSRANGE_Large")
'--------------------------------------------------
' Parameter 1 : (String) "MEANMASSRANGE_Large"
' Returned value : (Variant) (Long) 1
'--------------------------------------------------

Dim bSTR3975
bSTR3975 = ""
Dim bSTR3976
bSTR3976 = ""
Dim boolean1988
settingRepository1.GetAttrInfo "MEANMASSRANGE_Large", bSTR3975, bSTR3976, boolean1988
'--------------------------------------------------
' Parameter 1 : (String) "MEANMASSRANGE_Large"
' Parameter 2 : (String) "Default value"
' Parameter 3 : (String) "Unlocked"
' Parameter 4 : (Boolean) False
'--------------------------------------------------

long1989 = settingRepository1.GetAttr("MEANMASSRANGE_ExtraLarge")
'--------------------------------------------------
' Parameter 1 : (String) "MEANMASSRANGE_ExtraLarge"
' Returned value : (Variant) (Long) 1
'--------------------------------------------------

Dim bSTR3977
bSTR3977 = ""
Dim bSTR3978
bSTR3978 = ""
Dim boolean1989
settingRepository1.GetAttrInfo "MEANMASSRANGE_ExtraLarge", bSTR3977, bSTR3978, boolean1989
'--------------------------------------------------
' Parameter 1 : (String) "MEANMASSRANGE_ExtraLarge"
' Parameter 2 : (String) "Default value"
' Parameter 3 : (String) "Unlocked"
' Parameter 4 : (Boolean) False
'--------------------------------------------------

long1990 = settingRepository1.GetAttr("MEANMASSRANGE_Small")
'--------------------------------------------------
' Parameter 1 : (String) "MEANMASSRANGE_Small"
' Returned value : (Variant) (Long) 1
'--------------------------------------------------

Dim bSTR3979
bSTR3979 = ""
Dim bSTR3980
bSTR3980 = ""
Dim boolean1990
settingRepository1.GetAttrInfo "MEANMASSRANGE_Small", bSTR3979, bSTR3980, boolean1990
'--------------------------------------------------
' Parameter 1 : (String) "MEANMASSRANGE_Small"
' Parameter 2 : (String) "Default value"
' Parameter 3 : (String) "Unlocked"
' Parameter 4 : (Boolean) False
'--------------------------------------------------

long1991 = settingRepository1.GetAttr("MEANMASSRANGE_ExtraSmall")
'--------------------------------------------------
' Parameter 1 : (String) "MEANMASSRANGE_ExtraSmall"
' Returned value : (Variant) (Long) 1
'--------------------------------------------------

Dim bSTR3981
bSTR3981 = ""
Dim bSTR3982
bSTR3982 = ""
Dim boolean1991
settingRepository1.GetAttrInfo "MEANMASSRANGE_ExtraSmall", bSTR3981, bSTR3982, boolean1991
'--------------------------------------------------
' Parameter 1 : (String) "MEANMASSRANGE_ExtraSmall"
' Parameter 2 : (String) "Default value"
' Parameter 3 : (String) "Unlocked"
' Parameter 4 : (Boolean) False
'--------------------------------------------------

long1992 = settingRepository1.GetAttr("MEANMASSRANGE_Nanometric")
'--------------------------------------------------
' Parameter 1 : (String) "MEANMASSRANGE_Nanometric"
' Returned value : (Variant) (Long) 1
'--------------------------------------------------

Dim bSTR3983
bSTR3983 = ""
Dim bSTR3984
bSTR3984 = ""
Dim boolean1992
settingRepository1.GetAttrInfo "MEANMASSRANGE_Nanometric", bSTR3983, bSTR3984, boolean1992
'--------------------------------------------------
' Parameter 1 : (String) "MEANMASSRANGE_Nanometric"
' Parameter 2 : (String) "Default value"
' Parameter 3 : (String) "Unlocked"
' Parameter 4 : (Boolean) False
'--------------------------------------------------

long1993 = settingRepository1.GetAttr("LINEARIONIZATION")
'--------------------------------------------------
' Parameter 1 : (String) "LINEARIONIZATION"
' Returned value : (Variant) (Long) 1
'--------------------------------------------------

Dim bSTR3985
bSTR3985 = ""
Dim bSTR3986
bSTR3986 = ""
Dim boolean1993
settingRepository1.GetAttrInfo "LINEARIONIZATION", bSTR3985, bSTR3986, boolean1993
'--------------------------------------------------
' Parameter 1 : (String) "LINEARIONIZATION"
' Parameter 2 : (String) "Default value"
' Parameter 3 : (String) "Unlocked"
' Parameter 4 : (Boolean) False
'--------------------------------------------------

long1994 = settingRepository1.GetAttr("LINEARIONIZATION_Large")
'--------------------------------------------------
' Parameter 1 : (String) "LINEARIONIZATION_Large"
' Returned value : (Variant) (Long) 1
'--------------------------------------------------

Dim bSTR3987
bSTR3987 = ""
Dim bSTR3988
bSTR3988 = ""
Dim boolean1994
settingRepository1.GetAttrInfo "LINEARIONIZATION_Large", bSTR3987, bSTR3988, boolean1994
'--------------------------------------------------
' Parameter 1 : (String) "LINEARIONIZATION_Large"
' Parameter 2 : (String) "Default value"
' Parameter 3 : (String) "Unlocked"
' Parameter 4 : (Boolean) False
'--------------------------------------------------

long1995 = settingRepository1.GetAttr("LINEARIONIZATION_ExtraLarge")
'--------------------------------------------------
' Parameter 1 : (String) "LINEARIONIZATION_ExtraLarge"
' Returned value : (Variant) (Long) 1
'--------------------------------------------------

Dim bSTR3989
bSTR3989 = ""
Dim bSTR3990
bSTR3990 = ""
Dim boolean1995
settingRepository1.GetAttrInfo "LINEARIONIZATION_ExtraLarge", bSTR3989, bSTR3990, boolean1995
'--------------------------------------------------
' Parameter 1 : (String) "LINEARIONIZATION_ExtraLarge"
' Parameter 2 : (String) "Default value"
' Parameter 3 : (String) "Unlocked"
' Parameter 4 : (Boolean) False
'--------------------------------------------------

long1996 = settingRepository1.GetAttr("LINEARIONIZATION_Small")
'--------------------------------------------------
' Parameter 1 : (String) "LINEARIONIZATION_Small"
' Returned value : (Variant) (Long) 1
'--------------------------------------------------

Dim bSTR3991
bSTR3991 = ""
Dim bSTR3992
bSTR3992 = ""
Dim boolean1996
settingRepository1.GetAttrInfo "LINEARIONIZATION_Small", bSTR3991, bSTR3992, boolean1996
'--------------------------------------------------
' Parameter 1 : (String) "LINEARIONIZATION_Small"
' Parameter 2 : (String) "Default value"
' Parameter 3 : (String) "Unlocked"
' Parameter 4 : (Boolean) False
'--------------------------------------------------

long1997 = settingRepository1.GetAttr("LINEARIONIZATION_ExtraSmall")
'--------------------------------------------------
' Parameter 1 : (String) "LINEARIONIZATION_ExtraSmall"
' Returned value : (Variant) (Long) 1
'--------------------------------------------------

Dim bSTR3993
bSTR3993 = ""
Dim bSTR3994
bSTR3994 = ""
Dim boolean1997
settingRepository1.GetAttrInfo "LINEARIONIZATION_ExtraSmall", bSTR3993, bSTR3994, boolean1997
'--------------------------------------------------
' Parameter 1 : (String) "LINEARIONIZATION_ExtraSmall"
' Parameter 2 : (String) "Default value"
' Parameter 3 : (String) "Unlocked"
' Parameter 4 : (Boolean) False
'--------------------------------------------------

long1998 = settingRepository1.GetAttr("LINEARIONIZATION_Nanometric")
'--------------------------------------------------
' Parameter 1 : (String) "LINEARIONIZATION_Nanometric"
' Returned value : (Variant) (Long) 1
'--------------------------------------------------

Dim bSTR3995
bSTR3995 = ""
Dim bSTR3996
bSTR3996 = ""
Dim boolean1998
settingRepository1.GetAttrInfo "LINEARIONIZATION_Nanometric", bSTR3995, bSTR3996, boolean1998
'--------------------------------------------------
' Parameter 1 : (String) "LINEARIONIZATION_Nanometric"
' Parameter 2 : (String) "Default value"
' Parameter 3 : (String) "Unlocked"
' Parameter 4 : (Boolean) False
'--------------------------------------------------

long1999 = settingRepository1.GetAttr("MOBILITY")
'--------------------------------------------------
' Parameter 1 : (String) "MOBILITY"
' Returned value : (Variant) (Long) 1
'--------------------------------------------------

Dim bSTR3997
bSTR3997 = ""
Dim bSTR3998
bSTR3998 = ""
Dim boolean1999
settingRepository1.GetAttrInfo "MOBILITY", bSTR3997, bSTR3998, boolean1999
'--------------------------------------------------
' Parameter 1 : (String) "MOBILITY"
' Parameter 2 : (String) "Default value"
' Parameter 3 : (String) "Unlocked"
' Parameter 4 : (Boolean) False
'--------------------------------------------------

long2000 = settingRepository1.GetAttr("MOBILITY_Large")
'--------------------------------------------------
' Parameter 1 : (String) "MOBILITY_Large"
' Returned value : (Variant) (Long) 1
'--------------------------------------------------

Dim bSTR3999
bSTR3999 = ""
Dim bSTR4000
bSTR4000 = ""
Dim boolean2000
settingRepository1.GetAttrInfo "MOBILITY_Large", bSTR3999, bSTR4000, boolean2000
'--------------------------------------------------
' Parameter 1 : (String) "MOBILITY_Large"
' Parameter 2 : (String) "Default value"
' Parameter 3 : (String) "Unlocked"
' Parameter 4 : (Boolean) False
'--------------------------------------------------

long2001 = settingRepository1.GetAttr("MOBILITY_ExtraLarge")
'--------------------------------------------------
' Parameter 1 : (String) "MOBILITY_ExtraLarge"
' Returned value : (Variant) (Long) 1
'--------------------------------------------------

Dim bSTR4001
bSTR4001 = ""
Dim bSTR4002
bSTR4002 = ""
Dim boolean2001
settingRepository1.GetAttrInfo "MOBILITY_ExtraLarge", bSTR4001, bSTR4002, boolean2001
'--------------------------------------------------
' Parameter 1 : (String) "MOBILITY_ExtraLarge"
' Parameter 2 : (String) "Default value"
' Parameter 3 : (String) "Unlocked"
' Parameter 4 : (Boolean) False
'--------------------------------------------------

long2002 = settingRepository1.GetAttr("MOBILITY_Small")
'--------------------------------------------------
' Parameter 1 : (String) "MOBILITY_Small"
' Returned value : (Variant) (Long) 1
'--------------------------------------------------

Dim bSTR4003
bSTR4003 = ""
Dim bSTR4004
bSTR4004 = ""
Dim boolean2002
settingRepository1.GetAttrInfo "MOBILITY_Small", bSTR4003, bSTR4004, boolean2002
'--------------------------------------------------
' Parameter 1 : (String) "MOBILITY_Small"
' Parameter 2 : (String) "Default value"
' Parameter 3 : (String) "Unlocked"
' Parameter 4 : (Boolean) False
'--------------------------------------------------

long2003 = settingRepository1.GetAttr("MOBILITY_ExtraSmall")
'--------------------------------------------------
' Parameter 1 : (String) "MOBILITY_ExtraSmall"
' Returned value : (Variant) (Long) 1
'--------------------------------------------------

Dim bSTR4005
bSTR4005 = ""
Dim bSTR4006
bSTR4006 = ""
Dim boolean2003
settingRepository1.GetAttrInfo "MOBILITY_ExtraSmall", bSTR4005, bSTR4006, boolean2003
'--------------------------------------------------
' Parameter 1 : (String) "MOBILITY_ExtraSmall"
' Parameter 2 : (String) "Default value"
' Parameter 3 : (String) "Unlocked"
' Parameter 4 : (Boolean) False
'--------------------------------------------------

long2004 = settingRepository1.GetAttr("MOBILITY_Nanometric")
'--------------------------------------------------
' Parameter 1 : (String) "MOBILITY_Nanometric"
' Returned value : (Variant) (Long) 1
'--------------------------------------------------

Dim bSTR4007
bSTR4007 = ""
Dim bSTR4008
bSTR4008 = ""
Dim boolean2004
settingRepository1.GetAttrInfo "MOBILITY_Nanometric", bSTR4007, bSTR4008, boolean2004
'--------------------------------------------------
' Parameter 1 : (String) "MOBILITY_Nanometric"
' Parameter 2 : (String) "Default value"
' Parameter 3 : (String) "Unlocked"
' Parameter 4 : (Boolean) False
'--------------------------------------------------

long2005 = settingRepository1.GetAttr("RECOMBINATIONCOEFFICIENT")
'--------------------------------------------------
' Parameter 1 : (String) "RECOMBINATIONCOEFFICIENT"
' Returned value : (Variant) (Long) 1
'--------------------------------------------------

Dim bSTR4009
bSTR4009 = ""
Dim bSTR4010
bSTR4010 = ""
Dim boolean2005
settingRepository1.GetAttrInfo "RECOMBINATIONCOEFFICIENT", bSTR4009, bSTR4010, boolean2005
'--------------------------------------------------
' Parameter 1 : (String) "RECOMBINATIONCOEFFICIENT"
' Parameter 2 : (String) "Default value"
' Parameter 3 : (String) "Unlocked"
' Parameter 4 : (Boolean) False
'--------------------------------------------------

long2006 = settingRepository1.GetAttr("RECOMBINATIONCOEFFICIENT_Large")
'--------------------------------------------------
' Parameter 1 : (String) "RECOMBINATIONCOEFFICIENT_Large"
' Returned value : (Variant) (Long) 1
'--------------------------------------------------

Dim bSTR4011
bSTR4011 = ""
Dim bSTR4012
bSTR4012 = ""
Dim boolean2006
settingRepository1.GetAttrInfo "RECOMBINATIONCOEFFICIENT_Large", bSTR4011, bSTR4012, boolean2006
'--------------------------------------------------
' Parameter 1 : (String) "RECOMBINATIONCOEFFICIENT_Large"
' Parameter 2 : (String) "Default value"
' Parameter 3 : (String) "Unlocked"
' Parameter 4 : (Boolean) False
'--------------------------------------------------

long2007 = settingRepository1.GetAttr("RECOMBINATIONCOEFFICIENT_ExtraLarge")
'--------------------------------------------------
' Parameter 1 : (String) "RECOMBINATIONCOEFFICIENT_ExtraLarge"
' Returned value : (Variant) (Long) 1
'--------------------------------------------------

Dim bSTR4013
bSTR4013 = ""
Dim bSTR4014
bSTR4014 = ""
Dim boolean2007
settingRepository1.GetAttrInfo "RECOMBINATIONCOEFFICIENT_ExtraLarge", bSTR4013, bSTR4014, boolean2007
'--------------------------------------------------
' Parameter 1 : (String) "RECOMBINATIONCOEFFICIENT_ExtraLarge"
' Parameter 2 : (String) "Default value"
' Parameter 3 : (String) "Unlocked"
' Parameter 4 : (Boolean) False
'--------------------------------------------------

long2008 = settingRepository1.GetAttr("RECOMBINATIONCOEFFICIENT_Small")
'--------------------------------------------------
' Parameter 1 : (String) "RECOMBINATIONCOEFFICIENT_Small"
' Returned value : (Variant) (Long) 1
'--------------------------------------------------

Dim bSTR4015
bSTR4015 = ""
Dim bSTR4016
bSTR4016 = ""
Dim boolean2008
settingRepository1.GetAttrInfo "RECOMBINATIONCOEFFICIENT_Small", bSTR4015, bSTR4016, boolean2008
'--------------------------------------------------
' Parameter 1 : (String) "RECOMBINATIONCOEFFICIENT_Small"
' Parameter 2 : (String) "Default value"
' Parameter 3 : (String) "Unlocked"
' Parameter 4 : (Boolean) False
'--------------------------------------------------

long2009 = settingRepository1.GetAttr("RECOMBINATIONCOEFFICIENT_ExtraSmall")
'--------------------------------------------------
' Parameter 1 : (String) "RECOMBINATIONCOEFFICIENT_ExtraSmall"
' Returned value : (Variant) (Long) 1
'--------------------------------------------------

Dim bSTR4017
bSTR4017 = ""
Dim bSTR4018
bSTR4018 = ""
Dim boolean2009
settingRepository1.GetAttrInfo "RECOMBINATIONCOEFFICIENT_ExtraSmall", bSTR4017, bSTR4018, boolean2009
'--------------------------------------------------
' Parameter 1 : (String) "RECOMBINATIONCOEFFICIENT_ExtraSmall"
' Parameter 2 : (String) "Default value"
' Parameter 3 : (String) "Unlocked"
' Parameter 4 : (Boolean) False
'--------------------------------------------------

long2010 = settingRepository1.GetAttr("RECOMBINATIONCOEFFICIENT_Nanometric")
'--------------------------------------------------
' Parameter 1 : (String) "RECOMBINATIONCOEFFICIENT_Nanometric"
' Returned value : (Variant) (Long) 1
'--------------------------------------------------

Dim bSTR4019
bSTR4019 = ""
Dim bSTR4020
bSTR4020 = ""
Dim boolean2010
settingRepository1.GetAttrInfo "RECOMBINATIONCOEFFICIENT_Nanometric", bSTR4019, bSTR4020, boolean2010
'--------------------------------------------------
' Parameter 1 : (String) "RECOMBINATIONCOEFFICIENT_Nanometric"
' Parameter 2 : (String) "Default value"
' Parameter 3 : (String) "Unlocked"
' Parameter 4 : (Boolean) False
'--------------------------------------------------

long2011 = settingRepository1.GetAttr("NEUTRONFLUENCERATE")
'--------------------------------------------------
' Parameter 1 : (String) "NEUTRONFLUENCERATE"
' Returned value : (Variant) (Long) 1
'--------------------------------------------------

Dim bSTR4021
bSTR4021 = ""
Dim bSTR4022
bSTR4022 = ""
Dim boolean2011
settingRepository1.GetAttrInfo "NEUTRONFLUENCERATE", bSTR4021, bSTR4022, boolean2011
'--------------------------------------------------
' Parameter 1 : (String) "NEUTRONFLUENCERATE"
' Parameter 2 : (String) "Default value"
' Parameter 3 : (String) "Unlocked"
' Parameter 4 : (Boolean) False
'--------------------------------------------------

long2012 = settingRepository1.GetAttr("NEUTRONFLUENCERATE_Large")
'--------------------------------------------------
' Parameter 1 : (String) "NEUTRONFLUENCERATE_Large"
' Returned value : (Variant) (Long) 1
'--------------------------------------------------

Dim bSTR4023
bSTR4023 = ""
Dim bSTR4024
bSTR4024 = ""
Dim boolean2012
settingRepository1.GetAttrInfo "NEUTRONFLUENCERATE_Large", bSTR4023, bSTR4024, boolean2012
'--------------------------------------------------
' Parameter 1 : (String) "NEUTRONFLUENCERATE_Large"
' Parameter 2 : (String) "Default value"
' Parameter 3 : (String) "Unlocked"
' Parameter 4 : (Boolean) False
'--------------------------------------------------

long2013 = settingRepository1.GetAttr("NEUTRONFLUENCERATE_ExtraLarge")
'--------------------------------------------------
' Parameter 1 : (String) "NEUTRONFLUENCERATE_ExtraLarge"
' Returned value : (Variant) (Long) 1
'--------------------------------------------------

Dim bSTR4025
bSTR4025 = ""
Dim bSTR4026
bSTR4026 = ""
Dim boolean2013
settingRepository1.GetAttrInfo "NEUTRONFLUENCERATE_ExtraLarge", bSTR4025, bSTR4026, boolean2013
'--------------------------------------------------
' Parameter 1 : (String) "NEUTRONFLUENCERATE_ExtraLarge"
' Parameter 2 : (String) "Default value"
' Parameter 3 : (String) "Unlocked"
' Parameter 4 : (Boolean) False
'--------------------------------------------------

long2014 = settingRepository1.GetAttr("NEUTRONFLUENCERATE_Small")
'--------------------------------------------------
' Parameter 1 : (String) "NEUTRONFLUENCERATE_Small"
' Returned value : (Variant) (Long) 1
'--------------------------------------------------

Dim bSTR4027
bSTR4027 = ""
Dim bSTR4028
bSTR4028 = ""
Dim boolean2014
settingRepository1.GetAttrInfo "NEUTRONFLUENCERATE_Small", bSTR4027, bSTR4028, boolean2014
'--------------------------------------------------
' Parameter 1 : (String) "NEUTRONFLUENCERATE_Small"
' Parameter 2 : (String) "Default value"
' Parameter 3 : (String) "Unlocked"
' Parameter 4 : (Boolean) False
'--------------------------------------------------

long2015 = settingRepository1.GetAttr("NEUTRONFLUENCERATE_ExtraSmall")
'--------------------------------------------------
' Parameter 1 : (String) "NEUTRONFLUENCERATE_ExtraSmall"
' Returned value : (Variant) (Long) 1
'--------------------------------------------------

Dim bSTR4029
bSTR4029 = ""
Dim bSTR4030
bSTR4030 = ""
Dim boolean2015
settingRepository1.GetAttrInfo "NEUTRONFLUENCERATE_ExtraSmall", bSTR4029, bSTR4030, boolean2015
'--------------------------------------------------
' Parameter 1 : (String) "NEUTRONFLUENCERATE_ExtraSmall"
' Parameter 2 : (String) "Default value"
' Parameter 3 : (String) "Unlocked"
' Parameter 4 : (Boolean) False
'--------------------------------------------------

long2016 = settingRepository1.GetAttr("NEUTRONFLUENCERATE_Nanometric")
'--------------------------------------------------
' Parameter 1 : (String) "NEUTRONFLUENCERATE_Nanometric"
' Returned value : (Variant) (Long) 1
'--------------------------------------------------

Dim bSTR4031
bSTR4031 = ""
Dim bSTR4032
bSTR4032 = ""
Dim boolean2016
settingRepository1.GetAttrInfo "NEUTRONFLUENCERATE_Nanometric", bSTR4031, bSTR4032, boolean2016
'--------------------------------------------------
' Parameter 1 : (String) "NEUTRONFLUENCERATE_Nanometric"
' Parameter 2 : (String) "Default value"
' Parameter 3 : (String) "Unlocked"
' Parameter 4 : (Boolean) False
'--------------------------------------------------

long2017 = settingRepository1.GetAttr("TOTALNEUTRONSOURCEDENSITY")
'--------------------------------------------------
' Parameter 1 : (String) "TOTALNEUTRONSOURCEDENSITY"
' Returned value : (Variant) (Long) 1
'--------------------------------------------------

Dim bSTR4033
bSTR4033 = ""
Dim bSTR4034
bSTR4034 = ""
Dim boolean2017
settingRepository1.GetAttrInfo "TOTALNEUTRONSOURCEDENSITY", bSTR4033, bSTR4034, boolean2017
'--------------------------------------------------
' Parameter 1 : (String) "TOTALNEUTRONSOURCEDENSITY"
' Parameter 2 : (String) "Default value"
' Parameter 3 : (String) "Unlocked"
' Parameter 4 : (Boolean) False
'--------------------------------------------------

long2018 = settingRepository1.GetAttr("TOTALNEUTRONSOURCEDENSITY_Large")
'--------------------------------------------------
' Parameter 1 : (String) "TOTALNEUTRONSOURCEDENSITY_Large"
' Returned value : (Variant) (Long) 1
'--------------------------------------------------

Dim bSTR4035
bSTR4035 = ""
Dim bSTR4036
bSTR4036 = ""
Dim boolean2018
settingRepository1.GetAttrInfo "TOTALNEUTRONSOURCEDENSITY_Large", bSTR4035, bSTR4036, boolean2018
'--------------------------------------------------
' Parameter 1 : (String) "TOTALNEUTRONSOURCEDENSITY_Large"
' Parameter 2 : (String) "Default value"
' Parameter 3 : (String) "Unlocked"
' Parameter 4 : (Boolean) False
'--------------------------------------------------

long2019 = settingRepository1.GetAttr("TOTALNEUTRONSOURCEDENSITY_ExtraLarge")
'--------------------------------------------------
' Parameter 1 : (String) "TOTALNEUTRONSOURCEDENSITY_ExtraLarge"
' Returned value : (Variant) (Long) 1
'--------------------------------------------------

Dim bSTR4037
bSTR4037 = ""
Dim bSTR4038
bSTR4038 = ""
Dim boolean2019
settingRepository1.GetAttrInfo "TOTALNEUTRONSOURCEDENSITY_ExtraLarge", bSTR4037, bSTR4038, boolean2019
'--------------------------------------------------
' Parameter 1 : (String) "TOTALNEUTRONSOURCEDENSITY_ExtraLarge"
' Parameter 2 : (String) "Default value"
' Parameter 3 : (String) "Unlocked"
' Parameter 4 : (Boolean) False
'--------------------------------------------------

long2020 = settingRepository1.GetAttr("TOTALNEUTRONSOURCEDENSITY_Small")
'--------------------------------------------------
' Parameter 1 : (String) "TOTALNEUTRONSOURCEDENSITY_Small"
' Returned value : (Variant) (Long) 1
'--------------------------------------------------

Dim bSTR4039
bSTR4039 = ""
Dim bSTR4040
bSTR4040 = ""
Dim boolean2020
settingRepository1.GetAttrInfo "TOTALNEUTRONSOURCEDENSITY_Small", bSTR4039, bSTR4040, boolean2020
'--------------------------------------------------
' Parameter 1 : (String) "TOTALNEUTRONSOURCEDENSITY_Small"
' Parameter 2 : (String) "Default value"
' Parameter 3 : (String) "Unlocked"
' Parameter 4 : (Boolean) False
'--------------------------------------------------

long2021 = settingRepository1.GetAttr("TOTALNEUTRONSOURCEDENSITY_ExtraSmall")
'--------------------------------------------------
' Parameter 1 : (String) "TOTALNEUTRONSOURCEDENSITY_ExtraSmall"
' Returned value : (Variant) (Long) 1
'--------------------------------------------------

Dim bSTR4041
bSTR4041 = ""
Dim bSTR4042
bSTR4042 = ""
Dim boolean2021
settingRepository1.GetAttrInfo "TOTALNEUTRONSOURCEDENSITY_ExtraSmall", bSTR4041, bSTR4042, boolean2021
'--------------------------------------------------
' Parameter 1 : (String) "TOTALNEUTRONSOURCEDENSITY_ExtraSmall"
' Parameter 2 : (String) "Default value"
' Parameter 3 : (String) "Unlocked"
' Parameter 4 : (Boolean) False
'--------------------------------------------------

long2022 = settingRepository1.GetAttr("TOTALNEUTRONSOURCEDENSITY_Nanometric")
'--------------------------------------------------
' Parameter 1 : (String) "TOTALNEUTRONSOURCEDENSITY_Nanometric"
' Returned value : (Variant) (Long) 1
'--------------------------------------------------

Dim bSTR4043
bSTR4043 = ""
Dim bSTR4044
bSTR4044 = ""
Dim boolean2022
settingRepository1.GetAttrInfo "TOTALNEUTRONSOURCEDENSITY_Nanometric", bSTR4043, bSTR4044, boolean2022
'--------------------------------------------------
' Parameter 1 : (String) "TOTALNEUTRONSOURCEDENSITY_Nanometric"
' Parameter 2 : (String) "Default value"
' Parameter 3 : (String) "Unlocked"
' Parameter 4 : (Boolean) False
'--------------------------------------------------

long2023 = settingRepository1.GetAttr("SLOWINGDOWNDENSITY")
'--------------------------------------------------
' Parameter 1 : (String) "SLOWINGDOWNDENSITY"
' Returned value : (Variant) (Long) 1
'--------------------------------------------------

Dim bSTR4045
bSTR4045 = ""
Dim bSTR4046
bSTR4046 = ""
Dim boolean2023
settingRepository1.GetAttrInfo "SLOWINGDOWNDENSITY", bSTR4045, bSTR4046, boolean2023
'--------------------------------------------------
' Parameter 1 : (String) "SLOWINGDOWNDENSITY"
' Parameter 2 : (String) "Default value"
' Parameter 3 : (String) "Unlocked"
' Parameter 4 : (Boolean) False
'--------------------------------------------------

long2024 = settingRepository1.GetAttr("SLOWINGDOWNDENSITY_Large")
'--------------------------------------------------
' Parameter 1 : (String) "SLOWINGDOWNDENSITY_Large"
' Returned value : (Variant) (Long) 1
'--------------------------------------------------

Dim bSTR4047
bSTR4047 = ""
Dim bSTR4048
bSTR4048 = ""
Dim boolean2024
settingRepository1.GetAttrInfo "SLOWINGDOWNDENSITY_Large", bSTR4047, bSTR4048, boolean2024
'--------------------------------------------------
' Parameter 1 : (String) "SLOWINGDOWNDENSITY_Large"
' Parameter 2 : (String) "Default value"
' Parameter 3 : (String) "Unlocked"
' Parameter 4 : (Boolean) False
'--------------------------------------------------

long2025 = settingRepository1.GetAttr("SLOWINGDOWNDENSITY_ExtraLarge")
'--------------------------------------------------
' Parameter 1 : (String) "SLOWINGDOWNDENSITY_ExtraLarge"
' Returned value : (Variant) (Long) 1
'--------------------------------------------------

Dim bSTR4049
bSTR4049 = ""
Dim bSTR4050
bSTR4050 = ""
Dim boolean2025
settingRepository1.GetAttrInfo "SLOWINGDOWNDENSITY_ExtraLarge", bSTR4049, bSTR4050, boolean2025
'--------------------------------------------------
' Parameter 1 : (String) "SLOWINGDOWNDENSITY_ExtraLarge"
' Parameter 2 : (String) "Default value"
' Parameter 3 : (String) "Unlocked"
' Parameter 4 : (Boolean) False
'--------------------------------------------------

long2026 = settingRepository1.GetAttr("SLOWINGDOWNDENSITY_Small")
'--------------------------------------------------
' Parameter 1 : (String) "SLOWINGDOWNDENSITY_Small"
' Returned value : (Variant) (Long) 1
'--------------------------------------------------

Dim bSTR4051
bSTR4051 = ""
Dim bSTR4052
bSTR4052 = ""
Dim boolean2026
settingRepository1.GetAttrInfo "SLOWINGDOWNDENSITY_Small", bSTR4051, bSTR4052, boolean2026
'--------------------------------------------------
' Parameter 1 : (String) "SLOWINGDOWNDENSITY_Small"
' Parameter 2 : (String) "Default value"
' Parameter 3 : (String) "Unlocked"
' Parameter 4 : (Boolean) False
'--------------------------------------------------

long2027 = settingRepository1.GetAttr("SLOWINGDOWNDENSITY_ExtraSmall")
'--------------------------------------------------
' Parameter 1 : (String) "SLOWINGDOWNDENSITY_ExtraSmall"
' Returned value : (Variant) (Long) 1
'--------------------------------------------------

Dim bSTR4053
bSTR4053 = ""
Dim bSTR4054
bSTR4054 = ""
Dim boolean2027
settingRepository1.GetAttrInfo "SLOWINGDOWNDENSITY_ExtraSmall", bSTR4053, bSTR4054, boolean2027
'--------------------------------------------------
' Parameter 1 : (String) "SLOWINGDOWNDENSITY_ExtraSmall"
' Parameter 2 : (String) "Default value"
' Parameter 3 : (String) "Unlocked"
' Parameter 4 : (Boolean) False
'--------------------------------------------------

long2028 = settingRepository1.GetAttr("SLOWINGDOWNDENSITY_Nanometric")
'--------------------------------------------------
' Parameter 1 : (String) "SLOWINGDOWNDENSITY_Nanometric"
' Returned value : (Variant) (Long) 1
'--------------------------------------------------

Dim bSTR4055
bSTR4055 = ""
Dim bSTR4056
bSTR4056 = ""
Dim boolean2028
settingRepository1.GetAttrInfo "SLOWINGDOWNDENSITY_Nanometric", bSTR4055, bSTR4056, boolean2028
'--------------------------------------------------
' Parameter 1 : (String) "SLOWINGDOWNDENSITY_Nanometric"
' Parameter 2 : (String) "Default value"
' Parameter 3 : (String) "Unlocked"
' Parameter 4 : (Boolean) False
'--------------------------------------------------

long2029 = settingRepository1.GetAttr("ABSORBEDDOSE")
'--------------------------------------------------
' Parameter 1 : (String) "ABSORBEDDOSE"
' Returned value : (Variant) (Long) 1
'--------------------------------------------------

Dim bSTR4057
bSTR4057 = ""
Dim bSTR4058
bSTR4058 = ""
Dim boolean2029
settingRepository1.GetAttrInfo "ABSORBEDDOSE", bSTR4057, bSTR4058, boolean2029
'--------------------------------------------------
' Parameter 1 : (String) "ABSORBEDDOSE"
' Parameter 2 : (String) "Default value"
' Parameter 3 : (String) "Unlocked"
' Parameter 4 : (Boolean) False
'--------------------------------------------------

long2030 = settingRepository1.GetAttr("ABSORBEDDOSE_Large")
'--------------------------------------------------
' Parameter 1 : (String) "ABSORBEDDOSE_Large"
' Returned value : (Variant) (Long) 1
'--------------------------------------------------

Dim bSTR4059
bSTR4059 = ""
Dim bSTR4060
bSTR4060 = ""
Dim boolean2030
settingRepository1.GetAttrInfo "ABSORBEDDOSE_Large", bSTR4059, bSTR4060, boolean2030
'--------------------------------------------------
' Parameter 1 : (String) "ABSORBEDDOSE_Large"
' Parameter 2 : (String) "Default value"
' Parameter 3 : (String) "Unlocked"
' Parameter 4 : (Boolean) False
'--------------------------------------------------

long2031 = settingRepository1.GetAttr("ABSORBEDDOSE_ExtraLarge")
'--------------------------------------------------
' Parameter 1 : (String) "ABSORBEDDOSE_ExtraLarge"
' Returned value : (Variant) (Long) 1
'--------------------------------------------------

Dim bSTR4061
bSTR4061 = ""
Dim bSTR4062
bSTR4062 = ""
Dim boolean2031
settingRepository1.GetAttrInfo "ABSORBEDDOSE_ExtraLarge", bSTR4061, bSTR4062, boolean2031
'--------------------------------------------------
' Parameter 1 : (String) "ABSORBEDDOSE_ExtraLarge"
' Parameter 2 : (String) "Default value"
' Parameter 3 : (String) "Unlocked"
' Parameter 4 : (Boolean) False
'--------------------------------------------------

long2032 = settingRepository1.GetAttr("ABSORBEDDOSE_Small")
'--------------------------------------------------
' Parameter 1 : (String) "ABSORBEDDOSE_Small"
' Returned value : (Variant) (Long) 1
'--------------------------------------------------

Dim bSTR4063
bSTR4063 = ""
Dim bSTR4064
bSTR4064 = ""
Dim boolean2032
settingRepository1.GetAttrInfo "ABSORBEDDOSE_Small", bSTR4063, bSTR4064, boolean2032
'--------------------------------------------------
' Parameter 1 : (String) "ABSORBEDDOSE_Small"
' Parameter 2 : (String) "Default value"
' Parameter 3 : (String) "Unlocked"
' Parameter 4 : (Boolean) False
'--------------------------------------------------

long2033 = settingRepository1.GetAttr("ABSORBEDDOSE_ExtraSmall")
'--------------------------------------------------
' Parameter 1 : (String) "ABSORBEDDOSE_ExtraSmall"
' Returned value : (Variant) (Long) 1
'--------------------------------------------------

Dim bSTR4065
bSTR4065 = ""
Dim bSTR4066
bSTR4066 = ""
Dim boolean2033
settingRepository1.GetAttrInfo "ABSORBEDDOSE_ExtraSmall", bSTR4065, bSTR4066, boolean2033
'--------------------------------------------------
' Parameter 1 : (String) "ABSORBEDDOSE_ExtraSmall"
' Parameter 2 : (String) "Default value"
' Parameter 3 : (String) "Unlocked"
' Parameter 4 : (Boolean) False
'--------------------------------------------------

long2034 = settingRepository1.GetAttr("ABSORBEDDOSE_Nanometric")
'--------------------------------------------------
' Parameter 1 : (String) "ABSORBEDDOSE_Nanometric"
' Returned value : (Variant) (Long) 1
'--------------------------------------------------

Dim bSTR4067
bSTR4067 = ""
Dim bSTR4068
bSTR4068 = ""
Dim boolean2034
settingRepository1.GetAttrInfo "ABSORBEDDOSE_Nanometric", bSTR4067, bSTR4068, boolean2034
'--------------------------------------------------
' Parameter 1 : (String) "ABSORBEDDOSE_Nanometric"
' Parameter 2 : (String) "Default value"
' Parameter 3 : (String) "Unlocked"
' Parameter 4 : (Boolean) False
'--------------------------------------------------

long2035 = settingRepository1.GetAttr("SPECIFICENERGYIMPARTED")
'--------------------------------------------------
' Parameter 1 : (String) "SPECIFICENERGYIMPARTED"
' Returned value : (Variant) (Long) 1
'--------------------------------------------------

Dim bSTR4069
bSTR4069 = ""
Dim bSTR4070
bSTR4070 = ""
Dim boolean2035
settingRepository1.GetAttrInfo "SPECIFICENERGYIMPARTED", bSTR4069, bSTR4070, boolean2035
'--------------------------------------------------
' Parameter 1 : (String) "SPECIFICENERGYIMPARTED"
' Parameter 2 : (String) "Default value"
' Parameter 3 : (String) "Unlocked"
' Parameter 4 : (Boolean) False
'--------------------------------------------------

long2036 = settingRepository1.GetAttr("SPECIFICENERGYIMPARTED_Large")
'--------------------------------------------------
' Parameter 1 : (String) "SPECIFICENERGYIMPARTED_Large"
' Returned value : (Variant) (Long) 1
'--------------------------------------------------

Dim bSTR4071
bSTR4071 = ""
Dim bSTR4072
bSTR4072 = ""
Dim boolean2036
settingRepository1.GetAttrInfo "SPECIFICENERGYIMPARTED_Large", bSTR4071, bSTR4072, boolean2036
'--------------------------------------------------
' Parameter 1 : (String) "SPECIFICENERGYIMPARTED_Large"
' Parameter 2 : (String) "Default value"
' Parameter 3 : (String) "Unlocked"
' Parameter 4 : (Boolean) False
'--------------------------------------------------

long2037 = settingRepository1.GetAttr("SPECIFICENERGYIMPARTED_ExtraLarge")
'--------------------------------------------------
' Parameter 1 : (String) "SPECIFICENERGYIMPARTED_ExtraLarge"
' Returned value : (Variant) (Long) 1
'--------------------------------------------------

Dim bSTR4073
bSTR4073 = ""
Dim bSTR4074
bSTR4074 = ""
Dim boolean2037
settingRepository1.GetAttrInfo "SPECIFICENERGYIMPARTED_ExtraLarge", bSTR4073, bSTR4074, boolean2037
'--------------------------------------------------
' Parameter 1 : (String) "SPECIFICENERGYIMPARTED_ExtraLarge"
' Parameter 2 : (String) "Default value"
' Parameter 3 : (String) "Unlocked"
' Parameter 4 : (Boolean) False
'--------------------------------------------------

long2038 = settingRepository1.GetAttr("SPECIFICENERGYIMPARTED_Small")
'--------------------------------------------------
' Parameter 1 : (String) "SPECIFICENERGYIMPARTED_Small"
' Returned value : (Variant) (Long) 1
'--------------------------------------------------

Dim bSTR4075
bSTR4075 = ""
Dim bSTR4076
bSTR4076 = ""
Dim boolean2038
settingRepository1.GetAttrInfo "SPECIFICENERGYIMPARTED_Small", bSTR4075, bSTR4076, boolean2038
'--------------------------------------------------
' Parameter 1 : (String) "SPECIFICENERGYIMPARTED_Small"
' Parameter 2 : (String) "Default value"
' Parameter 3 : (String) "Unlocked"
' Parameter 4 : (Boolean) False
'--------------------------------------------------

long2039 = settingRepository1.GetAttr("SPECIFICENERGYIMPARTED_ExtraSmall")
'--------------------------------------------------
' Parameter 1 : (String) "SPECIFICENERGYIMPARTED_ExtraSmall"
' Returned value : (Variant) (Long) 1
'--------------------------------------------------

Dim bSTR4077
bSTR4077 = ""
Dim bSTR4078
bSTR4078 = ""
Dim boolean2039
settingRepository1.GetAttrInfo "SPECIFICENERGYIMPARTED_ExtraSmall", bSTR4077, bSTR4078, boolean2039
'--------------------------------------------------
' Parameter 1 : (String) "SPECIFICENERGYIMPARTED_ExtraSmall"
' Parameter 2 : (String) "Default value"
' Parameter 3 : (String) "Unlocked"
' Parameter 4 : (Boolean) False
'--------------------------------------------------

long2040 = settingRepository1.GetAttr("SPECIFICENERGYIMPARTED_Nanometric")
'--------------------------------------------------
' Parameter 1 : (String) "SPECIFICENERGYIMPARTED_Nanometric"
' Returned value : (Variant) (Long) 1
'--------------------------------------------------

Dim bSTR4079
bSTR4079 = ""
Dim bSTR4080
bSTR4080 = ""
Dim boolean2040
settingRepository1.GetAttrInfo "SPECIFICENERGYIMPARTED_Nanometric", bSTR4079, bSTR4080, boolean2040
'--------------------------------------------------
' Parameter 1 : (String) "SPECIFICENERGYIMPARTED_Nanometric"
' Parameter 2 : (String) "Default value"
' Parameter 3 : (String) "Unlocked"
' Parameter 4 : (Boolean) False
'--------------------------------------------------

long2041 = settingRepository1.GetAttr("DOSEEQUIVALENT")
'--------------------------------------------------
' Parameter 1 : (String) "DOSEEQUIVALENT"
' Returned value : (Variant) (Long) 1
'--------------------------------------------------

Dim bSTR4081
bSTR4081 = ""
Dim bSTR4082
bSTR4082 = ""
Dim boolean2041
settingRepository1.GetAttrInfo "DOSEEQUIVALENT", bSTR4081, bSTR4082, boolean2041
'--------------------------------------------------
' Parameter 1 : (String) "DOSEEQUIVALENT"
' Parameter 2 : (String) "Default value"
' Parameter 3 : (String) "Unlocked"
' Parameter 4 : (Boolean) False
'--------------------------------------------------

long2042 = settingRepository1.GetAttr("DOSEEQUIVALENT_Large")
'--------------------------------------------------
' Parameter 1 : (String) "DOSEEQUIVALENT_Large"
' Returned value : (Variant) (Long) 1
'--------------------------------------------------

Dim bSTR4083
bSTR4083 = ""
Dim bSTR4084
bSTR4084 = ""
Dim boolean2042
settingRepository1.GetAttrInfo "DOSEEQUIVALENT_Large", bSTR4083, bSTR4084, boolean2042
'--------------------------------------------------
' Parameter 1 : (String) "DOSEEQUIVALENT_Large"
' Parameter 2 : (String) "Default value"
' Parameter 3 : (String) "Unlocked"
' Parameter 4 : (Boolean) False
'--------------------------------------------------

long2043 = settingRepository1.GetAttr("DOSEEQUIVALENT_ExtraLarge")
'--------------------------------------------------
' Parameter 1 : (String) "DOSEEQUIVALENT_ExtraLarge"
' Returned value : (Variant) (Long) 1
'--------------------------------------------------

Dim bSTR4085
bSTR4085 = ""
Dim bSTR4086
bSTR4086 = ""
Dim boolean2043
settingRepository1.GetAttrInfo "DOSEEQUIVALENT_ExtraLarge", bSTR4085, bSTR4086, boolean2043
'--------------------------------------------------
' Parameter 1 : (String) "DOSEEQUIVALENT_ExtraLarge"
' Parameter 2 : (String) "Default value"
' Parameter 3 : (String) "Unlocked"
' Parameter 4 : (Boolean) False
'--------------------------------------------------

long2044 = settingRepository1.GetAttr("DOSEEQUIVALENT_Small")
'--------------------------------------------------
' Parameter 1 : (String) "DOSEEQUIVALENT_Small"
' Returned value : (Variant) (Long) 1
'--------------------------------------------------

Dim bSTR4087
bSTR4087 = ""
Dim bSTR4088
bSTR4088 = ""
Dim boolean2044
settingRepository1.GetAttrInfo "DOSEEQUIVALENT_Small", bSTR4087, bSTR4088, boolean2044
'--------------------------------------------------
' Parameter 1 : (String) "DOSEEQUIVALENT_Small"
' Parameter 2 : (String) "Default value"
' Parameter 3 : (String) "Unlocked"
' Parameter 4 : (Boolean) False
'--------------------------------------------------

long2045 = settingRepository1.GetAttr("DOSEEQUIVALENT_ExtraSmall")
'--------------------------------------------------
' Parameter 1 : (String) "DOSEEQUIVALENT_ExtraSmall"
' Returned value : (Variant) (Long) 1
'--------------------------------------------------

Dim bSTR4089
bSTR4089 = ""
Dim bSTR4090
bSTR4090 = ""
Dim boolean2045
settingRepository1.GetAttrInfo "DOSEEQUIVALENT_ExtraSmall", bSTR4089, bSTR4090, boolean2045
'--------------------------------------------------
' Parameter 1 : (String) "DOSEEQUIVALENT_ExtraSmall"
' Parameter 2 : (String) "Default value"
' Parameter 3 : (String) "Unlocked"
' Parameter 4 : (Boolean) False
'--------------------------------------------------

long2046 = settingRepository1.GetAttr("DOSEEQUIVALENT_Nanometric")
'--------------------------------------------------
' Parameter 1 : (String) "DOSEEQUIVALENT_Nanometric"
' Returned value : (Variant) (Long) 1
'--------------------------------------------------

Dim bSTR4091
bSTR4091 = ""
Dim bSTR4092
bSTR4092 = ""
Dim boolean2046
settingRepository1.GetAttrInfo "DOSEEQUIVALENT_Nanometric", bSTR4091, bSTR4092, boolean2046
'--------------------------------------------------
' Parameter 1 : (String) "DOSEEQUIVALENT_Nanometric"
' Parameter 2 : (String) "Default value"
' Parameter 3 : (String) "Unlocked"
' Parameter 4 : (Boolean) False
'--------------------------------------------------

long2047 = settingRepository1.GetAttr("ABSORBEDDOSERATE")
'--------------------------------------------------
' Parameter 1 : (String) "ABSORBEDDOSERATE"
' Returned value : (Variant) (Long) 1
'--------------------------------------------------

Dim bSTR4093
bSTR4093 = ""
Dim bSTR4094
bSTR4094 = ""
Dim boolean2047
settingRepository1.GetAttrInfo "ABSORBEDDOSERATE", bSTR4093, bSTR4094, boolean2047
'--------------------------------------------------
' Parameter 1 : (String) "ABSORBEDDOSERATE"
' Parameter 2 : (String) "Default value"
' Parameter 3 : (String) "Unlocked"
' Parameter 4 : (Boolean) False
'--------------------------------------------------

long2048 = settingRepository1.GetAttr("ABSORBEDDOSERATE_Large")
'--------------------------------------------------
' Parameter 1 : (String) "ABSORBEDDOSERATE_Large"
' Returned value : (Variant) (Long) 1
'--------------------------------------------------

Dim bSTR4095
bSTR4095 = ""
Dim bSTR4096
bSTR4096 = ""
Dim boolean2048
settingRepository1.GetAttrInfo "ABSORBEDDOSERATE_Large", bSTR4095, bSTR4096, boolean2048
'--------------------------------------------------
' Parameter 1 : (String) "ABSORBEDDOSERATE_Large"
' Parameter 2 : (String) "Default value"
' Parameter 3 : (String) "Unlocked"
' Parameter 4 : (Boolean) False
'--------------------------------------------------

long2049 = settingRepository1.GetAttr("ABSORBEDDOSERATE_ExtraLarge")
'--------------------------------------------------
' Parameter 1 : (String) "ABSORBEDDOSERATE_ExtraLarge"
' Returned value : (Variant) (Long) 1
'--------------------------------------------------

Dim bSTR4097
bSTR4097 = ""
Dim bSTR4098
bSTR4098 = ""
Dim boolean2049
settingRepository1.GetAttrInfo "ABSORBEDDOSERATE_ExtraLarge", bSTR4097, bSTR4098, boolean2049
'--------------------------------------------------
' Parameter 1 : (String) "ABSORBEDDOSERATE_ExtraLarge"
' Parameter 2 : (String) "Default value"
' Parameter 3 : (String) "Unlocked"
' Parameter 4 : (Boolean) False
'--------------------------------------------------

long2050 = settingRepository1.GetAttr("ABSORBEDDOSERATE_Small")
'--------------------------------------------------
' Parameter 1 : (String) "ABSORBEDDOSERATE_Small"
' Returned value : (Variant) (Long) 1
'--------------------------------------------------

Dim bSTR4099
bSTR4099 = ""
Dim bSTR4100
bSTR4100 = ""
Dim boolean2050
settingRepository1.GetAttrInfo "ABSORBEDDOSERATE_Small", bSTR4099, bSTR4100, boolean2050
'--------------------------------------------------
' Parameter 1 : (String) "ABSORBEDDOSERATE_Small"
' Parameter 2 : (String) "Default value"
' Parameter 3 : (String) "Unlocked"
' Parameter 4 : (Boolean) False
'--------------------------------------------------

long2051 = settingRepository1.GetAttr("ABSORBEDDOSERATE_ExtraSmall")
'--------------------------------------------------
' Parameter 1 : (String) "ABSORBEDDOSERATE_ExtraSmall"
' Returned value : (Variant) (Long) 1
'--------------------------------------------------

Dim bSTR4101
bSTR4101 = ""
Dim bSTR4102
bSTR4102 = ""
Dim boolean2051
settingRepository1.GetAttrInfo "ABSORBEDDOSERATE_ExtraSmall", bSTR4101, bSTR4102, boolean2051
'--------------------------------------------------
' Parameter 1 : (String) "ABSORBEDDOSERATE_ExtraSmall"
' Parameter 2 : (String) "Default value"
' Parameter 3 : (String) "Unlocked"
' Parameter 4 : (Boolean) False
'--------------------------------------------------

long2052 = settingRepository1.GetAttr("ABSORBEDDOSERATE_Nanometric")
'--------------------------------------------------
' Parameter 1 : (String) "ABSORBEDDOSERATE_Nanometric"
' Returned value : (Variant) (Long) 1
'--------------------------------------------------

Dim bSTR4103
bSTR4103 = ""
Dim bSTR4104
bSTR4104 = ""
Dim boolean2052
settingRepository1.GetAttrInfo "ABSORBEDDOSERATE_Nanometric", bSTR4103, bSTR4104, boolean2052
'--------------------------------------------------
' Parameter 1 : (String) "ABSORBEDDOSERATE_Nanometric"
' Parameter 2 : (String) "Default value"
' Parameter 3 : (String) "Unlocked"
' Parameter 4 : (Boolean) False
'--------------------------------------------------

long2053 = settingRepository1.GetAttr("LINEARENERGYTRANSFER")
'--------------------------------------------------
' Parameter 1 : (String) "LINEARENERGYTRANSFER"
' Returned value : (Variant) (Long) 1
'--------------------------------------------------

Dim bSTR4105
bSTR4105 = ""
Dim bSTR4106
bSTR4106 = ""
Dim boolean2053
settingRepository1.GetAttrInfo "LINEARENERGYTRANSFER", bSTR4105, bSTR4106, boolean2053
'--------------------------------------------------
' Parameter 1 : (String) "LINEARENERGYTRANSFER"
' Parameter 2 : (String) "Default value"
' Parameter 3 : (String) "Unlocked"
' Parameter 4 : (Boolean) False
'--------------------------------------------------

long2054 = settingRepository1.GetAttr("LINEARENERGYTRANSFER_Large")
'--------------------------------------------------
' Parameter 1 : (String) "LINEARENERGYTRANSFER_Large"
' Returned value : (Variant) (Long) 1
'--------------------------------------------------

Dim bSTR4107
bSTR4107 = ""
Dim bSTR4108
bSTR4108 = ""
Dim boolean2054
settingRepository1.GetAttrInfo "LINEARENERGYTRANSFER_Large", bSTR4107, bSTR4108, boolean2054
'--------------------------------------------------
' Parameter 1 : (String) "LINEARENERGYTRANSFER_Large"
' Parameter 2 : (String) "Default value"
' Parameter 3 : (String) "Unlocked"
' Parameter 4 : (Boolean) False
'--------------------------------------------------

long2055 = settingRepository1.GetAttr("LINEARENERGYTRANSFER_ExtraLarge")
'--------------------------------------------------
' Parameter 1 : (String) "LINEARENERGYTRANSFER_ExtraLarge"
' Returned value : (Variant) (Long) 1
'--------------------------------------------------

Dim bSTR4109
bSTR4109 = ""
Dim bSTR4110
bSTR4110 = ""
Dim boolean2055
settingRepository1.GetAttrInfo "LINEARENERGYTRANSFER_ExtraLarge", bSTR4109, bSTR4110, boolean2055
'--------------------------------------------------
' Parameter 1 : (String) "LINEARENERGYTRANSFER_ExtraLarge"
' Parameter 2 : (String) "Default value"
' Parameter 3 : (String) "Unlocked"
' Parameter 4 : (Boolean) False
'--------------------------------------------------

long2056 = settingRepository1.GetAttr("LINEARENERGYTRANSFER_Small")
'--------------------------------------------------
' Parameter 1 : (String) "LINEARENERGYTRANSFER_Small"
' Returned value : (Variant) (Long) 1
'--------------------------------------------------

Dim bSTR4111
bSTR4111 = ""
Dim bSTR4112
bSTR4112 = ""
Dim boolean2056
settingRepository1.GetAttrInfo "LINEARENERGYTRANSFER_Small", bSTR4111, bSTR4112, boolean2056
'--------------------------------------------------
' Parameter 1 : (String) "LINEARENERGYTRANSFER_Small"
' Parameter 2 : (String) "Default value"
' Parameter 3 : (String) "Unlocked"
' Parameter 4 : (Boolean) False
'--------------------------------------------------

long2057 = settingRepository1.GetAttr("LINEARENERGYTRANSFER_ExtraSmall")
'--------------------------------------------------
' Parameter 1 : (String) "LINEARENERGYTRANSFER_ExtraSmall"
' Returned value : (Variant) (Long) 1
'--------------------------------------------------

Dim bSTR4113
bSTR4113 = ""
Dim bSTR4114
bSTR4114 = ""
Dim boolean2057
settingRepository1.GetAttrInfo "LINEARENERGYTRANSFER_ExtraSmall", bSTR4113, bSTR4114, boolean2057
'--------------------------------------------------
' Parameter 1 : (String) "LINEARENERGYTRANSFER_ExtraSmall"
' Parameter 2 : (String) "Default value"
' Parameter 3 : (String) "Unlocked"
' Parameter 4 : (Boolean) False
'--------------------------------------------------

long2058 = settingRepository1.GetAttr("LINEARENERGYTRANSFER_Nanometric")
'--------------------------------------------------
' Parameter 1 : (String) "LINEARENERGYTRANSFER_Nanometric"
' Returned value : (Variant) (Long) 1
'--------------------------------------------------

Dim bSTR4115
bSTR4115 = ""
Dim bSTR4116
bSTR4116 = ""
Dim boolean2058
settingRepository1.GetAttrInfo "LINEARENERGYTRANSFER_Nanometric", bSTR4115, bSTR4116, boolean2058
'--------------------------------------------------
' Parameter 1 : (String) "LINEARENERGYTRANSFER_Nanometric"
' Parameter 2 : (String) "Default value"
' Parameter 3 : (String) "Unlocked"
' Parameter 4 : (Boolean) False
'--------------------------------------------------

long2059 = settingRepository1.GetAttr("KERMA")
'--------------------------------------------------
' Parameter 1 : (String) "KERMA"
' Returned value : (Variant) (Long) 1
'--------------------------------------------------

Dim bSTR4117
bSTR4117 = ""
Dim bSTR4118
bSTR4118 = ""
Dim boolean2059
settingRepository1.GetAttrInfo "KERMA", bSTR4117, bSTR4118, boolean2059
'--------------------------------------------------
' Parameter 1 : (String) "KERMA"
' Parameter 2 : (String) "Default value"
' Parameter 3 : (String) "Unlocked"
' Parameter 4 : (Boolean) False
'--------------------------------------------------

long2060 = settingRepository1.GetAttr("KERMA_Large")
'--------------------------------------------------
' Parameter 1 : (String) "KERMA_Large"
' Returned value : (Variant) (Long) 1
'--------------------------------------------------

Dim bSTR4119
bSTR4119 = ""
Dim bSTR4120
bSTR4120 = ""
Dim boolean2060
settingRepository1.GetAttrInfo "KERMA_Large", bSTR4119, bSTR4120, boolean2060
'--------------------------------------------------
' Parameter 1 : (String) "KERMA_Large"
' Parameter 2 : (String) "Default value"
' Parameter 3 : (String) "Unlocked"
' Parameter 4 : (Boolean) False
'--------------------------------------------------

long2061 = settingRepository1.GetAttr("KERMA_ExtraLarge")
'--------------------------------------------------
' Parameter 1 : (String) "KERMA_ExtraLarge"
' Returned value : (Variant) (Long) 1
'--------------------------------------------------

Dim bSTR4121
bSTR4121 = ""
Dim bSTR4122
bSTR4122 = ""
Dim boolean2061
settingRepository1.GetAttrInfo "KERMA_ExtraLarge", bSTR4121, bSTR4122, boolean2061
'--------------------------------------------------
' Parameter 1 : (String) "KERMA_ExtraLarge"
' Parameter 2 : (String) "Default value"
' Parameter 3 : (String) "Unlocked"
' Parameter 4 : (Boolean) False
'--------------------------------------------------

long2062 = settingRepository1.GetAttr("KERMA_Small")
'--------------------------------------------------
' Parameter 1 : (String) "KERMA_Small"
' Returned value : (Variant) (Long) 1
'--------------------------------------------------

Dim bSTR4123
bSTR4123 = ""
Dim bSTR4124
bSTR4124 = ""
Dim boolean2062
settingRepository1.GetAttrInfo "KERMA_Small", bSTR4123, bSTR4124, boolean2062
'--------------------------------------------------
' Parameter 1 : (String) "KERMA_Small"
' Parameter 2 : (String) "Default value"
' Parameter 3 : (String) "Unlocked"
' Parameter 4 : (Boolean) False
'--------------------------------------------------

long2063 = settingRepository1.GetAttr("KERMA_ExtraSmall")
'--------------------------------------------------
' Parameter 1 : (String) "KERMA_ExtraSmall"
' Returned value : (Variant) (Long) 1
'--------------------------------------------------

Dim bSTR4125
bSTR4125 = ""
Dim bSTR4126
bSTR4126 = ""
Dim boolean2063
settingRepository1.GetAttrInfo "KERMA_ExtraSmall", bSTR4125, bSTR4126, boolean2063
'--------------------------------------------------
' Parameter 1 : (String) "KERMA_ExtraSmall"
' Parameter 2 : (String) "Default value"
' Parameter 3 : (String) "Unlocked"
' Parameter 4 : (Boolean) False
'--------------------------------------------------

long2064 = settingRepository1.GetAttr("KERMA_Nanometric")
'--------------------------------------------------
' Parameter 1 : (String) "KERMA_Nanometric"
' Returned value : (Variant) (Long) 1
'--------------------------------------------------

Dim bSTR4127
bSTR4127 = ""
Dim bSTR4128
bSTR4128 = ""
Dim boolean2064
settingRepository1.GetAttrInfo "KERMA_Nanometric", bSTR4127, bSTR4128, boolean2064
'--------------------------------------------------
' Parameter 1 : (String) "KERMA_Nanometric"
' Parameter 2 : (String) "Default value"
' Parameter 3 : (String) "Unlocked"
' Parameter 4 : (Boolean) False
'--------------------------------------------------

long2065 = settingRepository1.GetAttr("KERMARATE")
'--------------------------------------------------
' Parameter 1 : (String) "KERMARATE"
' Returned value : (Variant) (Long) 1
'--------------------------------------------------

Dim bSTR4129
bSTR4129 = ""
Dim bSTR4130
bSTR4130 = ""
Dim boolean2065
settingRepository1.GetAttrInfo "KERMARATE", bSTR4129, bSTR4130, boolean2065
'--------------------------------------------------
' Parameter 1 : (String) "KERMARATE"
' Parameter 2 : (String) "Default value"
' Parameter 3 : (String) "Unlocked"
' Parameter 4 : (Boolean) False
'--------------------------------------------------

long2066 = settingRepository1.GetAttr("KERMARATE_Large")
'--------------------------------------------------
' Parameter 1 : (String) "KERMARATE_Large"
' Returned value : (Variant) (Long) 1
'--------------------------------------------------

Dim bSTR4131
bSTR4131 = ""
Dim bSTR4132
bSTR4132 = ""
Dim boolean2066
settingRepository1.GetAttrInfo "KERMARATE_Large", bSTR4131, bSTR4132, boolean2066
'--------------------------------------------------
' Parameter 1 : (String) "KERMARATE_Large"
' Parameter 2 : (String) "Default value"
' Parameter 3 : (String) "Unlocked"
' Parameter 4 : (Boolean) False
'--------------------------------------------------

long2067 = settingRepository1.GetAttr("KERMARATE_ExtraLarge")
'--------------------------------------------------
' Parameter 1 : (String) "KERMARATE_ExtraLarge"
' Returned value : (Variant) (Long) 1
'--------------------------------------------------

Dim bSTR4133
bSTR4133 = ""
Dim bSTR4134
bSTR4134 = ""
Dim boolean2067
settingRepository1.GetAttrInfo "KERMARATE_ExtraLarge", bSTR4133, bSTR4134, boolean2067
'--------------------------------------------------
' Parameter 1 : (String) "KERMARATE_ExtraLarge"
' Parameter 2 : (String) "Default value"
' Parameter 3 : (String) "Unlocked"
' Parameter 4 : (Boolean) False
'--------------------------------------------------

long2068 = settingRepository1.GetAttr("KERMARATE_Small")
'--------------------------------------------------
' Parameter 1 : (String) "KERMARATE_Small"
' Returned value : (Variant) (Long) 1
'--------------------------------------------------

Dim bSTR4135
bSTR4135 = ""
Dim bSTR4136
bSTR4136 = ""
Dim boolean2068
settingRepository1.GetAttrInfo "KERMARATE_Small", bSTR4135, bSTR4136, boolean2068
'--------------------------------------------------
' Parameter 1 : (String) "KERMARATE_Small"
' Parameter 2 : (String) "Default value"
' Parameter 3 : (String) "Unlocked"
' Parameter 4 : (Boolean) False
'--------------------------------------------------

long2069 = settingRepository1.GetAttr("KERMARATE_ExtraSmall")
'--------------------------------------------------
' Parameter 1 : (String) "KERMARATE_ExtraSmall"
' Returned value : (Variant) (Long) 1
'--------------------------------------------------

Dim bSTR4137
bSTR4137 = ""
Dim bSTR4138
bSTR4138 = ""
Dim boolean2069
settingRepository1.GetAttrInfo "KERMARATE_ExtraSmall", bSTR4137, bSTR4138, boolean2069
'--------------------------------------------------
' Parameter 1 : (String) "KERMARATE_ExtraSmall"
' Parameter 2 : (String) "Default value"
' Parameter 3 : (String) "Unlocked"
' Parameter 4 : (Boolean) False
'--------------------------------------------------

long2070 = settingRepository1.GetAttr("KERMARATE_Nanometric")
'--------------------------------------------------
' Parameter 1 : (String) "KERMARATE_Nanometric"
' Returned value : (Variant) (Long) 1
'--------------------------------------------------

Dim bSTR4139
bSTR4139 = ""
Dim bSTR4140
bSTR4140 = ""
Dim boolean2070
settingRepository1.GetAttrInfo "KERMARATE_Nanometric", bSTR4139, bSTR4140, boolean2070
'--------------------------------------------------
' Parameter 1 : (String) "KERMARATE_Nanometric"
' Parameter 2 : (String) "Default value"
' Parameter 3 : (String) "Unlocked"
' Parameter 4 : (Boolean) False
'--------------------------------------------------

long2071 = settingRepository1.GetAttr("MASSENERGYTRANSFERCOEFFICIENT")
'--------------------------------------------------
' Parameter 1 : (String) "MASSENERGYTRANSFERCOEFFICIENT"
' Returned value : (Variant) (Long) 1
'--------------------------------------------------

Dim bSTR4141
bSTR4141 = ""
Dim bSTR4142
bSTR4142 = ""
Dim boolean2071
settingRepository1.GetAttrInfo "MASSENERGYTRANSFERCOEFFICIENT", bSTR4141, bSTR4142, boolean2071
'--------------------------------------------------
' Parameter 1 : (String) "MASSENERGYTRANSFERCOEFFICIENT"
' Parameter 2 : (String) "Default value"
' Parameter 3 : (String) "Unlocked"
' Parameter 4 : (Boolean) False
'--------------------------------------------------

long2072 = settingRepository1.GetAttr("MASSENERGYTRANSFERCOEFFICIENT_Large")
'--------------------------------------------------
' Parameter 1 : (String) "MASSENERGYTRANSFERCOEFFICIENT_Large"
' Returned value : (Variant) (Long) 1
'--------------------------------------------------

Dim bSTR4143
bSTR4143 = ""
Dim bSTR4144
bSTR4144 = ""
Dim boolean2072
settingRepository1.GetAttrInfo "MASSENERGYTRANSFERCOEFFICIENT_Large", bSTR4143, bSTR4144, boolean2072
'--------------------------------------------------
' Parameter 1 : (String) "MASSENERGYTRANSFERCOEFFICIENT_Large"
' Parameter 2 : (String) "Default value"
' Parameter 3 : (String) "Unlocked"
' Parameter 4 : (Boolean) False
'--------------------------------------------------

long2073 = settingRepository1.GetAttr("MASSENERGYTRANSFERCOEFFICIENT_ExtraLarge")
'--------------------------------------------------
' Parameter 1 : (String) "MASSENERGYTRANSFERCOEFFICIENT_ExtraLarge"
' Returned value : (Variant) (Long) 1
'--------------------------------------------------

Dim bSTR4145
bSTR4145 = ""
Dim bSTR4146
bSTR4146 = ""
Dim boolean2073
settingRepository1.GetAttrInfo "MASSENERGYTRANSFERCOEFFICIENT_ExtraLarge", bSTR4145, bSTR4146, boolean2073
'--------------------------------------------------
' Parameter 1 : (String) "MASSENERGYTRANSFERCOEFFICIENT_ExtraLarge"
' Parameter 2 : (String) "Default value"
' Parameter 3 : (String) "Unlocked"
' Parameter 4 : (Boolean) False
'--------------------------------------------------

long2074 = settingRepository1.GetAttr("MASSENERGYTRANSFERCOEFFICIENT_Small")
'--------------------------------------------------
' Parameter 1 : (String) "MASSENERGYTRANSFERCOEFFICIENT_Small"
' Returned value : (Variant) (Long) 1
'--------------------------------------------------

Dim bSTR4147
bSTR4147 = ""
Dim bSTR4148
bSTR4148 = ""
Dim boolean2074
settingRepository1.GetAttrInfo "MASSENERGYTRANSFERCOEFFICIENT_Small", bSTR4147, bSTR4148, boolean2074
'--------------------------------------------------
' Parameter 1 : (String) "MASSENERGYTRANSFERCOEFFICIENT_Small"
' Parameter 2 : (String) "Default value"
' Parameter 3 : (String) "Unlocked"
' Parameter 4 : (Boolean) False
'--------------------------------------------------

long2075 = settingRepository1.GetAttr("MASSENERGYTRANSFERCOEFFICIENT_ExtraSmall")
'--------------------------------------------------
' Parameter 1 : (String) "MASSENERGYTRANSFERCOEFFICIENT_ExtraSmall"
' Returned value : (Variant) (Long) 1
'--------------------------------------------------

Dim bSTR4149
bSTR4149 = ""
Dim bSTR4150
bSTR4150 = ""
Dim boolean2075
settingRepository1.GetAttrInfo "MASSENERGYTRANSFERCOEFFICIENT_ExtraSmall", bSTR4149, bSTR4150, boolean2075
'--------------------------------------------------
' Parameter 1 : (String) "MASSENERGYTRANSFERCOEFFICIENT_ExtraSmall"
' Parameter 2 : (String) "Default value"
' Parameter 3 : (String) "Unlocked"
' Parameter 4 : (Boolean) False
'--------------------------------------------------

long2076 = settingRepository1.GetAttr("MASSENERGYTRANSFERCOEFFICIENT_Nanometric")
'--------------------------------------------------
' Parameter 1 : (String) "MASSENERGYTRANSFERCOEFFICIENT_Nanometric"
' Returned value : (Variant) (Long) 1
'--------------------------------------------------

Dim bSTR4151
bSTR4151 = ""
Dim bSTR4152
bSTR4152 = ""
Dim boolean2076
settingRepository1.GetAttrInfo "MASSENERGYTRANSFERCOEFFICIENT_Nanometric", bSTR4151, bSTR4152, boolean2076
'--------------------------------------------------
' Parameter 1 : (String) "MASSENERGYTRANSFERCOEFFICIENT_Nanometric"
' Parameter 2 : (String) "Default value"
' Parameter 3 : (String) "Unlocked"
' Parameter 4 : (Boolean) False
'--------------------------------------------------

long2077 = settingRepository1.GetAttr("EXPOSURE")
'--------------------------------------------------
' Parameter 1 : (String) "EXPOSURE"
' Returned value : (Variant) (Long) 1
'--------------------------------------------------

Dim bSTR4153
bSTR4153 = ""
Dim bSTR4154
bSTR4154 = ""
Dim boolean2077
settingRepository1.GetAttrInfo "EXPOSURE", bSTR4153, bSTR4154, boolean2077
'--------------------------------------------------
' Parameter 1 : (String) "EXPOSURE"
' Parameter 2 : (String) "Default value"
' Parameter 3 : (String) "Unlocked"
' Parameter 4 : (Boolean) False
'--------------------------------------------------

long2078 = settingRepository1.GetAttr("EXPOSURE_Large")
'--------------------------------------------------
' Parameter 1 : (String) "EXPOSURE_Large"
' Returned value : (Variant) (Long) 1
'--------------------------------------------------

Dim bSTR4155
bSTR4155 = ""
Dim bSTR4156
bSTR4156 = ""
Dim boolean2078
settingRepository1.GetAttrInfo "EXPOSURE_Large", bSTR4155, bSTR4156, boolean2078
'--------------------------------------------------
' Parameter 1 : (String) "EXPOSURE_Large"
' Parameter 2 : (String) "Default value"
' Parameter 3 : (String) "Unlocked"
' Parameter 4 : (Boolean) False
'--------------------------------------------------

long2079 = settingRepository1.GetAttr("EXPOSURE_ExtraLarge")
'--------------------------------------------------
' Parameter 1 : (String) "EXPOSURE_ExtraLarge"
' Returned value : (Variant) (Long) 1
'--------------------------------------------------

Dim bSTR4157
bSTR4157 = ""
Dim bSTR4158
bSTR4158 = ""
Dim boolean2079
settingRepository1.GetAttrInfo "EXPOSURE_ExtraLarge", bSTR4157, bSTR4158, boolean2079
'--------------------------------------------------
' Parameter 1 : (String) "EXPOSURE_ExtraLarge"
' Parameter 2 : (String) "Default value"
' Parameter 3 : (String) "Unlocked"
' Parameter 4 : (Boolean) False
'--------------------------------------------------

long2080 = settingRepository1.GetAttr("EXPOSURE_Small")
'--------------------------------------------------
' Parameter 1 : (String) "EXPOSURE_Small"
' Returned value : (Variant) (Long) 1
'--------------------------------------------------

Dim bSTR4159
bSTR4159 = ""
Dim bSTR4160
bSTR4160 = ""
Dim boolean2080
settingRepository1.GetAttrInfo "EXPOSURE_Small", bSTR4159, bSTR4160, boolean2080
'--------------------------------------------------
' Parameter 1 : (String) "EXPOSURE_Small"
' Parameter 2 : (String) "Default value"
' Parameter 3 : (String) "Unlocked"
' Parameter 4 : (Boolean) False
'--------------------------------------------------

long2081 = settingRepository1.GetAttr("EXPOSURE_ExtraSmall")
'--------------------------------------------------
' Parameter 1 : (String) "EXPOSURE_ExtraSmall"
' Returned value : (Variant) (Long) 1
'--------------------------------------------------

Dim bSTR4161
bSTR4161 = ""
Dim bSTR4162
bSTR4162 = ""
Dim boolean2081
settingRepository1.GetAttrInfo "EXPOSURE_ExtraSmall", bSTR4161, bSTR4162, boolean2081
'--------------------------------------------------
' Parameter 1 : (String) "EXPOSURE_ExtraSmall"
' Parameter 2 : (String) "Default value"
' Parameter 3 : (String) "Unlocked"
' Parameter 4 : (Boolean) False
'--------------------------------------------------

long2082 = settingRepository1.GetAttr("EXPOSURE_Nanometric")
'--------------------------------------------------
' Parameter 1 : (String) "EXPOSURE_Nanometric"
' Returned value : (Variant) (Long) 1
'--------------------------------------------------

Dim bSTR4163
bSTR4163 = ""
Dim bSTR4164
bSTR4164 = ""
Dim boolean2082
settingRepository1.GetAttrInfo "EXPOSURE_Nanometric", bSTR4163, bSTR4164, boolean2082
'--------------------------------------------------
' Parameter 1 : (String) "EXPOSURE_Nanometric"
' Parameter 2 : (String) "Default value"
' Parameter 3 : (String) "Unlocked"
' Parameter 4 : (Boolean) False
'--------------------------------------------------

long2083 = settingRepository1.GetAttr("EXPOSURERATE")
'--------------------------------------------------
' Parameter 1 : (String) "EXPOSURERATE"
' Returned value : (Variant) (Long) 1
'--------------------------------------------------

Dim bSTR4165
bSTR4165 = ""
Dim bSTR4166
bSTR4166 = ""
Dim boolean2083
settingRepository1.GetAttrInfo "EXPOSURERATE", bSTR4165, bSTR4166, boolean2083
'--------------------------------------------------
' Parameter 1 : (String) "EXPOSURERATE"
' Parameter 2 : (String) "Default value"
' Parameter 3 : (String) "Unlocked"
' Parameter 4 : (Boolean) False
'--------------------------------------------------

long2084 = settingRepository1.GetAttr("EXPOSURERATE_Large")
'--------------------------------------------------
' Parameter 1 : (String) "EXPOSURERATE_Large"
' Returned value : (Variant) (Long) 1
'--------------------------------------------------

Dim bSTR4167
bSTR4167 = ""
Dim bSTR4168
bSTR4168 = ""
Dim boolean2084
settingRepository1.GetAttrInfo "EXPOSURERATE_Large", bSTR4167, bSTR4168, boolean2084
'--------------------------------------------------
' Parameter 1 : (String) "EXPOSURERATE_Large"
' Parameter 2 : (String) "Default value"
' Parameter 3 : (String) "Unlocked"
' Parameter 4 : (Boolean) False
'--------------------------------------------------

long2085 = settingRepository1.GetAttr("EXPOSURERATE_ExtraLarge")
'--------------------------------------------------
' Parameter 1 : (String) "EXPOSURERATE_ExtraLarge"
' Returned value : (Variant) (Long) 1
'--------------------------------------------------

Dim bSTR4169
bSTR4169 = ""
Dim bSTR4170
bSTR4170 = ""
Dim boolean2085
settingRepository1.GetAttrInfo "EXPOSURERATE_ExtraLarge", bSTR4169, bSTR4170, boolean2085
'--------------------------------------------------
' Parameter 1 : (String) "EXPOSURERATE_ExtraLarge"
' Parameter 2 : (String) "Default value"
' Parameter 3 : (String) "Unlocked"
' Parameter 4 : (Boolean) False
'--------------------------------------------------

long2086 = settingRepository1.GetAttr("EXPOSURERATE_Small")
'--------------------------------------------------
' Parameter 1 : (String) "EXPOSURERATE_Small"
' Returned value : (Variant) (Long) 1
'--------------------------------------------------

Dim bSTR4171
bSTR4171 = ""
Dim bSTR4172
bSTR4172 = ""
Dim boolean2086
settingRepository1.GetAttrInfo "EXPOSURERATE_Small", bSTR4171, bSTR4172, boolean2086
'--------------------------------------------------
' Parameter 1 : (String) "EXPOSURERATE_Small"
' Parameter 2 : (String) "Default value"
' Parameter 3 : (String) "Unlocked"
' Parameter 4 : (Boolean) False
'--------------------------------------------------

long2087 = settingRepository1.GetAttr("EXPOSURERATE_ExtraSmall")
'--------------------------------------------------
' Parameter 1 : (String) "EXPOSURERATE_ExtraSmall"
' Returned value : (Variant) (Long) 1
'--------------------------------------------------

Dim bSTR4173
bSTR4173 = ""
Dim bSTR4174
bSTR4174 = ""
Dim boolean2087
settingRepository1.GetAttrInfo "EXPOSURERATE_ExtraSmall", bSTR4173, bSTR4174, boolean2087
'--------------------------------------------------
' Parameter 1 : (String) "EXPOSURERATE_ExtraSmall"
' Parameter 2 : (String) "Default value"
' Parameter 3 : (String) "Unlocked"
' Parameter 4 : (Boolean) False
'--------------------------------------------------

long2088 = settingRepository1.GetAttr("EXPOSURERATE_Nanometric")
'--------------------------------------------------
' Parameter 1 : (String) "EXPOSURERATE_Nanometric"
' Returned value : (Variant) (Long) 1
'--------------------------------------------------

Dim bSTR4175
bSTR4175 = ""
Dim bSTR4176
bSTR4176 = ""
Dim boolean2088
settingRepository1.GetAttrInfo "EXPOSURERATE_Nanometric", bSTR4175, bSTR4176, boolean2088
'--------------------------------------------------
' Parameter 1 : (String) "EXPOSURERATE_Nanometric"
' Parameter 2 : (String) "Default value"
' Parameter 3 : (String) "Unlocked"
' Parameter 4 : (Boolean) False
'--------------------------------------------------

long2089 = settingRepository1.GetAttr("SPECTRALCONCENTRATION")
'--------------------------------------------------
' Parameter 1 : (String) "SPECTRALCONCENTRATION"
' Returned value : (Variant) (Long) 1
'--------------------------------------------------

Dim bSTR4177
bSTR4177 = ""
Dim bSTR4178
bSTR4178 = ""
Dim boolean2089
settingRepository1.GetAttrInfo "SPECTRALCONCENTRATION", bSTR4177, bSTR4178, boolean2089
'--------------------------------------------------
' Parameter 1 : (String) "SPECTRALCONCENTRATION"
' Parameter 2 : (String) "Default value"
' Parameter 3 : (String) "Unlocked"
' Parameter 4 : (Boolean) False
'--------------------------------------------------

long2090 = settingRepository1.GetAttr("SPECTRALCONCENTRATION_Large")
'--------------------------------------------------
' Parameter 1 : (String) "SPECTRALCONCENTRATION_Large"
' Returned value : (Variant) (Long) 1
'--------------------------------------------------

Dim bSTR4179
bSTR4179 = ""
Dim bSTR4180
bSTR4180 = ""
Dim boolean2090
settingRepository1.GetAttrInfo "SPECTRALCONCENTRATION_Large", bSTR4179, bSTR4180, boolean2090
'--------------------------------------------------
' Parameter 1 : (String) "SPECTRALCONCENTRATION_Large"
' Parameter 2 : (String) "Default value"
' Parameter 3 : (String) "Unlocked"
' Parameter 4 : (Boolean) False
'--------------------------------------------------

long2091 = settingRepository1.GetAttr("SPECTRALCONCENTRATION_ExtraLarge")
'--------------------------------------------------
' Parameter 1 : (String) "SPECTRALCONCENTRATION_ExtraLarge"
' Returned value : (Variant) (Long) 1
'--------------------------------------------------

Dim bSTR4181
bSTR4181 = ""
Dim bSTR4182
bSTR4182 = ""
Dim boolean2091
settingRepository1.GetAttrInfo "SPECTRALCONCENTRATION_ExtraLarge", bSTR4181, bSTR4182, boolean2091
'--------------------------------------------------
' Parameter 1 : (String) "SPECTRALCONCENTRATION_ExtraLarge"
' Parameter 2 : (String) "Default value"
' Parameter 3 : (String) "Unlocked"
' Parameter 4 : (Boolean) False
'--------------------------------------------------

long2092 = settingRepository1.GetAttr("SPECTRALCONCENTRATION_Small")
'--------------------------------------------------
' Parameter 1 : (String) "SPECTRALCONCENTRATION_Small"
' Returned value : (Variant) (Long) 1
'--------------------------------------------------

Dim bSTR4183
bSTR4183 = ""
Dim bSTR4184
bSTR4184 = ""
Dim boolean2092
settingRepository1.GetAttrInfo "SPECTRALCONCENTRATION_Small", bSTR4183, bSTR4184, boolean2092
'--------------------------------------------------
' Parameter 1 : (String) "SPECTRALCONCENTRATION_Small"
' Parameter 2 : (String) "Default value"
' Parameter 3 : (String) "Unlocked"
' Parameter 4 : (Boolean) False
'--------------------------------------------------

long2093 = settingRepository1.GetAttr("SPECTRALCONCENTRATION_ExtraSmall")
'--------------------------------------------------
' Parameter 1 : (String) "SPECTRALCONCENTRATION_ExtraSmall"
' Returned value : (Variant) (Long) 1
'--------------------------------------------------

Dim bSTR4185
bSTR4185 = ""
Dim bSTR4186
bSTR4186 = ""
Dim boolean2093
settingRepository1.GetAttrInfo "SPECTRALCONCENTRATION_ExtraSmall", bSTR4185, bSTR4186, boolean2093
'--------------------------------------------------
' Parameter 1 : (String) "SPECTRALCONCENTRATION_ExtraSmall"
' Parameter 2 : (String) "Default value"
' Parameter 3 : (String) "Unlocked"
' Parameter 4 : (Boolean) False
'--------------------------------------------------

long2094 = settingRepository1.GetAttr("SPECTRALCONCENTRATION_Nanometric")
'--------------------------------------------------
' Parameter 1 : (String) "SPECTRALCONCENTRATION_Nanometric"
' Returned value : (Variant) (Long) 1
'--------------------------------------------------

Dim bSTR4187
bSTR4187 = ""
Dim bSTR4188
bSTR4188 = ""
Dim boolean2094
settingRepository1.GetAttrInfo "SPECTRALCONCENTRATION_Nanometric", bSTR4187, bSTR4188, boolean2094
'--------------------------------------------------
' Parameter 1 : (String) "SPECTRALCONCENTRATION_Nanometric"
' Parameter 2 : (String) "Default value"
' Parameter 3 : (String) "Unlocked"
' Parameter 4 : (Boolean) False
'--------------------------------------------------

long2095 = settingRepository1.GetAttr("DENSITYOFSTATES")
'--------------------------------------------------
' Parameter 1 : (String) "DENSITYOFSTATES"
' Returned value : (Variant) (Long) 1
'--------------------------------------------------

Dim bSTR4189
bSTR4189 = ""
Dim bSTR4190
bSTR4190 = ""
Dim boolean2095
settingRepository1.GetAttrInfo "DENSITYOFSTATES", bSTR4189, bSTR4190, boolean2095
'--------------------------------------------------
' Parameter 1 : (String) "DENSITYOFSTATES"
' Parameter 2 : (String) "Default value"
' Parameter 3 : (String) "Unlocked"
' Parameter 4 : (Boolean) False
'--------------------------------------------------

long2096 = settingRepository1.GetAttr("DENSITYOFSTATES_Large")
'--------------------------------------------------
' Parameter 1 : (String) "DENSITYOFSTATES_Large"
' Returned value : (Variant) (Long) 1
'--------------------------------------------------

Dim bSTR4191
bSTR4191 = ""
Dim bSTR4192
bSTR4192 = ""
Dim boolean2096
settingRepository1.GetAttrInfo "DENSITYOFSTATES_Large", bSTR4191, bSTR4192, boolean2096
'--------------------------------------------------
' Parameter 1 : (String) "DENSITYOFSTATES_Large"
' Parameter 2 : (String) "Default value"
' Parameter 3 : (String) "Unlocked"
' Parameter 4 : (Boolean) False
'--------------------------------------------------

long2097 = settingRepository1.GetAttr("DENSITYOFSTATES_ExtraLarge")
'--------------------------------------------------
' Parameter 1 : (String) "DENSITYOFSTATES_ExtraLarge"
' Returned value : (Variant) (Long) 1
'--------------------------------------------------

Dim bSTR4193
bSTR4193 = ""
Dim bSTR4194
bSTR4194 = ""
Dim boolean2097
settingRepository1.GetAttrInfo "DENSITYOFSTATES_ExtraLarge", bSTR4193, bSTR4194, boolean2097
'--------------------------------------------------
' Parameter 1 : (String) "DENSITYOFSTATES_ExtraLarge"
' Parameter 2 : (String) "Default value"
' Parameter 3 : (String) "Unlocked"
' Parameter 4 : (Boolean) False
'--------------------------------------------------

long2098 = settingRepository1.GetAttr("DENSITYOFSTATES_Small")
'--------------------------------------------------
' Parameter 1 : (String) "DENSITYOFSTATES_Small"
' Returned value : (Variant) (Long) 1
'--------------------------------------------------

Dim bSTR4195
bSTR4195 = ""
Dim bSTR4196
bSTR4196 = ""
Dim boolean2098
settingRepository1.GetAttrInfo "DENSITYOFSTATES_Small", bSTR4195, bSTR4196, boolean2098
'--------------------------------------------------
' Parameter 1 : (String) "DENSITYOFSTATES_Small"
' Parameter 2 : (String) "Default value"
' Parameter 3 : (String) "Unlocked"
' Parameter 4 : (Boolean) False
'--------------------------------------------------

long2099 = settingRepository1.GetAttr("DENSITYOFSTATES_ExtraSmall")
'--------------------------------------------------
' Parameter 1 : (String) "DENSITYOFSTATES_ExtraSmall"
' Returned value : (Variant) (Long) 1
'--------------------------------------------------

Dim bSTR4197
bSTR4197 = ""
Dim bSTR4198
bSTR4198 = ""
Dim boolean2099
settingRepository1.GetAttrInfo "DENSITYOFSTATES_ExtraSmall", bSTR4197, bSTR4198, boolean2099
'--------------------------------------------------
' Parameter 1 : (String) "DENSITYOFSTATES_ExtraSmall"
' Parameter 2 : (String) "Default value"
' Parameter 3 : (String) "Unlocked"
' Parameter 4 : (Boolean) False
'--------------------------------------------------

long2100 = settingRepository1.GetAttr("DENSITYOFSTATES_Nanometric")
'--------------------------------------------------
' Parameter 1 : (String) "DENSITYOFSTATES_Nanometric"
' Returned value : (Variant) (Long) 1
'--------------------------------------------------

Dim bSTR4199
bSTR4199 = ""
Dim bSTR4200
bSTR4200 = ""
Dim boolean2100
settingRepository1.GetAttrInfo "DENSITYOFSTATES_Nanometric", bSTR4199, bSTR4200, boolean2100
'--------------------------------------------------
' Parameter 1 : (String) "DENSITYOFSTATES_Nanometric"
' Parameter 2 : (String) "Default value"
' Parameter 3 : (String) "Unlocked"
' Parameter 4 : (Boolean) False
'--------------------------------------------------

long2101 = settingRepository1.GetAttr("LORENZCOEFFICIENT")
'--------------------------------------------------
' Parameter 1 : (String) "LORENZCOEFFICIENT"
' Returned value : (Variant) (Long) 1
'--------------------------------------------------

Dim bSTR4201
bSTR4201 = ""
Dim bSTR4202
bSTR4202 = ""
Dim boolean2101
settingRepository1.GetAttrInfo "LORENZCOEFFICIENT", bSTR4201, bSTR4202, boolean2101
'--------------------------------------------------
' Parameter 1 : (String) "LORENZCOEFFICIENT"
' Parameter 2 : (String) "Default value"
' Parameter 3 : (String) "Unlocked"
' Parameter 4 : (Boolean) False
'--------------------------------------------------

long2102 = settingRepository1.GetAttr("LORENZCOEFFICIENT_Large")
'--------------------------------------------------
' Parameter 1 : (String) "LORENZCOEFFICIENT_Large"
' Returned value : (Variant) (Long) 1
'--------------------------------------------------

Dim bSTR4203
bSTR4203 = ""
Dim bSTR4204
bSTR4204 = ""
Dim boolean2102
settingRepository1.GetAttrInfo "LORENZCOEFFICIENT_Large", bSTR4203, bSTR4204, boolean2102
'--------------------------------------------------
' Parameter 1 : (String) "LORENZCOEFFICIENT_Large"
' Parameter 2 : (String) "Default value"
' Parameter 3 : (String) "Unlocked"
' Parameter 4 : (Boolean) False
'--------------------------------------------------

long2103 = settingRepository1.GetAttr("LORENZCOEFFICIENT_ExtraLarge")
'--------------------------------------------------
' Parameter 1 : (String) "LORENZCOEFFICIENT_ExtraLarge"
' Returned value : (Variant) (Long) 1
'--------------------------------------------------

Dim bSTR4205
bSTR4205 = ""
Dim bSTR4206
bSTR4206 = ""
Dim boolean2103
settingRepository1.GetAttrInfo "LORENZCOEFFICIENT_ExtraLarge", bSTR4205, bSTR4206, boolean2103
'--------------------------------------------------
' Parameter 1 : (String) "LORENZCOEFFICIENT_ExtraLarge"
' Parameter 2 : (String) "Default value"
' Parameter 3 : (String) "Unlocked"
' Parameter 4 : (Boolean) False
'--------------------------------------------------

long2104 = settingRepository1.GetAttr("LORENZCOEFFICIENT_Small")
'--------------------------------------------------
' Parameter 1 : (String) "LORENZCOEFFICIENT_Small"
' Returned value : (Variant) (Long) 1
'--------------------------------------------------

Dim bSTR4207
bSTR4207 = ""
Dim bSTR4208
bSTR4208 = ""
Dim boolean2104
settingRepository1.GetAttrInfo "LORENZCOEFFICIENT_Small", bSTR4207, bSTR4208, boolean2104
'--------------------------------------------------
' Parameter 1 : (String) "LORENZCOEFFICIENT_Small"
' Parameter 2 : (String) "Default value"
' Parameter 3 : (String) "Unlocked"
' Parameter 4 : (Boolean) False
'--------------------------------------------------

long2105 = settingRepository1.GetAttr("LORENZCOEFFICIENT_ExtraSmall")
'--------------------------------------------------
' Parameter 1 : (String) "LORENZCOEFFICIENT_ExtraSmall"
' Returned value : (Variant) (Long) 1
'--------------------------------------------------

Dim bSTR4209
bSTR4209 = ""
Dim bSTR4210
bSTR4210 = ""
Dim boolean2105
settingRepository1.GetAttrInfo "LORENZCOEFFICIENT_ExtraSmall", bSTR4209, bSTR4210, boolean2105
'--------------------------------------------------
' Parameter 1 : (String) "LORENZCOEFFICIENT_ExtraSmall"
' Parameter 2 : (String) "Default value"
' Parameter 3 : (String) "Unlocked"
' Parameter 4 : (Boolean) False
'--------------------------------------------------

long2106 = settingRepository1.GetAttr("LORENZCOEFFICIENT_Nanometric")
'--------------------------------------------------
' Parameter 1 : (String) "LORENZCOEFFICIENT_Nanometric"
' Returned value : (Variant) (Long) 1
'--------------------------------------------------

Dim bSTR4211
bSTR4211 = ""
Dim bSTR4212
bSTR4212 = ""
Dim boolean2106
settingRepository1.GetAttrInfo "LORENZCOEFFICIENT_Nanometric", bSTR4211, bSTR4212, boolean2106
'--------------------------------------------------
' Parameter 1 : (String) "LORENZCOEFFICIENT_Nanometric"
' Parameter 2 : (String) "Default value"
' Parameter 3 : (String) "Unlocked"
' Parameter 4 : (Boolean) False
'--------------------------------------------------

long2107 = settingRepository1.GetAttr("HALLCOEFFICIENT")
'--------------------------------------------------
' Parameter 1 : (String) "HALLCOEFFICIENT"
' Returned value : (Variant) (Long) 1
'--------------------------------------------------

Dim bSTR4213
bSTR4213 = ""
Dim bSTR4214
bSTR4214 = ""
Dim boolean2107
settingRepository1.GetAttrInfo "HALLCOEFFICIENT", bSTR4213, bSTR4214, boolean2107
'--------------------------------------------------
' Parameter 1 : (String) "HALLCOEFFICIENT"
' Parameter 2 : (String) "Default value"
' Parameter 3 : (String) "Unlocked"
' Parameter 4 : (Boolean) False
'--------------------------------------------------

long2108 = settingRepository1.GetAttr("HALLCOEFFICIENT_Large")
'--------------------------------------------------
' Parameter 1 : (String) "HALLCOEFFICIENT_Large"
' Returned value : (Variant) (Long) 1
'--------------------------------------------------

Dim bSTR4215
bSTR4215 = ""
Dim bSTR4216
bSTR4216 = ""
Dim boolean2108
settingRepository1.GetAttrInfo "HALLCOEFFICIENT_Large", bSTR4215, bSTR4216, boolean2108
'--------------------------------------------------
' Parameter 1 : (String) "HALLCOEFFICIENT_Large"
' Parameter 2 : (String) "Default value"
' Parameter 3 : (String) "Unlocked"
' Parameter 4 : (Boolean) False
'--------------------------------------------------

long2109 = settingRepository1.GetAttr("HALLCOEFFICIENT_ExtraLarge")
'--------------------------------------------------
' Parameter 1 : (String) "HALLCOEFFICIENT_ExtraLarge"
' Returned value : (Variant) (Long) 1
'--------------------------------------------------

Dim bSTR4217
bSTR4217 = ""
Dim bSTR4218
bSTR4218 = ""
Dim boolean2109
settingRepository1.GetAttrInfo "HALLCOEFFICIENT_ExtraLarge", bSTR4217, bSTR4218, boolean2109
'--------------------------------------------------
' Parameter 1 : (String) "HALLCOEFFICIENT_ExtraLarge"
' Parameter 2 : (String) "Default value"
' Parameter 3 : (String) "Unlocked"
' Parameter 4 : (Boolean) False
'--------------------------------------------------

long2110 = settingRepository1.GetAttr("HALLCOEFFICIENT_Small")
'--------------------------------------------------
' Parameter 1 : (String) "HALLCOEFFICIENT_Small"
' Returned value : (Variant) (Long) 1
'--------------------------------------------------

Dim bSTR4219
bSTR4219 = ""
Dim bSTR4220
bSTR4220 = ""
Dim boolean2110
settingRepository1.GetAttrInfo "HALLCOEFFICIENT_Small", bSTR4219, bSTR4220, boolean2110
'--------------------------------------------------
' Parameter 1 : (String) "HALLCOEFFICIENT_Small"
' Parameter 2 : (String) "Default value"
' Parameter 3 : (String) "Unlocked"
' Parameter 4 : (Boolean) False
'--------------------------------------------------

long2111 = settingRepository1.GetAttr("HALLCOEFFICIENT_ExtraSmall")
'--------------------------------------------------
' Parameter 1 : (String) "HALLCOEFFICIENT_ExtraSmall"
' Returned value : (Variant) (Long) 1
'--------------------------------------------------

Dim bSTR4221
bSTR4221 = ""
Dim bSTR4222
bSTR4222 = ""
Dim boolean2111
settingRepository1.GetAttrInfo "HALLCOEFFICIENT_ExtraSmall", bSTR4221, bSTR4222, boolean2111
'--------------------------------------------------
' Parameter 1 : (String) "HALLCOEFFICIENT_ExtraSmall"
' Parameter 2 : (String) "Default value"
' Parameter 3 : (String) "Unlocked"
' Parameter 4 : (Boolean) False
'--------------------------------------------------

long2112 = settingRepository1.GetAttr("HALLCOEFFICIENT_Nanometric")
'--------------------------------------------------
' Parameter 1 : (String) "HALLCOEFFICIENT_Nanometric"
' Returned value : (Variant) (Long) 1
'--------------------------------------------------

Dim bSTR4223
bSTR4223 = ""
Dim bSTR4224
bSTR4224 = ""
Dim boolean2112
settingRepository1.GetAttrInfo "HALLCOEFFICIENT_Nanometric", bSTR4223, bSTR4224, boolean2112
'--------------------------------------------------
' Parameter 1 : (String) "HALLCOEFFICIENT_Nanometric"
' Parameter 2 : (String) "Default value"
' Parameter 3 : (String) "Unlocked"
' Parameter 4 : (Boolean) False
'--------------------------------------------------

long2113 = settingRepository1.GetAttr("SEEBECKCOEFFICIENT")
'--------------------------------------------------
' Parameter 1 : (String) "SEEBECKCOEFFICIENT"
' Returned value : (Variant) (Long) 1
'--------------------------------------------------

Dim bSTR4225
bSTR4225 = ""
Dim bSTR4226
bSTR4226 = ""
Dim boolean2113
settingRepository1.GetAttrInfo "SEEBECKCOEFFICIENT", bSTR4225, bSTR4226, boolean2113
'--------------------------------------------------
' Parameter 1 : (String) "SEEBECKCOEFFICIENT"
' Parameter 2 : (String) "Default value"
' Parameter 3 : (String) "Unlocked"
' Parameter 4 : (Boolean) False
'--------------------------------------------------

long2114 = settingRepository1.GetAttr("SEEBECKCOEFFICIENT_Large")
'--------------------------------------------------
' Parameter 1 : (String) "SEEBECKCOEFFICIENT_Large"
' Returned value : (Variant) (Long) 1
'--------------------------------------------------

Dim bSTR4227
bSTR4227 = ""
Dim bSTR4228
bSTR4228 = ""
Dim boolean2114
settingRepository1.GetAttrInfo "SEEBECKCOEFFICIENT_Large", bSTR4227, bSTR4228, boolean2114
'--------------------------------------------------
' Parameter 1 : (String) "SEEBECKCOEFFICIENT_Large"
' Parameter 2 : (String) "Default value"
' Parameter 3 : (String) "Unlocked"
' Parameter 4 : (Boolean) False
'--------------------------------------------------

long2115 = settingRepository1.GetAttr("SEEBECKCOEFFICIENT_ExtraLarge")
'--------------------------------------------------
' Parameter 1 : (String) "SEEBECKCOEFFICIENT_ExtraLarge"
' Returned value : (Variant) (Long) 1
'--------------------------------------------------

Dim bSTR4229
bSTR4229 = ""
Dim bSTR4230
bSTR4230 = ""
Dim boolean2115
settingRepository1.GetAttrInfo "SEEBECKCOEFFICIENT_ExtraLarge", bSTR4229, bSTR4230, boolean2115
'--------------------------------------------------
' Parameter 1 : (String) "SEEBECKCOEFFICIENT_ExtraLarge"
' Parameter 2 : (String) "Default value"
' Parameter 3 : (String) "Unlocked"
' Parameter 4 : (Boolean) False
'--------------------------------------------------

long2116 = settingRepository1.GetAttr("SEEBECKCOEFFICIENT_Small")
'--------------------------------------------------
' Parameter 1 : (String) "SEEBECKCOEFFICIENT_Small"
' Returned value : (Variant) (Long) 1
'--------------------------------------------------

Dim bSTR4231
bSTR4231 = ""
Dim bSTR4232
bSTR4232 = ""
Dim boolean2116
settingRepository1.GetAttrInfo "SEEBECKCOEFFICIENT_Small", bSTR4231, bSTR4232, boolean2116
'--------------------------------------------------
' Parameter 1 : (String) "SEEBECKCOEFFICIENT_Small"
' Parameter 2 : (String) "Default value"
' Parameter 3 : (String) "Unlocked"
' Parameter 4 : (Boolean) False
'--------------------------------------------------

long2117 = settingRepository1.GetAttr("SEEBECKCOEFFICIENT_ExtraSmall")
'--------------------------------------------------
' Parameter 1 : (String) "SEEBECKCOEFFICIENT_ExtraSmall"
' Returned value : (Variant) (Long) 1
'--------------------------------------------------

Dim bSTR4233
bSTR4233 = ""
Dim bSTR4234
bSTR4234 = ""
Dim boolean2117
settingRepository1.GetAttrInfo "SEEBECKCOEFFICIENT_ExtraSmall", bSTR4233, bSTR4234, boolean2117
'--------------------------------------------------
' Parameter 1 : (String) "SEEBECKCOEFFICIENT_ExtraSmall"
' Parameter 2 : (String) "Default value"
' Parameter 3 : (String) "Unlocked"
' Parameter 4 : (Boolean) False
'--------------------------------------------------

long2118 = settingRepository1.GetAttr("SEEBECKCOEFFICIENT_Nanometric")
'--------------------------------------------------
' Parameter 1 : (String) "SEEBECKCOEFFICIENT_Nanometric"
' Returned value : (Variant) (Long) 1
'--------------------------------------------------

Dim bSTR4235
bSTR4235 = ""
Dim bSTR4236
bSTR4236 = ""
Dim boolean2118
settingRepository1.GetAttrInfo "SEEBECKCOEFFICIENT_Nanometric", bSTR4235, bSTR4236, boolean2118
'--------------------------------------------------
' Parameter 1 : (String) "SEEBECKCOEFFICIENT_Nanometric"
' Parameter 2 : (String) "Default value"
' Parameter 3 : (String) "Unlocked"
' Parameter 4 : (Boolean) False
'--------------------------------------------------

long2119 = settingRepository1.GetAttr("THOMSONCOEFFICIENT")
'--------------------------------------------------
' Parameter 1 : (String) "THOMSONCOEFFICIENT"
' Returned value : (Variant) (Long) 1
'--------------------------------------------------

Dim bSTR4237
bSTR4237 = ""
Dim bSTR4238
bSTR4238 = ""
Dim boolean2119
settingRepository1.GetAttrInfo "THOMSONCOEFFICIENT", bSTR4237, bSTR4238, boolean2119
'--------------------------------------------------
' Parameter 1 : (String) "THOMSONCOEFFICIENT"
' Parameter 2 : (String) "Default value"
' Parameter 3 : (String) "Unlocked"
' Parameter 4 : (Boolean) False
'--------------------------------------------------

long2120 = settingRepository1.GetAttr("THOMSONCOEFFICIENT_Large")
'--------------------------------------------------
' Parameter 1 : (String) "THOMSONCOEFFICIENT_Large"
' Returned value : (Variant) (Long) 1
'--------------------------------------------------

Dim bSTR4239
bSTR4239 = ""
Dim bSTR4240
bSTR4240 = ""
Dim boolean2120
settingRepository1.GetAttrInfo "THOMSONCOEFFICIENT_Large", bSTR4239, bSTR4240, boolean2120
'--------------------------------------------------
' Parameter 1 : (String) "THOMSONCOEFFICIENT_Large"
' Parameter 2 : (String) "Default value"
' Parameter 3 : (String) "Unlocked"
' Parameter 4 : (Boolean) False
'--------------------------------------------------

long2121 = settingRepository1.GetAttr("THOMSONCOEFFICIENT_ExtraLarge")
'--------------------------------------------------
' Parameter 1 : (String) "THOMSONCOEFFICIENT_ExtraLarge"
' Returned value : (Variant) (Long) 1
'--------------------------------------------------

Dim bSTR4241
bSTR4241 = ""
Dim bSTR4242
bSTR4242 = ""
Dim boolean2121
settingRepository1.GetAttrInfo "THOMSONCOEFFICIENT_ExtraLarge", bSTR4241, bSTR4242, boolean2121
'--------------------------------------------------
' Parameter 1 : (String) "THOMSONCOEFFICIENT_ExtraLarge"
' Parameter 2 : (String) "Default value"
' Parameter 3 : (String) "Unlocked"
' Parameter 4 : (Boolean) False
'--------------------------------------------------

long2122 = settingRepository1.GetAttr("THOMSONCOEFFICIENT_Small")
'--------------------------------------------------
' Parameter 1 : (String) "THOMSONCOEFFICIENT_Small"
' Returned value : (Variant) (Long) 1
'--------------------------------------------------

Dim bSTR4243
bSTR4243 = ""
Dim bSTR4244
bSTR4244 = ""
Dim boolean2122
settingRepository1.GetAttrInfo "THOMSONCOEFFICIENT_Small", bSTR4243, bSTR4244, boolean2122
'--------------------------------------------------
' Parameter 1 : (String) "THOMSONCOEFFICIENT_Small"
' Parameter 2 : (String) "Default value"
' Parameter 3 : (String) "Unlocked"
' Parameter 4 : (Boolean) False
'--------------------------------------------------

long2123 = settingRepository1.GetAttr("THOMSONCOEFFICIENT_ExtraSmall")
'--------------------------------------------------
' Parameter 1 : (String) "THOMSONCOEFFICIENT_ExtraSmall"
' Returned value : (Variant) (Long) 1
'--------------------------------------------------

Dim bSTR4245
bSTR4245 = ""
Dim bSTR4246
bSTR4246 = ""
Dim boolean2123
settingRepository1.GetAttrInfo "THOMSONCOEFFICIENT_ExtraSmall", bSTR4245, bSTR4246, boolean2123
'--------------------------------------------------
' Parameter 1 : (String) "THOMSONCOEFFICIENT_ExtraSmall"
' Parameter 2 : (String) "Default value"
' Parameter 3 : (String) "Unlocked"
' Parameter 4 : (Boolean) False
'--------------------------------------------------

long2124 = settingRepository1.GetAttr("THOMSONCOEFFICIENT_Nanometric")
'--------------------------------------------------
' Parameter 1 : (String) "THOMSONCOEFFICIENT_Nanometric"
' Returned value : (Variant) (Long) 1
'--------------------------------------------------

Dim bSTR4247
bSTR4247 = ""
Dim bSTR4248
bSTR4248 = ""
Dim boolean2124
settingRepository1.GetAttrInfo "THOMSONCOEFFICIENT_Nanometric", bSTR4247, bSTR4248, boolean2124
'--------------------------------------------------
' Parameter 1 : (String) "THOMSONCOEFFICIENT_Nanometric"
' Parameter 2 : (String) "Default value"
' Parameter 3 : (String) "Unlocked"
' Parameter 4 : (Boolean) False
'--------------------------------------------------

long2125 = settingRepository1.GetAttr("RICHARDSONCONSTANT")
'--------------------------------------------------
' Parameter 1 : (String) "RICHARDSONCONSTANT"
' Returned value : (Variant) (Long) 1
'--------------------------------------------------

Dim bSTR4249
bSTR4249 = ""
Dim bSTR4250
bSTR4250 = ""
Dim boolean2125
settingRepository1.GetAttrInfo "RICHARDSONCONSTANT", bSTR4249, bSTR4250, boolean2125
'--------------------------------------------------
' Parameter 1 : (String) "RICHARDSONCONSTANT"
' Parameter 2 : (String) "Default value"
' Parameter 3 : (String) "Unlocked"
' Parameter 4 : (Boolean) False
'--------------------------------------------------

long2126 = settingRepository1.GetAttr("RICHARDSONCONSTANT_Large")
'--------------------------------------------------
' Parameter 1 : (String) "RICHARDSONCONSTANT_Large"
' Returned value : (Variant) (Long) 1
'--------------------------------------------------

Dim bSTR4251
bSTR4251 = ""
Dim bSTR4252
bSTR4252 = ""
Dim boolean2126
settingRepository1.GetAttrInfo "RICHARDSONCONSTANT_Large", bSTR4251, bSTR4252, boolean2126
'--------------------------------------------------
' Parameter 1 : (String) "RICHARDSONCONSTANT_Large"
' Parameter 2 : (String) "Default value"
' Parameter 3 : (String) "Unlocked"
' Parameter 4 : (Boolean) False
'--------------------------------------------------

long2127 = settingRepository1.GetAttr("RICHARDSONCONSTANT_ExtraLarge")
'--------------------------------------------------
' Parameter 1 : (String) "RICHARDSONCONSTANT_ExtraLarge"
' Returned value : (Variant) (Long) 1
'--------------------------------------------------

Dim bSTR4253
bSTR4253 = ""
Dim bSTR4254
bSTR4254 = ""
Dim boolean2127
settingRepository1.GetAttrInfo "RICHARDSONCONSTANT_ExtraLarge", bSTR4253, bSTR4254, boolean2127
'--------------------------------------------------
' Parameter 1 : (String) "RICHARDSONCONSTANT_ExtraLarge"
' Parameter 2 : (String) "Default value"
' Parameter 3 : (String) "Unlocked"
' Parameter 4 : (Boolean) False
'--------------------------------------------------

long2128 = settingRepository1.GetAttr("RICHARDSONCONSTANT_Small")
'--------------------------------------------------
' Parameter 1 : (String) "RICHARDSONCONSTANT_Small"
' Returned value : (Variant) (Long) 1
'--------------------------------------------------

Dim bSTR4255
bSTR4255 = ""
Dim bSTR4256
bSTR4256 = ""
Dim boolean2128
settingRepository1.GetAttrInfo "RICHARDSONCONSTANT_Small", bSTR4255, bSTR4256, boolean2128
'--------------------------------------------------
' Parameter 1 : (String) "RICHARDSONCONSTANT_Small"
' Parameter 2 : (String) "Default value"
' Parameter 3 : (String) "Unlocked"
' Parameter 4 : (Boolean) False
'--------------------------------------------------

long2129 = settingRepository1.GetAttr("RICHARDSONCONSTANT_ExtraSmall")
'--------------------------------------------------
' Parameter 1 : (String) "RICHARDSONCONSTANT_ExtraSmall"
' Returned value : (Variant) (Long) 1
'--------------------------------------------------

Dim bSTR4257
bSTR4257 = ""
Dim bSTR4258
bSTR4258 = ""
Dim boolean2129
settingRepository1.GetAttrInfo "RICHARDSONCONSTANT_ExtraSmall", bSTR4257, bSTR4258, boolean2129
'--------------------------------------------------
' Parameter 1 : (String) "RICHARDSONCONSTANT_ExtraSmall"
' Parameter 2 : (String) "Default value"
' Parameter 3 : (String) "Unlocked"
' Parameter 4 : (Boolean) False
'--------------------------------------------------

long2130 = settingRepository1.GetAttr("RICHARDSONCONSTANT_Nanometric")
'--------------------------------------------------
' Parameter 1 : (String) "RICHARDSONCONSTANT_Nanometric"
' Returned value : (Variant) (Long) 1
'--------------------------------------------------

Dim bSTR4259
bSTR4259 = ""
Dim bSTR4260
bSTR4260 = ""
Dim boolean2130
settingRepository1.GetAttrInfo "RICHARDSONCONSTANT_Nanometric", bSTR4259, bSTR4260, boolean2130
'--------------------------------------------------
' Parameter 1 : (String) "RICHARDSONCONSTANT_Nanometric"
' Parameter 2 : (String) "Default value"
' Parameter 3 : (String) "Unlocked"
' Parameter 4 : (Boolean) False
'--------------------------------------------------

long2131 = settingRepository1.GetAttr("FERMIENERGY")
'--------------------------------------------------
' Parameter 1 : (String) "FERMIENERGY"
' Returned value : (Variant) (Long) 1
'--------------------------------------------------

Dim bSTR4261
bSTR4261 = ""
Dim bSTR4262
bSTR4262 = ""
Dim boolean2131
settingRepository1.GetAttrInfo "FERMIENERGY", bSTR4261, bSTR4262, boolean2131
'--------------------------------------------------
' Parameter 1 : (String) "FERMIENERGY"
' Parameter 2 : (String) "Default value"
' Parameter 3 : (String) "Unlocked"
' Parameter 4 : (Boolean) False
'--------------------------------------------------

long2132 = settingRepository1.GetAttr("FERMIENERGY_Large")
'--------------------------------------------------
' Parameter 1 : (String) "FERMIENERGY_Large"
' Returned value : (Variant) (Long) 1
'--------------------------------------------------

Dim bSTR4263
bSTR4263 = ""
Dim bSTR4264
bSTR4264 = ""
Dim boolean2132
settingRepository1.GetAttrInfo "FERMIENERGY_Large", bSTR4263, bSTR4264, boolean2132
'--------------------------------------------------
' Parameter 1 : (String) "FERMIENERGY_Large"
' Parameter 2 : (String) "Default value"
' Parameter 3 : (String) "Unlocked"
' Parameter 4 : (Boolean) False
'--------------------------------------------------

long2133 = settingRepository1.GetAttr("FERMIENERGY_ExtraLarge")
'--------------------------------------------------
' Parameter 1 : (String) "FERMIENERGY_ExtraLarge"
' Returned value : (Variant) (Long) 1
'--------------------------------------------------

Dim bSTR4265
bSTR4265 = ""
Dim bSTR4266
bSTR4266 = ""
Dim boolean2133
settingRepository1.GetAttrInfo "FERMIENERGY_ExtraLarge", bSTR4265, bSTR4266, boolean2133
'--------------------------------------------------
' Parameter 1 : (String) "FERMIENERGY_ExtraLarge"
' Parameter 2 : (String) "Default value"
' Parameter 3 : (String) "Unlocked"
' Parameter 4 : (Boolean) False
'--------------------------------------------------

long2134 = settingRepository1.GetAttr("FERMIENERGY_Small")
'--------------------------------------------------
' Parameter 1 : (String) "FERMIENERGY_Small"
' Returned value : (Variant) (Long) 1
'--------------------------------------------------

Dim bSTR4267
bSTR4267 = ""
Dim bSTR4268
bSTR4268 = ""
Dim boolean2134
settingRepository1.GetAttrInfo "FERMIENERGY_Small", bSTR4267, bSTR4268, boolean2134
'--------------------------------------------------
' Parameter 1 : (String) "FERMIENERGY_Small"
' Parameter 2 : (String) "Default value"
' Parameter 3 : (String) "Unlocked"
' Parameter 4 : (Boolean) False
'--------------------------------------------------

long2135 = settingRepository1.GetAttr("FERMIENERGY_ExtraSmall")
'--------------------------------------------------
' Parameter 1 : (String) "FERMIENERGY_ExtraSmall"
' Returned value : (Variant) (Long) 1
'--------------------------------------------------

Dim bSTR4269
bSTR4269 = ""
Dim bSTR4270
bSTR4270 = ""
Dim boolean2135
settingRepository1.GetAttrInfo "FERMIENERGY_ExtraSmall", bSTR4269, bSTR4270, boolean2135
'--------------------------------------------------
' Parameter 1 : (String) "FERMIENERGY_ExtraSmall"
' Parameter 2 : (String) "Default value"
' Parameter 3 : (String) "Unlocked"
' Parameter 4 : (Boolean) False
'--------------------------------------------------

long2136 = settingRepository1.GetAttr("FERMIENERGY_Nanometric")
'--------------------------------------------------
' Parameter 1 : (String) "FERMIENERGY_Nanometric"
' Returned value : (Variant) (Long) 1
'--------------------------------------------------

Dim bSTR4271
bSTR4271 = ""
Dim bSTR4272
bSTR4272 = ""
Dim boolean2136
settingRepository1.GetAttrInfo "FERMIENERGY_Nanometric", bSTR4271, bSTR4272, boolean2136
'--------------------------------------------------
' Parameter 1 : (String) "FERMIENERGY_Nanometric"
' Parameter 2 : (String) "Default value"
' Parameter 3 : (String) "Unlocked"
' Parameter 4 : (Boolean) False
'--------------------------------------------------

long2137 = settingRepository1.GetAttr("FLUXIODQUANTUM")
'--------------------------------------------------
' Parameter 1 : (String) "FLUXIODQUANTUM"
' Returned value : (Variant) (Long) 1
'--------------------------------------------------

Dim bSTR4273
bSTR4273 = ""
Dim bSTR4274
bSTR4274 = ""
Dim boolean2137
settingRepository1.GetAttrInfo "FLUXIODQUANTUM", bSTR4273, bSTR4274, boolean2137
'--------------------------------------------------
' Parameter 1 : (String) "FLUXIODQUANTUM"
' Parameter 2 : (String) "Default value"
' Parameter 3 : (String) "Unlocked"
' Parameter 4 : (Boolean) False
'--------------------------------------------------

long2138 = settingRepository1.GetAttr("FLUXIODQUANTUM_Large")
'--------------------------------------------------
' Parameter 1 : (String) "FLUXIODQUANTUM_Large"
' Returned value : (Variant) (Long) 1
'--------------------------------------------------

Dim bSTR4275
bSTR4275 = ""
Dim bSTR4276
bSTR4276 = ""
Dim boolean2138
settingRepository1.GetAttrInfo "FLUXIODQUANTUM_Large", bSTR4275, bSTR4276, boolean2138
'--------------------------------------------------
' Parameter 1 : (String) "FLUXIODQUANTUM_Large"
' Parameter 2 : (String) "Default value"
' Parameter 3 : (String) "Unlocked"
' Parameter 4 : (Boolean) False
'--------------------------------------------------

long2139 = settingRepository1.GetAttr("FLUXIODQUANTUM_ExtraLarge")
'--------------------------------------------------
' Parameter 1 : (String) "FLUXIODQUANTUM_ExtraLarge"
' Returned value : (Variant) (Long) 1
'--------------------------------------------------

Dim bSTR4277
bSTR4277 = ""
Dim bSTR4278
bSTR4278 = ""
Dim boolean2139
settingRepository1.GetAttrInfo "FLUXIODQUANTUM_ExtraLarge", bSTR4277, bSTR4278, boolean2139
'--------------------------------------------------
' Parameter 1 : (String) "FLUXIODQUANTUM_ExtraLarge"
' Parameter 2 : (String) "Default value"
' Parameter 3 : (String) "Unlocked"
' Parameter 4 : (Boolean) False
'--------------------------------------------------

long2140 = settingRepository1.GetAttr("FLUXIODQUANTUM_Small")
'--------------------------------------------------
' Parameter 1 : (String) "FLUXIODQUANTUM_Small"
' Returned value : (Variant) (Long) 1
'--------------------------------------------------

Dim bSTR4279
bSTR4279 = ""
Dim bSTR4280
bSTR4280 = ""
Dim boolean2140
settingRepository1.GetAttrInfo "FLUXIODQUANTUM_Small", bSTR4279, bSTR4280, boolean2140
'--------------------------------------------------
' Parameter 1 : (String) "FLUXIODQUANTUM_Small"
' Parameter 2 : (String) "Default value"
' Parameter 3 : (String) "Unlocked"
' Parameter 4 : (Boolean) False
'--------------------------------------------------

long2141 = settingRepository1.GetAttr("FLUXIODQUANTUM_ExtraSmall")
'--------------------------------------------------
' Parameter 1 : (String) "FLUXIODQUANTUM_ExtraSmall"
' Returned value : (Variant) (Long) 1
'--------------------------------------------------

Dim bSTR4281
bSTR4281 = ""
Dim bSTR4282
bSTR4282 = ""
Dim boolean2141
settingRepository1.GetAttrInfo "FLUXIODQUANTUM_ExtraSmall", bSTR4281, bSTR4282, boolean2141
'--------------------------------------------------
' Parameter 1 : (String) "FLUXIODQUANTUM_ExtraSmall"
' Parameter 2 : (String) "Default value"
' Parameter 3 : (String) "Unlocked"
' Parameter 4 : (Boolean) False
'--------------------------------------------------

long2142 = settingRepository1.GetAttr("FLUXIODQUANTUM_Nanometric")
'--------------------------------------------------
' Parameter 1 : (String) "FLUXIODQUANTUM_Nanometric"
' Returned value : (Variant) (Long) 1
'--------------------------------------------------

Dim bSTR4283
bSTR4283 = ""
Dim bSTR4284
bSTR4284 = ""
Dim boolean2142
settingRepository1.GetAttrInfo "FLUXIODQUANTUM_Nanometric", bSTR4283, bSTR4284, boolean2142
'--------------------------------------------------
' Parameter 1 : (String) "FLUXIODQUANTUM_Nanometric"
' Parameter 2 : (String) "Default value"
' Parameter 3 : (String) "Unlocked"
' Parameter 4 : (Boolean) False
'--------------------------------------------------

long2143 = settingRepository1.GetAttr("SURFACE_POWER_DENSITY")
'--------------------------------------------------
' Parameter 1 : (String) "SURFACE_POWER_DENSITY"
' Returned value : (Variant) (Long) 1
'--------------------------------------------------

Dim bSTR4285
bSTR4285 = ""
Dim bSTR4286
bSTR4286 = ""
Dim boolean2143
settingRepository1.GetAttrInfo "SURFACE_POWER_DENSITY", bSTR4285, bSTR4286, boolean2143
'--------------------------------------------------
' Parameter 1 : (String) "SURFACE_POWER_DENSITY"
' Parameter 2 : (String) "Default value"
' Parameter 3 : (String) "Unlocked"
' Parameter 4 : (Boolean) False
'--------------------------------------------------

long2144 = settingRepository1.GetAttr("SURFACE_POWER_DENSITY_Large")
'--------------------------------------------------
' Parameter 1 : (String) "SURFACE_POWER_DENSITY_Large"
' Returned value : (Variant) (Long) 1
'--------------------------------------------------

Dim bSTR4287
bSTR4287 = ""
Dim bSTR4288
bSTR4288 = ""
Dim boolean2144
settingRepository1.GetAttrInfo "SURFACE_POWER_DENSITY_Large", bSTR4287, bSTR4288, boolean2144
'--------------------------------------------------
' Parameter 1 : (String) "SURFACE_POWER_DENSITY_Large"
' Parameter 2 : (String) "Default value"
' Parameter 3 : (String) "Unlocked"
' Parameter 4 : (Boolean) False
'--------------------------------------------------

long2145 = settingRepository1.GetAttr("SURFACE_POWER_DENSITY_ExtraLarge")
'--------------------------------------------------
' Parameter 1 : (String) "SURFACE_POWER_DENSITY_ExtraLarge"
' Returned value : (Variant) (Long) 1
'--------------------------------------------------

Dim bSTR4289
bSTR4289 = ""
Dim bSTR4290
bSTR4290 = ""
Dim boolean2145
settingRepository1.GetAttrInfo "SURFACE_POWER_DENSITY_ExtraLarge", bSTR4289, bSTR4290, boolean2145
'--------------------------------------------------
' Parameter 1 : (String) "SURFACE_POWER_DENSITY_ExtraLarge"
' Parameter 2 : (String) "Default value"
' Parameter 3 : (String) "Unlocked"
' Parameter 4 : (Boolean) False
'--------------------------------------------------

long2146 = settingRepository1.GetAttr("SURFACE_POWER_DENSITY_Small")
'--------------------------------------------------
' Parameter 1 : (String) "SURFACE_POWER_DENSITY_Small"
' Returned value : (Variant) (Long) 1
'--------------------------------------------------

Dim bSTR4291
bSTR4291 = ""
Dim bSTR4292
bSTR4292 = ""
Dim boolean2146
settingRepository1.GetAttrInfo "SURFACE_POWER_DENSITY_Small", bSTR4291, bSTR4292, boolean2146
'--------------------------------------------------
' Parameter 1 : (String) "SURFACE_POWER_DENSITY_Small"
' Parameter 2 : (String) "Default value"
' Parameter 3 : (String) "Unlocked"
' Parameter 4 : (Boolean) False
'--------------------------------------------------

long2147 = settingRepository1.GetAttr("SURFACE_POWER_DENSITY_ExtraSmall")
'--------------------------------------------------
' Parameter 1 : (String) "SURFACE_POWER_DENSITY_ExtraSmall"
' Returned value : (Variant) (Long) 1
'--------------------------------------------------

Dim bSTR4293
bSTR4293 = ""
Dim bSTR4294
bSTR4294 = ""
Dim boolean2147
settingRepository1.GetAttrInfo "SURFACE_POWER_DENSITY_ExtraSmall", bSTR4293, bSTR4294, boolean2147
'--------------------------------------------------
' Parameter 1 : (String) "SURFACE_POWER_DENSITY_ExtraSmall"
' Parameter 2 : (String) "Default value"
' Parameter 3 : (String) "Unlocked"
' Parameter 4 : (Boolean) False
'--------------------------------------------------

long2148 = settingRepository1.GetAttr("SURFACE_POWER_DENSITY_Nanometric")
'--------------------------------------------------
' Parameter 1 : (String) "SURFACE_POWER_DENSITY_Nanometric"
' Returned value : (Variant) (Long) 1
'--------------------------------------------------

Dim bSTR4295
bSTR4295 = ""
Dim bSTR4296
bSTR4296 = ""
Dim boolean2148
settingRepository1.GetAttrInfo "SURFACE_POWER_DENSITY_Nanometric", bSTR4295, bSTR4296, boolean2148
'--------------------------------------------------
' Parameter 1 : (String) "SURFACE_POWER_DENSITY_Nanometric"
' Parameter 2 : (String) "Default value"
' Parameter 3 : (String) "Unlocked"
' Parameter 4 : (Boolean) False
'--------------------------------------------------

long2149 = settingRepository1.GetAttr("POWER_DENSITY")
'--------------------------------------------------
' Parameter 1 : (String) "POWER_DENSITY"
' Returned value : (Variant) (Long) 1
'--------------------------------------------------

Dim bSTR4297
bSTR4297 = ""
Dim bSTR4298
bSTR4298 = ""
Dim boolean2149
settingRepository1.GetAttrInfo "POWER_DENSITY", bSTR4297, bSTR4298, boolean2149
'--------------------------------------------------
' Parameter 1 : (String) "POWER_DENSITY"
' Parameter 2 : (String) "Default value"
' Parameter 3 : (String) "Unlocked"
' Parameter 4 : (Boolean) False
'--------------------------------------------------

long2150 = settingRepository1.GetAttr("POWER_DENSITY_Large")
'--------------------------------------------------
' Parameter 1 : (String) "POWER_DENSITY_Large"
' Returned value : (Variant) (Long) 1
'--------------------------------------------------

Dim bSTR4299
bSTR4299 = ""
Dim bSTR4300
bSTR4300 = ""
Dim boolean2150
settingRepository1.GetAttrInfo "POWER_DENSITY_Large", bSTR4299, bSTR4300, boolean2150
'--------------------------------------------------
' Parameter 1 : (String) "POWER_DENSITY_Large"
' Parameter 2 : (String) "Default value"
' Parameter 3 : (String) "Unlocked"
' Parameter 4 : (Boolean) False
'--------------------------------------------------

long2151 = settingRepository1.GetAttr("POWER_DENSITY_ExtraLarge")
'--------------------------------------------------
' Parameter 1 : (String) "POWER_DENSITY_ExtraLarge"
' Returned value : (Variant) (Long) 1
'--------------------------------------------------

Dim bSTR4301
bSTR4301 = ""
Dim bSTR4302
bSTR4302 = ""
Dim boolean2151
settingRepository1.GetAttrInfo "POWER_DENSITY_ExtraLarge", bSTR4301, bSTR4302, boolean2151
'--------------------------------------------------
' Parameter 1 : (String) "POWER_DENSITY_ExtraLarge"
' Parameter 2 : (String) "Default value"
' Parameter 3 : (String) "Unlocked"
' Parameter 4 : (Boolean) False
'--------------------------------------------------

long2152 = settingRepository1.GetAttr("POWER_DENSITY_Small")
'--------------------------------------------------
' Parameter 1 : (String) "POWER_DENSITY_Small"
' Returned value : (Variant) (Long) 1
'--------------------------------------------------

Dim bSTR4303
bSTR4303 = ""
Dim bSTR4304
bSTR4304 = ""
Dim boolean2152
settingRepository1.GetAttrInfo "POWER_DENSITY_Small", bSTR4303, bSTR4304, boolean2152
'--------------------------------------------------
' Parameter 1 : (String) "POWER_DENSITY_Small"
' Parameter 2 : (String) "Default value"
' Parameter 3 : (String) "Unlocked"
' Parameter 4 : (Boolean) False
'--------------------------------------------------

long2153 = settingRepository1.GetAttr("POWER_DENSITY_ExtraSmall")
'--------------------------------------------------
' Parameter 1 : (String) "POWER_DENSITY_ExtraSmall"
' Returned value : (Variant) (Long) 1
'--------------------------------------------------

Dim bSTR4305
bSTR4305 = ""
Dim bSTR4306
bSTR4306 = ""
Dim boolean2153
settingRepository1.GetAttrInfo "POWER_DENSITY_ExtraSmall", bSTR4305, bSTR4306, boolean2153
'--------------------------------------------------
' Parameter 1 : (String) "POWER_DENSITY_ExtraSmall"
' Parameter 2 : (String) "Default value"
' Parameter 3 : (String) "Unlocked"
' Parameter 4 : (Boolean) False
'--------------------------------------------------

long2154 = settingRepository1.GetAttr("POWER_DENSITY_Nanometric")
'--------------------------------------------------
' Parameter 1 : (String) "POWER_DENSITY_Nanometric"
' Returned value : (Variant) (Long) 1
'--------------------------------------------------

Dim bSTR4307
bSTR4307 = ""
Dim bSTR4308
bSTR4308 = ""
Dim boolean2154
settingRepository1.GetAttrInfo "POWER_DENSITY_Nanometric", bSTR4307, bSTR4308, boolean2154
'--------------------------------------------------
' Parameter 1 : (String) "POWER_DENSITY_Nanometric"
' Parameter 2 : (String) "Default value"
' Parameter 3 : (String) "Unlocked"
' Parameter 4 : (Boolean) False
'--------------------------------------------------

long2155 = settingRepository1.GetAttr("DISPLACEMENT_OVER_VOLTAGE")
'--------------------------------------------------
' Parameter 1 : (String) "DISPLACEMENT_OVER_VOLTAGE"
' Returned value : (Variant) (Long) 1
'--------------------------------------------------

Dim bSTR4309
bSTR4309 = ""
Dim bSTR4310
bSTR4310 = ""
Dim boolean2155
settingRepository1.GetAttrInfo "DISPLACEMENT_OVER_VOLTAGE", bSTR4309, bSTR4310, boolean2155
'--------------------------------------------------
' Parameter 1 : (String) "DISPLACEMENT_OVER_VOLTAGE"
' Parameter 2 : (String) "Default value"
' Parameter 3 : (String) "Unlocked"
' Parameter 4 : (Boolean) False
'--------------------------------------------------

long2156 = settingRepository1.GetAttr("DISPLACEMENT_OVER_VOLTAGE_Large")
'--------------------------------------------------
' Parameter 1 : (String) "DISPLACEMENT_OVER_VOLTAGE_Large"
' Returned value : (Variant) (Long) 1
'--------------------------------------------------

Dim bSTR4311
bSTR4311 = ""
Dim bSTR4312
bSTR4312 = ""
Dim boolean2156
settingRepository1.GetAttrInfo "DISPLACEMENT_OVER_VOLTAGE_Large", bSTR4311, bSTR4312, boolean2156
'--------------------------------------------------
' Parameter 1 : (String) "DISPLACEMENT_OVER_VOLTAGE_Large"
' Parameter 2 : (String) "Default value"
' Parameter 3 : (String) "Unlocked"
' Parameter 4 : (Boolean) False
'--------------------------------------------------

long2157 = settingRepository1.GetAttr("DISPLACEMENT_OVER_VOLTAGE_ExtraLarge")
'--------------------------------------------------
' Parameter 1 : (String) "DISPLACEMENT_OVER_VOLTAGE_ExtraLarge"
' Returned value : (Variant) (Long) 1
'--------------------------------------------------

Dim bSTR4313
bSTR4313 = ""
Dim bSTR4314
bSTR4314 = ""
Dim boolean2157
settingRepository1.GetAttrInfo "DISPLACEMENT_OVER_VOLTAGE_ExtraLarge", bSTR4313, bSTR4314, boolean2157
'--------------------------------------------------
' Parameter 1 : (String) "DISPLACEMENT_OVER_VOLTAGE_ExtraLarge"
' Parameter 2 : (String) "Default value"
' Parameter 3 : (String) "Unlocked"
' Parameter 4 : (Boolean) False
'--------------------------------------------------

long2158 = settingRepository1.GetAttr("DISPLACEMENT_OVER_VOLTAGE_Small")
'--------------------------------------------------
' Parameter 1 : (String) "DISPLACEMENT_OVER_VOLTAGE_Small"
' Returned value : (Variant) (Long) 1
'--------------------------------------------------

Dim bSTR4315
bSTR4315 = ""
Dim bSTR4316
bSTR4316 = ""
Dim boolean2158
settingRepository1.GetAttrInfo "DISPLACEMENT_OVER_VOLTAGE_Small", bSTR4315, bSTR4316, boolean2158
'--------------------------------------------------
' Parameter 1 : (String) "DISPLACEMENT_OVER_VOLTAGE_Small"
' Parameter 2 : (String) "Default value"
' Parameter 3 : (String) "Unlocked"
' Parameter 4 : (Boolean) False
'--------------------------------------------------

long2159 = settingRepository1.GetAttr("DISPLACEMENT_OVER_VOLTAGE_ExtraSmall")
'--------------------------------------------------
' Parameter 1 : (String) "DISPLACEMENT_OVER_VOLTAGE_ExtraSmall"
' Returned value : (Variant) (Long) 1
'--------------------------------------------------

Dim bSTR4317
bSTR4317 = ""
Dim bSTR4318
bSTR4318 = ""
Dim boolean2159
settingRepository1.GetAttrInfo "DISPLACEMENT_OVER_VOLTAGE_ExtraSmall", bSTR4317, bSTR4318, boolean2159
'--------------------------------------------------
' Parameter 1 : (String) "DISPLACEMENT_OVER_VOLTAGE_ExtraSmall"
' Parameter 2 : (String) "Default value"
' Parameter 3 : (String) "Unlocked"
' Parameter 4 : (Boolean) False
'--------------------------------------------------

long2160 = settingRepository1.GetAttr("DISPLACEMENT_OVER_VOLTAGE_Nanometric")
'--------------------------------------------------
' Parameter 1 : (String) "DISPLACEMENT_OVER_VOLTAGE_Nanometric"
' Returned value : (Variant) (Long) 1
'--------------------------------------------------

Dim bSTR4319
bSTR4319 = ""
Dim bSTR4320
bSTR4320 = ""
Dim boolean2160
settingRepository1.GetAttrInfo "DISPLACEMENT_OVER_VOLTAGE_Nanometric", bSTR4319, bSTR4320, boolean2160
'--------------------------------------------------
' Parameter 1 : (String) "DISPLACEMENT_OVER_VOLTAGE_Nanometric"
' Parameter 2 : (String) "Default value"
' Parameter 3 : (String) "Unlocked"
' Parameter 4 : (Boolean) False
'--------------------------------------------------

long2161 = settingRepository1.GetAttr("VELOCITY_OVER_VOLTAGE")
'--------------------------------------------------
' Parameter 1 : (String) "VELOCITY_OVER_VOLTAGE"
' Returned value : (Variant) (Long) 1
'--------------------------------------------------

Dim bSTR4321
bSTR4321 = ""
Dim bSTR4322
bSTR4322 = ""
Dim boolean2161
settingRepository1.GetAttrInfo "VELOCITY_OVER_VOLTAGE", bSTR4321, bSTR4322, boolean2161
'--------------------------------------------------
' Parameter 1 : (String) "VELOCITY_OVER_VOLTAGE"
' Parameter 2 : (String) "Default value"
' Parameter 3 : (String) "Unlocked"
' Parameter 4 : (Boolean) False
'--------------------------------------------------

long2162 = settingRepository1.GetAttr("VELOCITY_OVER_VOLTAGE_Large")
'--------------------------------------------------
' Parameter 1 : (String) "VELOCITY_OVER_VOLTAGE_Large"
' Returned value : (Variant) (Long) 1
'--------------------------------------------------

Dim bSTR4323
bSTR4323 = ""
Dim bSTR4324
bSTR4324 = ""
Dim boolean2162
settingRepository1.GetAttrInfo "VELOCITY_OVER_VOLTAGE_Large", bSTR4323, bSTR4324, boolean2162
'--------------------------------------------------
' Parameter 1 : (String) "VELOCITY_OVER_VOLTAGE_Large"
' Parameter 2 : (String) "Default value"
' Parameter 3 : (String) "Unlocked"
' Parameter 4 : (Boolean) False
'--------------------------------------------------

long2163 = settingRepository1.GetAttr("VELOCITY_OVER_VOLTAGE_ExtraLarge")
'--------------------------------------------------
' Parameter 1 : (String) "VELOCITY_OVER_VOLTAGE_ExtraLarge"
' Returned value : (Variant) (Long) 1
'--------------------------------------------------

Dim bSTR4325
bSTR4325 = ""
Dim bSTR4326
bSTR4326 = ""
Dim boolean2163
settingRepository1.GetAttrInfo "VELOCITY_OVER_VOLTAGE_ExtraLarge", bSTR4325, bSTR4326, boolean2163
'--------------------------------------------------
' Parameter 1 : (String) "VELOCITY_OVER_VOLTAGE_ExtraLarge"
' Parameter 2 : (String) "Default value"
' Parameter 3 : (String) "Unlocked"
' Parameter 4 : (Boolean) False
'--------------------------------------------------

long2164 = settingRepository1.GetAttr("VELOCITY_OVER_VOLTAGE_Small")
'--------------------------------------------------
' Parameter 1 : (String) "VELOCITY_OVER_VOLTAGE_Small"
' Returned value : (Variant) (Long) 1
'--------------------------------------------------

Dim bSTR4327
bSTR4327 = ""
Dim bSTR4328
bSTR4328 = ""
Dim boolean2164
settingRepository1.GetAttrInfo "VELOCITY_OVER_VOLTAGE_Small", bSTR4327, bSTR4328, boolean2164
'--------------------------------------------------
' Parameter 1 : (String) "VELOCITY_OVER_VOLTAGE_Small"
' Parameter 2 : (String) "Default value"
' Parameter 3 : (String) "Unlocked"
' Parameter 4 : (Boolean) False
'--------------------------------------------------

long2165 = settingRepository1.GetAttr("VELOCITY_OVER_VOLTAGE_ExtraSmall")
'--------------------------------------------------
' Parameter 1 : (String) "VELOCITY_OVER_VOLTAGE_ExtraSmall"
' Returned value : (Variant) (Long) 1
'--------------------------------------------------

Dim bSTR4329
bSTR4329 = ""
Dim bSTR4330
bSTR4330 = ""
Dim boolean2165
settingRepository1.GetAttrInfo "VELOCITY_OVER_VOLTAGE_ExtraSmall", bSTR4329, bSTR4330, boolean2165
'--------------------------------------------------
' Parameter 1 : (String) "VELOCITY_OVER_VOLTAGE_ExtraSmall"
' Parameter 2 : (String) "Default value"
' Parameter 3 : (String) "Unlocked"
' Parameter 4 : (Boolean) False
'--------------------------------------------------

long2166 = settingRepository1.GetAttr("VELOCITY_OVER_VOLTAGE_Nanometric")
'--------------------------------------------------
' Parameter 1 : (String) "VELOCITY_OVER_VOLTAGE_Nanometric"
' Returned value : (Variant) (Long) 1
'--------------------------------------------------

Dim bSTR4331
bSTR4331 = ""
Dim bSTR4332
bSTR4332 = ""
Dim boolean2166
settingRepository1.GetAttrInfo "VELOCITY_OVER_VOLTAGE_Nanometric", bSTR4331, bSTR4332, boolean2166
'--------------------------------------------------
' Parameter 1 : (String) "VELOCITY_OVER_VOLTAGE_Nanometric"
' Parameter 2 : (String) "Default value"
' Parameter 3 : (String) "Unlocked"
' Parameter 4 : (Boolean) False
'--------------------------------------------------

long2167 = settingRepository1.GetAttr("ACCELERATION_OVER_VOLTAGE")
'--------------------------------------------------
' Parameter 1 : (String) "ACCELERATION_OVER_VOLTAGE"
' Returned value : (Variant) (Long) 1
'--------------------------------------------------

Dim bSTR4333
bSTR4333 = ""
Dim bSTR4334
bSTR4334 = ""
Dim boolean2167
settingRepository1.GetAttrInfo "ACCELERATION_OVER_VOLTAGE", bSTR4333, bSTR4334, boolean2167
'--------------------------------------------------
' Parameter 1 : (String) "ACCELERATION_OVER_VOLTAGE"
' Parameter 2 : (String) "Default value"
' Parameter 3 : (String) "Unlocked"
' Parameter 4 : (Boolean) False
'--------------------------------------------------

long2168 = settingRepository1.GetAttr("ACCELERATION_OVER_VOLTAGE_Large")
'--------------------------------------------------
' Parameter 1 : (String) "ACCELERATION_OVER_VOLTAGE_Large"
' Returned value : (Variant) (Long) 1
'--------------------------------------------------

Dim bSTR4335
bSTR4335 = ""
Dim bSTR4336
bSTR4336 = ""
Dim boolean2168
settingRepository1.GetAttrInfo "ACCELERATION_OVER_VOLTAGE_Large", bSTR4335, bSTR4336, boolean2168
'--------------------------------------------------
' Parameter 1 : (String) "ACCELERATION_OVER_VOLTAGE_Large"
' Parameter 2 : (String) "Default value"
' Parameter 3 : (String) "Unlocked"
' Parameter 4 : (Boolean) False
'--------------------------------------------------

long2169 = settingRepository1.GetAttr("ACCELERATION_OVER_VOLTAGE_ExtraLarge")
'--------------------------------------------------
' Parameter 1 : (String) "ACCELERATION_OVER_VOLTAGE_ExtraLarge"
' Returned value : (Variant) (Long) 1
'--------------------------------------------------

Dim bSTR4337
bSTR4337 = ""
Dim bSTR4338
bSTR4338 = ""
Dim boolean2169
settingRepository1.GetAttrInfo "ACCELERATION_OVER_VOLTAGE_ExtraLarge", bSTR4337, bSTR4338, boolean2169
'--------------------------------------------------
' Parameter 1 : (String) "ACCELERATION_OVER_VOLTAGE_ExtraLarge"
' Parameter 2 : (String) "Default value"
' Parameter 3 : (String) "Unlocked"
' Parameter 4 : (Boolean) False
'--------------------------------------------------

long2170 = settingRepository1.GetAttr("ACCELERATION_OVER_VOLTAGE_Small")
'--------------------------------------------------
' Parameter 1 : (String) "ACCELERATION_OVER_VOLTAGE_Small"
' Returned value : (Variant) (Long) 1
'--------------------------------------------------

Dim bSTR4339
bSTR4339 = ""
Dim bSTR4340
bSTR4340 = ""
Dim boolean2170
settingRepository1.GetAttrInfo "ACCELERATION_OVER_VOLTAGE_Small", bSTR4339, bSTR4340, boolean2170
'--------------------------------------------------
' Parameter 1 : (String) "ACCELERATION_OVER_VOLTAGE_Small"
' Parameter 2 : (String) "Default value"
' Parameter 3 : (String) "Unlocked"
' Parameter 4 : (Boolean) False
'--------------------------------------------------

long2171 = settingRepository1.GetAttr("ACCELERATION_OVER_VOLTAGE_ExtraSmall")
'--------------------------------------------------
' Parameter 1 : (String) "ACCELERATION_OVER_VOLTAGE_ExtraSmall"
' Returned value : (Variant) (Long) 1
'--------------------------------------------------

Dim bSTR4341
bSTR4341 = ""
Dim bSTR4342
bSTR4342 = ""
Dim boolean2171
settingRepository1.GetAttrInfo "ACCELERATION_OVER_VOLTAGE_ExtraSmall", bSTR4341, bSTR4342, boolean2171
'--------------------------------------------------
' Parameter 1 : (String) "ACCELERATION_OVER_VOLTAGE_ExtraSmall"
' Parameter 2 : (String) "Default value"
' Parameter 3 : (String) "Unlocked"
' Parameter 4 : (Boolean) False
'--------------------------------------------------

long2172 = settingRepository1.GetAttr("ACCELERATION_OVER_VOLTAGE_Nanometric")
'--------------------------------------------------
' Parameter 1 : (String) "ACCELERATION_OVER_VOLTAGE_Nanometric"
' Returned value : (Variant) (Long) 1
'--------------------------------------------------

Dim bSTR4343
bSTR4343 = ""
Dim bSTR4344
bSTR4344 = ""
Dim boolean2172
settingRepository1.GetAttrInfo "ACCELERATION_OVER_VOLTAGE_Nanometric", bSTR4343, bSTR4344, boolean2172
'--------------------------------------------------
' Parameter 1 : (String) "ACCELERATION_OVER_VOLTAGE_Nanometric"
' Parameter 2 : (String) "Default value"
' Parameter 3 : (String) "Unlocked"
' Parameter 4 : (Boolean) False
'--------------------------------------------------

long2173 = settingRepository1.GetAttr("VOLTAGE_OVER_DISPLACEMENT")
'--------------------------------------------------
' Parameter 1 : (String) "VOLTAGE_OVER_DISPLACEMENT"
' Returned value : (Variant) (Long) 1
'--------------------------------------------------

Dim bSTR4345
bSTR4345 = ""
Dim bSTR4346
bSTR4346 = ""
Dim boolean2173
settingRepository1.GetAttrInfo "VOLTAGE_OVER_DISPLACEMENT", bSTR4345, bSTR4346, boolean2173
'--------------------------------------------------
' Parameter 1 : (String) "VOLTAGE_OVER_DISPLACEMENT"
' Parameter 2 : (String) "Default value"
' Parameter 3 : (String) "Unlocked"
' Parameter 4 : (Boolean) False
'--------------------------------------------------

long2174 = settingRepository1.GetAttr("VOLTAGE_OVER_DISPLACEMENT_Large")
'--------------------------------------------------
' Parameter 1 : (String) "VOLTAGE_OVER_DISPLACEMENT_Large"
' Returned value : (Variant) (Long) 1
'--------------------------------------------------

Dim bSTR4347
bSTR4347 = ""
Dim bSTR4348
bSTR4348 = ""
Dim boolean2174
settingRepository1.GetAttrInfo "VOLTAGE_OVER_DISPLACEMENT_Large", bSTR4347, bSTR4348, boolean2174
'--------------------------------------------------
' Parameter 1 : (String) "VOLTAGE_OVER_DISPLACEMENT_Large"
' Parameter 2 : (String) "Default value"
' Parameter 3 : (String) "Unlocked"
' Parameter 4 : (Boolean) False
'--------------------------------------------------

long2175 = settingRepository1.GetAttr("VOLTAGE_OVER_DISPLACEMENT_ExtraLarge")
'--------------------------------------------------
' Parameter 1 : (String) "VOLTAGE_OVER_DISPLACEMENT_ExtraLarge"
' Returned value : (Variant) (Long) 1
'--------------------------------------------------

Dim bSTR4349
bSTR4349 = ""
Dim bSTR4350
bSTR4350 = ""
Dim boolean2175
settingRepository1.GetAttrInfo "VOLTAGE_OVER_DISPLACEMENT_ExtraLarge", bSTR4349, bSTR4350, boolean2175
'--------------------------------------------------
' Parameter 1 : (String) "VOLTAGE_OVER_DISPLACEMENT_ExtraLarge"
' Parameter 2 : (String) "Default value"
' Parameter 3 : (String) "Unlocked"
' Parameter 4 : (Boolean) False
'--------------------------------------------------

long2176 = settingRepository1.GetAttr("VOLTAGE_OVER_DISPLACEMENT_Small")
'--------------------------------------------------
' Parameter 1 : (String) "VOLTAGE_OVER_DISPLACEMENT_Small"
' Returned value : (Variant) (Long) 1
'--------------------------------------------------

Dim bSTR4351
bSTR4351 = ""
Dim bSTR4352
bSTR4352 = ""
Dim boolean2176
settingRepository1.GetAttrInfo "VOLTAGE_OVER_DISPLACEMENT_Small", bSTR4351, bSTR4352, boolean2176
'--------------------------------------------------
' Parameter 1 : (String) "VOLTAGE_OVER_DISPLACEMENT_Small"
' Parameter 2 : (String) "Default value"
' Parameter 3 : (String) "Unlocked"
' Parameter 4 : (Boolean) False
'--------------------------------------------------

long2177 = settingRepository1.GetAttr("VOLTAGE_OVER_DISPLACEMENT_ExtraSmall")
'--------------------------------------------------
' Parameter 1 : (String) "VOLTAGE_OVER_DISPLACEMENT_ExtraSmall"
' Returned value : (Variant) (Long) 1
'--------------------------------------------------

Dim bSTR4353
bSTR4353 = ""
Dim bSTR4354
bSTR4354 = ""
Dim boolean2177
settingRepository1.GetAttrInfo "VOLTAGE_OVER_DISPLACEMENT_ExtraSmall", bSTR4353, bSTR4354, boolean2177
'--------------------------------------------------
' Parameter 1 : (String) "VOLTAGE_OVER_DISPLACEMENT_ExtraSmall"
' Parameter 2 : (String) "Default value"
' Parameter 3 : (String) "Unlocked"
' Parameter 4 : (Boolean) False
'--------------------------------------------------

long2178 = settingRepository1.GetAttr("VOLTAGE_OVER_DISPLACEMENT_Nanometric")
'--------------------------------------------------
' Parameter 1 : (String) "VOLTAGE_OVER_DISPLACEMENT_Nanometric"
' Returned value : (Variant) (Long) 1
'--------------------------------------------------

Dim bSTR4355
bSTR4355 = ""
Dim bSTR4356
bSTR4356 = ""
Dim boolean2178
settingRepository1.GetAttrInfo "VOLTAGE_OVER_DISPLACEMENT_Nanometric", bSTR4355, bSTR4356, boolean2178
'--------------------------------------------------
' Parameter 1 : (String) "VOLTAGE_OVER_DISPLACEMENT_Nanometric"
' Parameter 2 : (String) "Default value"
' Parameter 3 : (String) "Unlocked"
' Parameter 4 : (Boolean) False
'--------------------------------------------------

long2179 = settingRepository1.GetAttr("VOLTAGE_OVER_VELOCITY")
'--------------------------------------------------
' Parameter 1 : (String) "VOLTAGE_OVER_VELOCITY"
' Returned value : (Variant) (Long) 1
'--------------------------------------------------

Dim bSTR4357
bSTR4357 = ""
Dim bSTR4358
bSTR4358 = ""
Dim boolean2179
settingRepository1.GetAttrInfo "VOLTAGE_OVER_VELOCITY", bSTR4357, bSTR4358, boolean2179
'--------------------------------------------------
' Parameter 1 : (String) "VOLTAGE_OVER_VELOCITY"
' Parameter 2 : (String) "Default value"
' Parameter 3 : (String) "Unlocked"
' Parameter 4 : (Boolean) False
'--------------------------------------------------

long2180 = settingRepository1.GetAttr("VOLTAGE_OVER_VELOCITY_Large")
'--------------------------------------------------
' Parameter 1 : (String) "VOLTAGE_OVER_VELOCITY_Large"
' Returned value : (Variant) (Long) 1
'--------------------------------------------------

Dim bSTR4359
bSTR4359 = ""
Dim bSTR4360
bSTR4360 = ""
Dim boolean2180
settingRepository1.GetAttrInfo "VOLTAGE_OVER_VELOCITY_Large", bSTR4359, bSTR4360, boolean2180
'--------------------------------------------------
' Parameter 1 : (String) "VOLTAGE_OVER_VELOCITY_Large"
' Parameter 2 : (String) "Default value"
' Parameter 3 : (String) "Unlocked"
' Parameter 4 : (Boolean) False
'--------------------------------------------------

long2181 = settingRepository1.GetAttr("VOLTAGE_OVER_VELOCITY_ExtraLarge")
'--------------------------------------------------
' Parameter 1 : (String) "VOLTAGE_OVER_VELOCITY_ExtraLarge"
' Returned value : (Variant) (Long) 1
'--------------------------------------------------

Dim bSTR4361
bSTR4361 = ""
Dim bSTR4362
bSTR4362 = ""
Dim boolean2181
settingRepository1.GetAttrInfo "VOLTAGE_OVER_VELOCITY_ExtraLarge", bSTR4361, bSTR4362, boolean2181
'--------------------------------------------------
' Parameter 1 : (String) "VOLTAGE_OVER_VELOCITY_ExtraLarge"
' Parameter 2 : (String) "Default value"
' Parameter 3 : (String) "Unlocked"
' Parameter 4 : (Boolean) False
'--------------------------------------------------

long2182 = settingRepository1.GetAttr("VOLTAGE_OVER_VELOCITY_Small")
'--------------------------------------------------
' Parameter 1 : (String) "VOLTAGE_OVER_VELOCITY_Small"
' Returned value : (Variant) (Long) 1
'--------------------------------------------------

Dim bSTR4363
bSTR4363 = ""
Dim bSTR4364
bSTR4364 = ""
Dim boolean2182
settingRepository1.GetAttrInfo "VOLTAGE_OVER_VELOCITY_Small", bSTR4363, bSTR4364, boolean2182
'--------------------------------------------------
' Parameter 1 : (String) "VOLTAGE_OVER_VELOCITY_Small"
' Parameter 2 : (String) "Default value"
' Parameter 3 : (String) "Unlocked"
' Parameter 4 : (Boolean) False
'--------------------------------------------------

long2183 = settingRepository1.GetAttr("VOLTAGE_OVER_VELOCITY_ExtraSmall")
'--------------------------------------------------
' Parameter 1 : (String) "VOLTAGE_OVER_VELOCITY_ExtraSmall"
' Returned value : (Variant) (Long) 1
'--------------------------------------------------

Dim bSTR4365
bSTR4365 = ""
Dim bSTR4366
bSTR4366 = ""
Dim boolean2183
settingRepository1.GetAttrInfo "VOLTAGE_OVER_VELOCITY_ExtraSmall", bSTR4365, bSTR4366, boolean2183
'--------------------------------------------------
' Parameter 1 : (String) "VOLTAGE_OVER_VELOCITY_ExtraSmall"
' Parameter 2 : (String) "Default value"
' Parameter 3 : (String) "Unlocked"
' Parameter 4 : (Boolean) False
'--------------------------------------------------

long2184 = settingRepository1.GetAttr("VOLTAGE_OVER_VELOCITY_Nanometric")
'--------------------------------------------------
' Parameter 1 : (String) "VOLTAGE_OVER_VELOCITY_Nanometric"
' Returned value : (Variant) (Long) 1
'--------------------------------------------------

Dim bSTR4367
bSTR4367 = ""
Dim bSTR4368
bSTR4368 = ""
Dim boolean2184
settingRepository1.GetAttrInfo "VOLTAGE_OVER_VELOCITY_Nanometric", bSTR4367, bSTR4368, boolean2184
'--------------------------------------------------
' Parameter 1 : (String) "VOLTAGE_OVER_VELOCITY_Nanometric"
' Parameter 2 : (String) "Default value"
' Parameter 3 : (String) "Unlocked"
' Parameter 4 : (Boolean) False
'--------------------------------------------------

long2185 = settingRepository1.GetAttr("VOLTAGE_OVER_ACCELERATION")
'--------------------------------------------------
' Parameter 1 : (String) "VOLTAGE_OVER_ACCELERATION"
' Returned value : (Variant) (Long) 1
'--------------------------------------------------

Dim bSTR4369
bSTR4369 = ""
Dim bSTR4370
bSTR4370 = ""
Dim boolean2185
settingRepository1.GetAttrInfo "VOLTAGE_OVER_ACCELERATION", bSTR4369, bSTR4370, boolean2185
'--------------------------------------------------
' Parameter 1 : (String) "VOLTAGE_OVER_ACCELERATION"
' Parameter 2 : (String) "Default value"
' Parameter 3 : (String) "Unlocked"
' Parameter 4 : (Boolean) False
'--------------------------------------------------

long2186 = settingRepository1.GetAttr("VOLTAGE_OVER_ACCELERATION_Large")
'--------------------------------------------------
' Parameter 1 : (String) "VOLTAGE_OVER_ACCELERATION_Large"
' Returned value : (Variant) (Long) 1
'--------------------------------------------------

Dim bSTR4371
bSTR4371 = ""
Dim bSTR4372
bSTR4372 = ""
Dim boolean2186
settingRepository1.GetAttrInfo "VOLTAGE_OVER_ACCELERATION_Large", bSTR4371, bSTR4372, boolean2186
'--------------------------------------------------
' Parameter 1 : (String) "VOLTAGE_OVER_ACCELERATION_Large"
' Parameter 2 : (String) "Default value"
' Parameter 3 : (String) "Unlocked"
' Parameter 4 : (Boolean) False
'--------------------------------------------------

long2187 = settingRepository1.GetAttr("VOLTAGE_OVER_ACCELERATION_ExtraLarge")
'--------------------------------------------------
' Parameter 1 : (String) "VOLTAGE_OVER_ACCELERATION_ExtraLarge"
' Returned value : (Variant) (Long) 1
'--------------------------------------------------

Dim bSTR4373
bSTR4373 = ""
Dim bSTR4374
bSTR4374 = ""
Dim boolean2187
settingRepository1.GetAttrInfo "VOLTAGE_OVER_ACCELERATION_ExtraLarge", bSTR4373, bSTR4374, boolean2187
'--------------------------------------------------
' Parameter 1 : (String) "VOLTAGE_OVER_ACCELERATION_ExtraLarge"
' Parameter 2 : (String) "Default value"
' Parameter 3 : (String) "Unlocked"
' Parameter 4 : (Boolean) False
'--------------------------------------------------

long2188 = settingRepository1.GetAttr("VOLTAGE_OVER_ACCELERATION_Small")
'--------------------------------------------------
' Parameter 1 : (String) "VOLTAGE_OVER_ACCELERATION_Small"
' Returned value : (Variant) (Long) 1
'--------------------------------------------------

Dim bSTR4375
bSTR4375 = ""
Dim bSTR4376
bSTR4376 = ""
Dim boolean2188
settingRepository1.GetAttrInfo "VOLTAGE_OVER_ACCELERATION_Small", bSTR4375, bSTR4376, boolean2188
'--------------------------------------------------
' Parameter 1 : (String) "VOLTAGE_OVER_ACCELERATION_Small"
' Parameter 2 : (String) "Default value"
' Parameter 3 : (String) "Unlocked"
' Parameter 4 : (Boolean) False
'--------------------------------------------------

long2189 = settingRepository1.GetAttr("VOLTAGE_OVER_ACCELERATION_ExtraSmall")
'--------------------------------------------------
' Parameter 1 : (String) "VOLTAGE_OVER_ACCELERATION_ExtraSmall"
' Returned value : (Variant) (Long) 1
'--------------------------------------------------

Dim bSTR4377
bSTR4377 = ""
Dim bSTR4378
bSTR4378 = ""
Dim boolean2189
settingRepository1.GetAttrInfo "VOLTAGE_OVER_ACCELERATION_ExtraSmall", bSTR4377, bSTR4378, boolean2189
'--------------------------------------------------
' Parameter 1 : (String) "VOLTAGE_OVER_ACCELERATION_ExtraSmall"
' Parameter 2 : (String) "Default value"
' Parameter 3 : (String) "Unlocked"
' Parameter 4 : (Boolean) False
'--------------------------------------------------

long2190 = settingRepository1.GetAttr("VOLTAGE_OVER_ACCELERATION_Nanometric")
'--------------------------------------------------
' Parameter 1 : (String) "VOLTAGE_OVER_ACCELERATION_Nanometric"
' Returned value : (Variant) (Long) 1
'--------------------------------------------------

Dim bSTR4379
bSTR4379 = ""
Dim bSTR4380
bSTR4380 = ""
Dim boolean2190
settingRepository1.GetAttrInfo "VOLTAGE_OVER_ACCELERATION_Nanometric", bSTR4379, bSTR4380, boolean2190
'--------------------------------------------------
' Parameter 1 : (String) "VOLTAGE_OVER_ACCELERATION_Nanometric"
' Parameter 2 : (String) "Default value"
' Parameter 3 : (String) "Unlocked"
' Parameter 4 : (Boolean) False
'--------------------------------------------------

long2191 = settingRepository1.GetAttr("PRESSURE_OVER_VOLTAGE")
'--------------------------------------------------
' Parameter 1 : (String) "PRESSURE_OVER_VOLTAGE"
' Returned value : (Variant) (Long) 1
'--------------------------------------------------

Dim bSTR4381
bSTR4381 = ""
Dim bSTR4382
bSTR4382 = ""
Dim boolean2191
settingRepository1.GetAttrInfo "PRESSURE_OVER_VOLTAGE", bSTR4381, bSTR4382, boolean2191
'--------------------------------------------------
' Parameter 1 : (String) "PRESSURE_OVER_VOLTAGE"
' Parameter 2 : (String) "Default value"
' Parameter 3 : (String) "Unlocked"
' Parameter 4 : (Boolean) False
'--------------------------------------------------

long2192 = settingRepository1.GetAttr("PRESSURE_OVER_VOLTAGE_Large")
'--------------------------------------------------
' Parameter 1 : (String) "PRESSURE_OVER_VOLTAGE_Large"
' Returned value : (Variant) (Long) 1
'--------------------------------------------------

Dim bSTR4383
bSTR4383 = ""
Dim bSTR4384
bSTR4384 = ""
Dim boolean2192
settingRepository1.GetAttrInfo "PRESSURE_OVER_VOLTAGE_Large", bSTR4383, bSTR4384, boolean2192
'--------------------------------------------------
' Parameter 1 : (String) "PRESSURE_OVER_VOLTAGE_Large"
' Parameter 2 : (String) "Default value"
' Parameter 3 : (String) "Unlocked"
' Parameter 4 : (Boolean) False
'--------------------------------------------------

long2193 = settingRepository1.GetAttr("PRESSURE_OVER_VOLTAGE_ExtraLarge")
'--------------------------------------------------
' Parameter 1 : (String) "PRESSURE_OVER_VOLTAGE_ExtraLarge"
' Returned value : (Variant) (Long) 1
'--------------------------------------------------

Dim bSTR4385
bSTR4385 = ""
Dim bSTR4386
bSTR4386 = ""
Dim boolean2193
settingRepository1.GetAttrInfo "PRESSURE_OVER_VOLTAGE_ExtraLarge", bSTR4385, bSTR4386, boolean2193
'--------------------------------------------------
' Parameter 1 : (String) "PRESSURE_OVER_VOLTAGE_ExtraLarge"
' Parameter 2 : (String) "Default value"
' Parameter 3 : (String) "Unlocked"
' Parameter 4 : (Boolean) False
'--------------------------------------------------

long2194 = settingRepository1.GetAttr("PRESSURE_OVER_VOLTAGE_Small")
'--------------------------------------------------
' Parameter 1 : (String) "PRESSURE_OVER_VOLTAGE_Small"
' Returned value : (Variant) (Long) 1
'--------------------------------------------------

Dim bSTR4387
bSTR4387 = ""
Dim bSTR4388
bSTR4388 = ""
Dim boolean2194
settingRepository1.GetAttrInfo "PRESSURE_OVER_VOLTAGE_Small", bSTR4387, bSTR4388, boolean2194
'--------------------------------------------------
' Parameter 1 : (String) "PRESSURE_OVER_VOLTAGE_Small"
' Parameter 2 : (String) "Default value"
' Parameter 3 : (String) "Unlocked"
' Parameter 4 : (Boolean) False
'--------------------------------------------------

long2195 = settingRepository1.GetAttr("PRESSURE_OVER_VOLTAGE_ExtraSmall")
'--------------------------------------------------
' Parameter 1 : (String) "PRESSURE_OVER_VOLTAGE_ExtraSmall"
' Returned value : (Variant) (Long) 1
'--------------------------------------------------

Dim bSTR4389
bSTR4389 = ""
Dim bSTR4390
bSTR4390 = ""
Dim boolean2195
settingRepository1.GetAttrInfo "PRESSURE_OVER_VOLTAGE_ExtraSmall", bSTR4389, bSTR4390, boolean2195
'--------------------------------------------------
' Parameter 1 : (String) "PRESSURE_OVER_VOLTAGE_ExtraSmall"
' Parameter 2 : (String) "Default value"
' Parameter 3 : (String) "Unlocked"
' Parameter 4 : (Boolean) False
'--------------------------------------------------

long2196 = settingRepository1.GetAttr("PRESSURE_OVER_VOLTAGE_Nanometric")
'--------------------------------------------------
' Parameter 1 : (String) "PRESSURE_OVER_VOLTAGE_Nanometric"
' Returned value : (Variant) (Long) 1
'--------------------------------------------------

Dim bSTR4391
bSTR4391 = ""
Dim bSTR4392
bSTR4392 = ""
Dim boolean2196
settingRepository1.GetAttrInfo "PRESSURE_OVER_VOLTAGE_Nanometric", bSTR4391, bSTR4392, boolean2196
'--------------------------------------------------
' Parameter 1 : (String) "PRESSURE_OVER_VOLTAGE_Nanometric"
' Parameter 2 : (String) "Default value"
' Parameter 3 : (String) "Unlocked"
' Parameter 4 : (Boolean) False
'--------------------------------------------------

long2197 = settingRepository1.GetAttr("VOLTAGE_OVER_PRESSURE")
'--------------------------------------------------
' Parameter 1 : (String) "VOLTAGE_OVER_PRESSURE"
' Returned value : (Variant) (Long) 1
'--------------------------------------------------

Dim bSTR4393
bSTR4393 = ""
Dim bSTR4394
bSTR4394 = ""
Dim boolean2197
settingRepository1.GetAttrInfo "VOLTAGE_OVER_PRESSURE", bSTR4393, bSTR4394, boolean2197
'--------------------------------------------------
' Parameter 1 : (String) "VOLTAGE_OVER_PRESSURE"
' Parameter 2 : (String) "Default value"
' Parameter 3 : (String) "Unlocked"
' Parameter 4 : (Boolean) False
'--------------------------------------------------

long2198 = settingRepository1.GetAttr("VOLTAGE_OVER_PRESSURE_Large")
'--------------------------------------------------
' Parameter 1 : (String) "VOLTAGE_OVER_PRESSURE_Large"
' Returned value : (Variant) (Long) 1
'--------------------------------------------------

Dim bSTR4395
bSTR4395 = ""
Dim bSTR4396
bSTR4396 = ""
Dim boolean2198
settingRepository1.GetAttrInfo "VOLTAGE_OVER_PRESSURE_Large", bSTR4395, bSTR4396, boolean2198
'--------------------------------------------------
' Parameter 1 : (String) "VOLTAGE_OVER_PRESSURE_Large"
' Parameter 2 : (String) "Default value"
' Parameter 3 : (String) "Unlocked"
' Parameter 4 : (Boolean) False
'--------------------------------------------------

long2199 = settingRepository1.GetAttr("VOLTAGE_OVER_PRESSURE_ExtraLarge")
'--------------------------------------------------
' Parameter 1 : (String) "VOLTAGE_OVER_PRESSURE_ExtraLarge"
' Returned value : (Variant) (Long) 1
'--------------------------------------------------

Dim bSTR4397
bSTR4397 = ""
Dim bSTR4398
bSTR4398 = ""
Dim boolean2199
settingRepository1.GetAttrInfo "VOLTAGE_OVER_PRESSURE_ExtraLarge", bSTR4397, bSTR4398, boolean2199
'--------------------------------------------------
' Parameter 1 : (String) "VOLTAGE_OVER_PRESSURE_ExtraLarge"
' Parameter 2 : (String) "Default value"
' Parameter 3 : (String) "Unlocked"
' Parameter 4 : (Boolean) False
'--------------------------------------------------

long2200 = settingRepository1.GetAttr("VOLTAGE_OVER_PRESSURE_Small")
'--------------------------------------------------
' Parameter 1 : (String) "VOLTAGE_OVER_PRESSURE_Small"
' Returned value : (Variant) (Long) 1
'--------------------------------------------------

Dim bSTR4399
bSTR4399 = ""
Dim bSTR4400
bSTR4400 = ""
Dim boolean2200
settingRepository1.GetAttrInfo "VOLTAGE_OVER_PRESSURE_Small", bSTR4399, bSTR4400, boolean2200
'--------------------------------------------------
' Parameter 1 : (String) "VOLTAGE_OVER_PRESSURE_Small"
' Parameter 2 : (String) "Default value"
' Parameter 3 : (String) "Unlocked"
' Parameter 4 : (Boolean) False
'--------------------------------------------------

long2201 = settingRepository1.GetAttr("VOLTAGE_OVER_PRESSURE_ExtraSmall")
'--------------------------------------------------
' Parameter 1 : (String) "VOLTAGE_OVER_PRESSURE_ExtraSmall"
' Returned value : (Variant) (Long) 1
'--------------------------------------------------

Dim bSTR4401
bSTR4401 = ""
Dim bSTR4402
bSTR4402 = ""
Dim boolean2201
settingRepository1.GetAttrInfo "VOLTAGE_OVER_PRESSURE_ExtraSmall", bSTR4401, bSTR4402, boolean2201
'--------------------------------------------------
' Parameter 1 : (String) "VOLTAGE_OVER_PRESSURE_ExtraSmall"
' Parameter 2 : (String) "Default value"
' Parameter 3 : (String) "Unlocked"
' Parameter 4 : (Boolean) False
'--------------------------------------------------

long2202 = settingRepository1.GetAttr("VOLTAGE_OVER_PRESSURE_Nanometric")
'--------------------------------------------------
' Parameter 1 : (String) "VOLTAGE_OVER_PRESSURE_Nanometric"
' Returned value : (Variant) (Long) 1
'--------------------------------------------------

Dim bSTR4403
bSTR4403 = ""
Dim bSTR4404
bSTR4404 = ""
Dim boolean2202
settingRepository1.GetAttrInfo "VOLTAGE_OVER_PRESSURE_Nanometric", bSTR4403, bSTR4404, boolean2202
'--------------------------------------------------
' Parameter 1 : (String) "VOLTAGE_OVER_PRESSURE_Nanometric"
' Parameter 2 : (String) "Default value"
' Parameter 3 : (String) "Unlocked"
' Parameter 4 : (Boolean) False
'--------------------------------------------------

long2203 = settingRepository1.GetAttr("RATE")
'--------------------------------------------------
' Parameter 1 : (String) "RATE"
' Returned value : (Variant) (Long) 1
'--------------------------------------------------

Dim bSTR4405
bSTR4405 = ""
Dim bSTR4406
bSTR4406 = ""
Dim boolean2203
settingRepository1.GetAttrInfo "RATE", bSTR4405, bSTR4406, boolean2203
'--------------------------------------------------
' Parameter 1 : (String) "RATE"
' Parameter 2 : (String) "Default value"
' Parameter 3 : (String) "Unlocked"
' Parameter 4 : (Boolean) False
'--------------------------------------------------

long2204 = settingRepository1.GetAttr("RATE_Large")
'--------------------------------------------------
' Parameter 1 : (String) "RATE_Large"
' Returned value : (Variant) (Long) 1
'--------------------------------------------------

Dim bSTR4407
bSTR4407 = ""
Dim bSTR4408
bSTR4408 = ""
Dim boolean2204
settingRepository1.GetAttrInfo "RATE_Large", bSTR4407, bSTR4408, boolean2204
'--------------------------------------------------
' Parameter 1 : (String) "RATE_Large"
' Parameter 2 : (String) "Default value"
' Parameter 3 : (String) "Unlocked"
' Parameter 4 : (Boolean) False
'--------------------------------------------------

long2205 = settingRepository1.GetAttr("RATE_ExtraLarge")
'--------------------------------------------------
' Parameter 1 : (String) "RATE_ExtraLarge"
' Returned value : (Variant) (Long) 1
'--------------------------------------------------

Dim bSTR4409
bSTR4409 = ""
Dim bSTR4410
bSTR4410 = ""
Dim boolean2205
settingRepository1.GetAttrInfo "RATE_ExtraLarge", bSTR4409, bSTR4410, boolean2205
'--------------------------------------------------
' Parameter 1 : (String) "RATE_ExtraLarge"
' Parameter 2 : (String) "Default value"
' Parameter 3 : (String) "Unlocked"
' Parameter 4 : (Boolean) False
'--------------------------------------------------

long2206 = settingRepository1.GetAttr("RATE_Small")
'--------------------------------------------------
' Parameter 1 : (String) "RATE_Small"
' Returned value : (Variant) (Long) 1
'--------------------------------------------------

Dim bSTR4411
bSTR4411 = ""
Dim bSTR4412
bSTR4412 = ""
Dim boolean2206
settingRepository1.GetAttrInfo "RATE_Small", bSTR4411, bSTR4412, boolean2206
'--------------------------------------------------
' Parameter 1 : (String) "RATE_Small"
' Parameter 2 : (String) "Default value"
' Parameter 3 : (String) "Unlocked"
' Parameter 4 : (Boolean) False
'--------------------------------------------------

long2207 = settingRepository1.GetAttr("RATE_ExtraSmall")
'--------------------------------------------------
' Parameter 1 : (String) "RATE_ExtraSmall"
' Returned value : (Variant) (Long) 1
'--------------------------------------------------

Dim bSTR4413
bSTR4413 = ""
Dim bSTR4414
bSTR4414 = ""
Dim boolean2207
settingRepository1.GetAttrInfo "RATE_ExtraSmall", bSTR4413, bSTR4414, boolean2207
'--------------------------------------------------
' Parameter 1 : (String) "RATE_ExtraSmall"
' Parameter 2 : (String) "Default value"
' Parameter 3 : (String) "Unlocked"
' Parameter 4 : (Boolean) False
'--------------------------------------------------

long2208 = settingRepository1.GetAttr("RATE_Nanometric")
'--------------------------------------------------
' Parameter 1 : (String) "RATE_Nanometric"
' Returned value : (Variant) (Long) 1
'--------------------------------------------------

Dim bSTR4415
bSTR4415 = ""
Dim bSTR4416
bSTR4416 = ""
Dim boolean2208
settingRepository1.GetAttrInfo "RATE_Nanometric", bSTR4415, bSTR4416, boolean2208
'--------------------------------------------------
' Parameter 1 : (String) "RATE_Nanometric"
' Parameter 2 : (String) "Default value"
' Parameter 3 : (String) "Unlocked"
' Parameter 4 : (Boolean) False
'--------------------------------------------------

long2209 = settingRepository1.GetAttr("STRAIN_RATE")
'--------------------------------------------------
' Parameter 1 : (String) "STRAIN_RATE"
' Returned value : (Variant) (Long) 1
'--------------------------------------------------

Dim bSTR4417
bSTR4417 = ""
Dim bSTR4418
bSTR4418 = ""
Dim boolean2209
settingRepository1.GetAttrInfo "STRAIN_RATE", bSTR4417, bSTR4418, boolean2209
'--------------------------------------------------
' Parameter 1 : (String) "STRAIN_RATE"
' Parameter 2 : (String) "Default value"
' Parameter 3 : (String) "Unlocked"
' Parameter 4 : (Boolean) False
'--------------------------------------------------

long2210 = settingRepository1.GetAttr("STRAIN_RATE_Large")
'--------------------------------------------------
' Parameter 1 : (String) "STRAIN_RATE_Large"
' Returned value : (Variant) (Long) 1
'--------------------------------------------------

Dim bSTR4419
bSTR4419 = ""
Dim bSTR4420
bSTR4420 = ""
Dim boolean2210
settingRepository1.GetAttrInfo "STRAIN_RATE_Large", bSTR4419, bSTR4420, boolean2210
'--------------------------------------------------
' Parameter 1 : (String) "STRAIN_RATE_Large"
' Parameter 2 : (String) "Default value"
' Parameter 3 : (String) "Unlocked"
' Parameter 4 : (Boolean) False
'--------------------------------------------------

long2211 = settingRepository1.GetAttr("STRAIN_RATE_ExtraLarge")
'--------------------------------------------------
' Parameter 1 : (String) "STRAIN_RATE_ExtraLarge"
' Returned value : (Variant) (Long) 1
'--------------------------------------------------

Dim bSTR4421
bSTR4421 = ""
Dim bSTR4422
bSTR4422 = ""
Dim boolean2211
settingRepository1.GetAttrInfo "STRAIN_RATE_ExtraLarge", bSTR4421, bSTR4422, boolean2211
'--------------------------------------------------
' Parameter 1 : (String) "STRAIN_RATE_ExtraLarge"
' Parameter 2 : (String) "Default value"
' Parameter 3 : (String) "Unlocked"
' Parameter 4 : (Boolean) False
'--------------------------------------------------

long2212 = settingRepository1.GetAttr("STRAIN_RATE_Small")
'--------------------------------------------------
' Parameter 1 : (String) "STRAIN_RATE_Small"
' Returned value : (Variant) (Long) 1
'--------------------------------------------------

Dim bSTR4423
bSTR4423 = ""
Dim bSTR4424
bSTR4424 = ""
Dim boolean2212
settingRepository1.GetAttrInfo "STRAIN_RATE_Small", bSTR4423, bSTR4424, boolean2212
'--------------------------------------------------
' Parameter 1 : (String) "STRAIN_RATE_Small"
' Parameter 2 : (String) "Default value"
' Parameter 3 : (String) "Unlocked"
' Parameter 4 : (Boolean) False
'--------------------------------------------------

long2213 = settingRepository1.GetAttr("STRAIN_RATE_ExtraSmall")
'--------------------------------------------------
' Parameter 1 : (String) "STRAIN_RATE_ExtraSmall"
' Returned value : (Variant) (Long) 1
'--------------------------------------------------

Dim bSTR4425
bSTR4425 = ""
Dim bSTR4426
bSTR4426 = ""
Dim boolean2213
settingRepository1.GetAttrInfo "STRAIN_RATE_ExtraSmall", bSTR4425, bSTR4426, boolean2213
'--------------------------------------------------
' Parameter 1 : (String) "STRAIN_RATE_ExtraSmall"
' Parameter 2 : (String) "Default value"
' Parameter 3 : (String) "Unlocked"
' Parameter 4 : (Boolean) False
'--------------------------------------------------

long2214 = settingRepository1.GetAttr("STRAIN_RATE_Nanometric")
'--------------------------------------------------
' Parameter 1 : (String) "STRAIN_RATE_Nanometric"
' Returned value : (Variant) (Long) 1
'--------------------------------------------------

Dim bSTR4427
bSTR4427 = ""
Dim bSTR4428
bSTR4428 = ""
Dim boolean2214
settingRepository1.GetAttrInfo "STRAIN_RATE_Nanometric", bSTR4427, bSTR4428, boolean2214
'--------------------------------------------------
' Parameter 1 : (String) "STRAIN_RATE_Nanometric"
' Parameter 2 : (String) "Default value"
' Parameter 3 : (String) "Unlocked"
' Parameter 4 : (Boolean) False
'--------------------------------------------------

long2215 = settingRepository1.GetAttr("SPECIFIC_HEAT_PER_UNIT_VOLUME")
'--------------------------------------------------
' Parameter 1 : (String) "SPECIFIC_HEAT_PER_UNIT_VOLUME"
' Returned value : (Variant) (Long) 1
'--------------------------------------------------

Dim bSTR4429
bSTR4429 = ""
Dim bSTR4430
bSTR4430 = ""
Dim boolean2215
settingRepository1.GetAttrInfo "SPECIFIC_HEAT_PER_UNIT_VOLUME", bSTR4429, bSTR4430, boolean2215
'--------------------------------------------------
' Parameter 1 : (String) "SPECIFIC_HEAT_PER_UNIT_VOLUME"
' Parameter 2 : (String) "Default value"
' Parameter 3 : (String) "Unlocked"
' Parameter 4 : (Boolean) False
'--------------------------------------------------

long2216 = settingRepository1.GetAttr("SPECIFIC_HEAT_PER_UNIT_VOLUME_Large")
'--------------------------------------------------
' Parameter 1 : (String) "SPECIFIC_HEAT_PER_UNIT_VOLUME_Large"
' Returned value : (Variant) (Long) 1
'--------------------------------------------------

Dim bSTR4431
bSTR4431 = ""
Dim bSTR4432
bSTR4432 = ""
Dim boolean2216
settingRepository1.GetAttrInfo "SPECIFIC_HEAT_PER_UNIT_VOLUME_Large", bSTR4431, bSTR4432, boolean2216
'--------------------------------------------------
' Parameter 1 : (String) "SPECIFIC_HEAT_PER_UNIT_VOLUME_Large"
' Parameter 2 : (String) "Default value"
' Parameter 3 : (String) "Unlocked"
' Parameter 4 : (Boolean) False
'--------------------------------------------------

long2217 = settingRepository1.GetAttr("SPECIFIC_HEAT_PER_UNIT_VOLUME_ExtraLarge")
'--------------------------------------------------
' Parameter 1 : (String) "SPECIFIC_HEAT_PER_UNIT_VOLUME_ExtraLarge"
' Returned value : (Variant) (Long) 1
'--------------------------------------------------

Dim bSTR4433
bSTR4433 = ""
Dim bSTR4434
bSTR4434 = ""
Dim boolean2217
settingRepository1.GetAttrInfo "SPECIFIC_HEAT_PER_UNIT_VOLUME_ExtraLarge", bSTR4433, bSTR4434, boolean2217
'--------------------------------------------------
' Parameter 1 : (String) "SPECIFIC_HEAT_PER_UNIT_VOLUME_ExtraLarge"
' Parameter 2 : (String) "Default value"
' Parameter 3 : (String) "Unlocked"
' Parameter 4 : (Boolean) False
'--------------------------------------------------

long2218 = settingRepository1.GetAttr("SPECIFIC_HEAT_PER_UNIT_VOLUME_Small")
'--------------------------------------------------
' Parameter 1 : (String) "SPECIFIC_HEAT_PER_UNIT_VOLUME_Small"
' Returned value : (Variant) (Long) 1
'--------------------------------------------------

Dim bSTR4435
bSTR4435 = ""
Dim bSTR4436
bSTR4436 = ""
Dim boolean2218
settingRepository1.GetAttrInfo "SPECIFIC_HEAT_PER_UNIT_VOLUME_Small", bSTR4435, bSTR4436, boolean2218
'--------------------------------------------------
' Parameter 1 : (String) "SPECIFIC_HEAT_PER_UNIT_VOLUME_Small"
' Parameter 2 : (String) "Default value"
' Parameter 3 : (String) "Unlocked"
' Parameter 4 : (Boolean) False
'--------------------------------------------------

long2219 = settingRepository1.GetAttr("SPECIFIC_HEAT_PER_UNIT_VOLUME_ExtraSmall")
'--------------------------------------------------
' Parameter 1 : (String) "SPECIFIC_HEAT_PER_UNIT_VOLUME_ExtraSmall"
' Returned value : (Variant) (Long) 1
'--------------------------------------------------

Dim bSTR4437
bSTR4437 = ""
Dim bSTR4438
bSTR4438 = ""
Dim boolean2219
settingRepository1.GetAttrInfo "SPECIFIC_HEAT_PER_UNIT_VOLUME_ExtraSmall", bSTR4437, bSTR4438, boolean2219
'--------------------------------------------------
' Parameter 1 : (String) "SPECIFIC_HEAT_PER_UNIT_VOLUME_ExtraSmall"
' Parameter 2 : (String) "Default value"
' Parameter 3 : (String) "Unlocked"
' Parameter 4 : (Boolean) False
'--------------------------------------------------

long2220 = settingRepository1.GetAttr("SPECIFIC_HEAT_PER_UNIT_VOLUME_Nanometric")
'--------------------------------------------------
' Parameter 1 : (String) "SPECIFIC_HEAT_PER_UNIT_VOLUME_Nanometric"
' Returned value : (Variant) (Long) 1
'--------------------------------------------------

Dim bSTR4439
bSTR4439 = ""
Dim bSTR4440
bSTR4440 = ""
Dim boolean2220
settingRepository1.GetAttrInfo "SPECIFIC_HEAT_PER_UNIT_VOLUME_Nanometric", bSTR4439, bSTR4440, boolean2220
'--------------------------------------------------
' Parameter 1 : (String) "SPECIFIC_HEAT_PER_UNIT_VOLUME_Nanometric"
' Parameter 2 : (String) "Default value"
' Parameter 3 : (String) "Unlocked"
' Parameter 4 : (Boolean) False
'--------------------------------------------------

long2221 = settingRepository1.GetAttr("POWERbis")
'--------------------------------------------------
' Parameter 1 : (String) "POWERbis"
' Returned value : (Variant) (Long) 1
'--------------------------------------------------

Dim bSTR4441
bSTR4441 = ""
Dim bSTR4442
bSTR4442 = ""
Dim boolean2221
settingRepository1.GetAttrInfo "POWERbis", bSTR4441, bSTR4442, boolean2221
'--------------------------------------------------
' Parameter 1 : (String) "POWERbis"
' Parameter 2 : (String) "Default value"
' Parameter 3 : (String) "Unlocked"
' Parameter 4 : (Boolean) False
'--------------------------------------------------

long2222 = settingRepository1.GetAttr("POWERbis_Large")
'--------------------------------------------------
' Parameter 1 : (String) "POWERbis_Large"
' Returned value : (Variant) (Long) 1
'--------------------------------------------------

Dim bSTR4443
bSTR4443 = ""
Dim bSTR4444
bSTR4444 = ""
Dim boolean2222
settingRepository1.GetAttrInfo "POWERbis_Large", bSTR4443, bSTR4444, boolean2222
'--------------------------------------------------
' Parameter 1 : (String) "POWERbis_Large"
' Parameter 2 : (String) "Default value"
' Parameter 3 : (String) "Unlocked"
' Parameter 4 : (Boolean) False
'--------------------------------------------------

long2223 = settingRepository1.GetAttr("POWERbis_ExtraLarge")
'--------------------------------------------------
' Parameter 1 : (String) "POWERbis_ExtraLarge"
' Returned value : (Variant) (Long) 1
'--------------------------------------------------

Dim bSTR4445
bSTR4445 = ""
Dim bSTR4446
bSTR4446 = ""
Dim boolean2223
settingRepository1.GetAttrInfo "POWERbis_ExtraLarge", bSTR4445, bSTR4446, boolean2223
'--------------------------------------------------
' Parameter 1 : (String) "POWERbis_ExtraLarge"
' Parameter 2 : (String) "Default value"
' Parameter 3 : (String) "Unlocked"
' Parameter 4 : (Boolean) False
'--------------------------------------------------

long2224 = settingRepository1.GetAttr("POWERbis_Small")
'--------------------------------------------------
' Parameter 1 : (String) "POWERbis_Small"
' Returned value : (Variant) (Long) 1
'--------------------------------------------------

Dim bSTR4447
bSTR4447 = ""
Dim bSTR4448
bSTR4448 = ""
Dim boolean2224
settingRepository1.GetAttrInfo "POWERbis_Small", bSTR4447, bSTR4448, boolean2224
'--------------------------------------------------
' Parameter 1 : (String) "POWERbis_Small"
' Parameter 2 : (String) "Default value"
' Parameter 3 : (String) "Unlocked"
' Parameter 4 : (Boolean) False
'--------------------------------------------------

long2225 = settingRepository1.GetAttr("POWERbis_ExtraSmall")
'--------------------------------------------------
' Parameter 1 : (String) "POWERbis_ExtraSmall"
' Returned value : (Variant) (Long) 1
'--------------------------------------------------

Dim bSTR4449
bSTR4449 = ""
Dim bSTR4450
bSTR4450 = ""
Dim boolean2225
settingRepository1.GetAttrInfo "POWERbis_ExtraSmall", bSTR4449, bSTR4450, boolean2225
'--------------------------------------------------
' Parameter 1 : (String) "POWERbis_ExtraSmall"
' Parameter 2 : (String) "Default value"
' Parameter 3 : (String) "Unlocked"
' Parameter 4 : (Boolean) False
'--------------------------------------------------

long2226 = settingRepository1.GetAttr("POWERbis_Nanometric")
'--------------------------------------------------
' Parameter 1 : (String) "POWERbis_Nanometric"
' Returned value : (Variant) (Long) 1
'--------------------------------------------------

Dim bSTR4451
bSTR4451 = ""
Dim bSTR4452
bSTR4452 = ""
Dim boolean2226
settingRepository1.GetAttrInfo "POWERbis_Nanometric", bSTR4451, bSTR4452, boolean2226
'--------------------------------------------------
' Parameter 1 : (String) "POWERbis_Nanometric"
' Parameter 2 : (String) "Default value"
' Parameter 3 : (String) "Unlocked"
' Parameter 4 : (Boolean) False
'--------------------------------------------------

long2227 = settingRepository1.GetAttr("MOLARCONCENTRATION")
'--------------------------------------------------
' Parameter 1 : (String) "MOLARCONCENTRATION"
' Returned value : (Variant) (Long) 2
'--------------------------------------------------

Dim bSTR4453
bSTR4453 = ""
Dim bSTR4454
bSTR4454 = ""
Dim boolean2227
settingRepository1.GetAttrInfo "MOLARCONCENTRATION", bSTR4453, bSTR4454, boolean2227
'--------------------------------------------------
' Parameter 1 : (String) "MOLARCONCENTRATION"
' Parameter 2 : (String) "Default value"
' Parameter 3 : (String) "Unlocked"
' Parameter 4 : (Boolean) False
'--------------------------------------------------

long2228 = settingRepository1.GetAttr("MOLARCONCENTRATION_Large")
'--------------------------------------------------
' Parameter 1 : (String) "MOLARCONCENTRATION_Large"
' Returned value : (Variant) (Long) 2
'--------------------------------------------------

Dim bSTR4455
bSTR4455 = ""
Dim bSTR4456
bSTR4456 = ""
Dim boolean2228
settingRepository1.GetAttrInfo "MOLARCONCENTRATION_Large", bSTR4455, bSTR4456, boolean2228
'--------------------------------------------------
' Parameter 1 : (String) "MOLARCONCENTRATION_Large"
' Parameter 2 : (String) "Default value"
' Parameter 3 : (String) "Unlocked"
' Parameter 4 : (Boolean) False
'--------------------------------------------------

long2229 = settingRepository1.GetAttr("MOLARCONCENTRATION_ExtraLarge")
'--------------------------------------------------
' Parameter 1 : (String) "MOLARCONCENTRATION_ExtraLarge"
' Returned value : (Variant) (Long) 2
'--------------------------------------------------

Dim bSTR4457
bSTR4457 = ""
Dim bSTR4458
bSTR4458 = ""
Dim boolean2229
settingRepository1.GetAttrInfo "MOLARCONCENTRATION_ExtraLarge", bSTR4457, bSTR4458, boolean2229
'--------------------------------------------------
' Parameter 1 : (String) "MOLARCONCENTRATION_ExtraLarge"
' Parameter 2 : (String) "Default value"
' Parameter 3 : (String) "Unlocked"
' Parameter 4 : (Boolean) False
'--------------------------------------------------

long2230 = settingRepository1.GetAttr("MOLARCONCENTRATION_Small")
'--------------------------------------------------
' Parameter 1 : (String) "MOLARCONCENTRATION_Small"
' Returned value : (Variant) (Long) 2
'--------------------------------------------------

Dim bSTR4459
bSTR4459 = ""
Dim bSTR4460
bSTR4460 = ""
Dim boolean2230
settingRepository1.GetAttrInfo "MOLARCONCENTRATION_Small", bSTR4459, bSTR4460, boolean2230
'--------------------------------------------------
' Parameter 1 : (String) "MOLARCONCENTRATION_Small"
' Parameter 2 : (String) "Default value"
' Parameter 3 : (String) "Unlocked"
' Parameter 4 : (Boolean) False
'--------------------------------------------------

long2231 = settingRepository1.GetAttr("MOLARCONCENTRATION_ExtraSmall")
'--------------------------------------------------
' Parameter 1 : (String) "MOLARCONCENTRATION_ExtraSmall"
' Returned value : (Variant) (Long) 2
'--------------------------------------------------

Dim bSTR4461
bSTR4461 = ""
Dim bSTR4462
bSTR4462 = ""
Dim boolean2231
settingRepository1.GetAttrInfo "MOLARCONCENTRATION_ExtraSmall", bSTR4461, bSTR4462, boolean2231
'--------------------------------------------------
' Parameter 1 : (String) "MOLARCONCENTRATION_ExtraSmall"
' Parameter 2 : (String) "Default value"
' Parameter 3 : (String) "Unlocked"
' Parameter 4 : (Boolean) False
'--------------------------------------------------

long2232 = settingRepository1.GetAttr("MOLARCONCENTRATION_Nanometric")
'--------------------------------------------------
' Parameter 1 : (String) "MOLARCONCENTRATION_Nanometric"
' Returned value : (Variant) (Long) 2
'--------------------------------------------------

Dim bSTR4463
bSTR4463 = ""
Dim bSTR4464
bSTR4464 = ""
Dim boolean2232
settingRepository1.GetAttrInfo "MOLARCONCENTRATION_Nanometric", bSTR4463, bSTR4464, boolean2232
'--------------------------------------------------
' Parameter 1 : (String) "MOLARCONCENTRATION_Nanometric"
' Parameter 2 : (String) "Default value"
' Parameter 3 : (String) "Unlocked"
' Parameter 4 : (Boolean) False
'--------------------------------------------------

long2233 = settingRepository1.GetAttr("THERMALTRANSMITTANCE")
'--------------------------------------------------
' Parameter 1 : (String) "THERMALTRANSMITTANCE"
' Returned value : (Variant) (Long) 1
'--------------------------------------------------

Dim bSTR4465
bSTR4465 = ""
Dim bSTR4466
bSTR4466 = ""
Dim boolean2233
settingRepository1.GetAttrInfo "THERMALTRANSMITTANCE", bSTR4465, bSTR4466, boolean2233
'--------------------------------------------------
' Parameter 1 : (String) "THERMALTRANSMITTANCE"
' Parameter 2 : (String) "Default value"
' Parameter 3 : (String) "Unlocked"
' Parameter 4 : (Boolean) False
'--------------------------------------------------

long2234 = settingRepository1.GetAttr("THERMALTRANSMITTANCE_Large")
'--------------------------------------------------
' Parameter 1 : (String) "THERMALTRANSMITTANCE_Large"
' Returned value : (Variant) (Long) 1
'--------------------------------------------------

Dim bSTR4467
bSTR4467 = ""
Dim bSTR4468
bSTR4468 = ""
Dim boolean2234
settingRepository1.GetAttrInfo "THERMALTRANSMITTANCE_Large", bSTR4467, bSTR4468, boolean2234
'--------------------------------------------------
' Parameter 1 : (String) "THERMALTRANSMITTANCE_Large"
' Parameter 2 : (String) "Default value"
' Parameter 3 : (String) "Unlocked"
' Parameter 4 : (Boolean) False
'--------------------------------------------------

long2235 = settingRepository1.GetAttr("THERMALTRANSMITTANCE_ExtraLarge")
'--------------------------------------------------
' Parameter 1 : (String) "THERMALTRANSMITTANCE_ExtraLarge"
' Returned value : (Variant) (Long) 1
'--------------------------------------------------

Dim bSTR4469
bSTR4469 = ""
Dim bSTR4470
bSTR4470 = ""
Dim boolean2235
settingRepository1.GetAttrInfo "THERMALTRANSMITTANCE_ExtraLarge", bSTR4469, bSTR4470, boolean2235
'--------------------------------------------------
' Parameter 1 : (String) "THERMALTRANSMITTANCE_ExtraLarge"
' Parameter 2 : (String) "Default value"
' Parameter 3 : (String) "Unlocked"
' Parameter 4 : (Boolean) False
'--------------------------------------------------

long2236 = settingRepository1.GetAttr("THERMALTRANSMITTANCE_Small")
'--------------------------------------------------
' Parameter 1 : (String) "THERMALTRANSMITTANCE_Small"
' Returned value : (Variant) (Long) 1
'--------------------------------------------------

Dim bSTR4471
bSTR4471 = ""
Dim bSTR4472
bSTR4472 = ""
Dim boolean2236
settingRepository1.GetAttrInfo "THERMALTRANSMITTANCE_Small", bSTR4471, bSTR4472, boolean2236
'--------------------------------------------------
' Parameter 1 : (String) "THERMALTRANSMITTANCE_Small"
' Parameter 2 : (String) "Default value"
' Parameter 3 : (String) "Unlocked"
' Parameter 4 : (Boolean) False
'--------------------------------------------------

long2237 = settingRepository1.GetAttr("THERMALTRANSMITTANCE_ExtraSmall")
'--------------------------------------------------
' Parameter 1 : (String) "THERMALTRANSMITTANCE_ExtraSmall"
' Returned value : (Variant) (Long) 1
'--------------------------------------------------

Dim bSTR4473
bSTR4473 = ""
Dim bSTR4474
bSTR4474 = ""
Dim boolean2237
settingRepository1.GetAttrInfo "THERMALTRANSMITTANCE_ExtraSmall", bSTR4473, bSTR4474, boolean2237
'--------------------------------------------------
' Parameter 1 : (String) "THERMALTRANSMITTANCE_ExtraSmall"
' Parameter 2 : (String) "Default value"
' Parameter 3 : (String) "Unlocked"
' Parameter 4 : (Boolean) False
'--------------------------------------------------

long2238 = settingRepository1.GetAttr("THERMALTRANSMITTANCE_Nanometric")
'--------------------------------------------------
' Parameter 1 : (String) "THERMALTRANSMITTANCE_Nanometric"
' Returned value : (Variant) (Long) 1
'--------------------------------------------------

Dim bSTR4475
bSTR4475 = ""
Dim bSTR4476
bSTR4476 = ""
Dim boolean2238
settingRepository1.GetAttrInfo "THERMALTRANSMITTANCE_Nanometric", bSTR4475, bSTR4476, boolean2238
'--------------------------------------------------
' Parameter 1 : (String) "THERMALTRANSMITTANCE_Nanometric"
' Parameter 2 : (String) "Default value"
' Parameter 3 : (String) "Unlocked"
' Parameter 4 : (Boolean) False
'--------------------------------------------------

long2239 = settingRepository1.GetAttr("TEMPERATURE_OVER_PRESSURE")
'--------------------------------------------------
' Parameter 1 : (String) "TEMPERATURE_OVER_PRESSURE"
' Returned value : (Variant) (Long) 1
'--------------------------------------------------

Dim bSTR4477
bSTR4477 = ""
Dim bSTR4478
bSTR4478 = ""
Dim boolean2239
settingRepository1.GetAttrInfo "TEMPERATURE_OVER_PRESSURE", bSTR4477, bSTR4478, boolean2239
'--------------------------------------------------
' Parameter 1 : (String) "TEMPERATURE_OVER_PRESSURE"
' Parameter 2 : (String) "Default value"
' Parameter 3 : (String) "Unlocked"
' Parameter 4 : (Boolean) False
'--------------------------------------------------

long2240 = settingRepository1.GetAttr("TEMPERATURE_OVER_PRESSURE_Large")
'--------------------------------------------------
' Parameter 1 : (String) "TEMPERATURE_OVER_PRESSURE_Large"
' Returned value : (Variant) (Long) 1
'--------------------------------------------------

Dim bSTR4479
bSTR4479 = ""
Dim bSTR4480
bSTR4480 = ""
Dim boolean2240
settingRepository1.GetAttrInfo "TEMPERATURE_OVER_PRESSURE_Large", bSTR4479, bSTR4480, boolean2240
'--------------------------------------------------
' Parameter 1 : (String) "TEMPERATURE_OVER_PRESSURE_Large"
' Parameter 2 : (String) "Default value"
' Parameter 3 : (String) "Unlocked"
' Parameter 4 : (Boolean) False
'--------------------------------------------------

long2241 = settingRepository1.GetAttr("TEMPERATURE_OVER_PRESSURE_ExtraLarge")
'--------------------------------------------------
' Parameter 1 : (String) "TEMPERATURE_OVER_PRESSURE_ExtraLarge"
' Returned value : (Variant) (Long) 1
'--------------------------------------------------

Dim bSTR4481
bSTR4481 = ""
Dim bSTR4482
bSTR4482 = ""
Dim boolean2241
settingRepository1.GetAttrInfo "TEMPERATURE_OVER_PRESSURE_ExtraLarge", bSTR4481, bSTR4482, boolean2241
'--------------------------------------------------
' Parameter 1 : (String) "TEMPERATURE_OVER_PRESSURE_ExtraLarge"
' Parameter 2 : (String) "Default value"
' Parameter 3 : (String) "Unlocked"
' Parameter 4 : (Boolean) False
'--------------------------------------------------

long2242 = settingRepository1.GetAttr("TEMPERATURE_OVER_PRESSURE_Small")
'--------------------------------------------------
' Parameter 1 : (String) "TEMPERATURE_OVER_PRESSURE_Small"
' Returned value : (Variant) (Long) 1
'--------------------------------------------------

Dim bSTR4483
bSTR4483 = ""
Dim bSTR4484
bSTR4484 = ""
Dim boolean2242
settingRepository1.GetAttrInfo "TEMPERATURE_OVER_PRESSURE_Small", bSTR4483, bSTR4484, boolean2242
'--------------------------------------------------
' Parameter 1 : (String) "TEMPERATURE_OVER_PRESSURE_Small"
' Parameter 2 : (String) "Default value"
' Parameter 3 : (String) "Unlocked"
' Parameter 4 : (Boolean) False
'--------------------------------------------------

long2243 = settingRepository1.GetAttr("TEMPERATURE_OVER_PRESSURE_ExtraSmall")
'--------------------------------------------------
' Parameter 1 : (String) "TEMPERATURE_OVER_PRESSURE_ExtraSmall"
' Returned value : (Variant) (Long) 1
'--------------------------------------------------

Dim bSTR4485
bSTR4485 = ""
Dim bSTR4486
bSTR4486 = ""
Dim boolean2243
settingRepository1.GetAttrInfo "TEMPERATURE_OVER_PRESSURE_ExtraSmall", bSTR4485, bSTR4486, boolean2243
'--------------------------------------------------
' Parameter 1 : (String) "TEMPERATURE_OVER_PRESSURE_ExtraSmall"
' Parameter 2 : (String) "Default value"
' Parameter 3 : (String) "Unlocked"
' Parameter 4 : (Boolean) False
'--------------------------------------------------

long2244 = settingRepository1.GetAttr("TEMPERATURE_OVER_PRESSURE_Nanometric")
'--------------------------------------------------
' Parameter 1 : (String) "TEMPERATURE_OVER_PRESSURE_Nanometric"
' Returned value : (Variant) (Long) 1
'--------------------------------------------------

Dim bSTR4487
bSTR4487 = ""
Dim bSTR4488
bSTR4488 = ""
Dim boolean2244
settingRepository1.GetAttrInfo "TEMPERATURE_OVER_PRESSURE_Nanometric", bSTR4487, bSTR4488, boolean2244
'--------------------------------------------------
' Parameter 1 : (String) "TEMPERATURE_OVER_PRESSURE_Nanometric"
' Parameter 2 : (String) "Default value"
' Parameter 3 : (String) "Unlocked"
' Parameter 4 : (Boolean) False
'--------------------------------------------------

long2245 = settingRepository1.GetAttr("SPECIFICVOLUME_OVER_TEMPERATURE")
'--------------------------------------------------
' Parameter 1 : (String) "SPECIFICVOLUME_OVER_TEMPERATURE"
' Returned value : (Variant) (Long) 1
'--------------------------------------------------

Dim bSTR4489
bSTR4489 = ""
Dim bSTR4490
bSTR4490 = ""
Dim boolean2245
settingRepository1.GetAttrInfo "SPECIFICVOLUME_OVER_TEMPERATURE", bSTR4489, bSTR4490, boolean2245
'--------------------------------------------------
' Parameter 1 : (String) "SPECIFICVOLUME_OVER_TEMPERATURE"
' Parameter 2 : (String) "Default value"
' Parameter 3 : (String) "Unlocked"
' Parameter 4 : (Boolean) False
'--------------------------------------------------

long2246 = settingRepository1.GetAttr("SPECIFICVOLUME_OVER_TEMPERATURE_Large")
'--------------------------------------------------
' Parameter 1 : (String) "SPECIFICVOLUME_OVER_TEMPERATURE_Large"
' Returned value : (Variant) (Long) 1
'--------------------------------------------------

Dim bSTR4491
bSTR4491 = ""
Dim bSTR4492
bSTR4492 = ""
Dim boolean2246
settingRepository1.GetAttrInfo "SPECIFICVOLUME_OVER_TEMPERATURE_Large", bSTR4491, bSTR4492, boolean2246
'--------------------------------------------------
' Parameter 1 : (String) "SPECIFICVOLUME_OVER_TEMPERATURE_Large"
' Parameter 2 : (String) "Default value"
' Parameter 3 : (String) "Unlocked"
' Parameter 4 : (Boolean) False
'--------------------------------------------------

long2247 = settingRepository1.GetAttr("SPECIFICVOLUME_OVER_TEMPERATURE_ExtraLarge")
'--------------------------------------------------
' Parameter 1 : (String) "SPECIFICVOLUME_OVER_TEMPERATURE_ExtraLarge"
' Returned value : (Variant) (Long) 1
'--------------------------------------------------

Dim bSTR4493
bSTR4493 = ""
Dim bSTR4494
bSTR4494 = ""
Dim boolean2247
settingRepository1.GetAttrInfo "SPECIFICVOLUME_OVER_TEMPERATURE_ExtraLarge", bSTR4493, bSTR4494, boolean2247
'--------------------------------------------------
' Parameter 1 : (String) "SPECIFICVOLUME_OVER_TEMPERATURE_ExtraLarge"
' Parameter 2 : (String) "Default value"
' Parameter 3 : (String) "Unlocked"
' Parameter 4 : (Boolean) False
'--------------------------------------------------

long2248 = settingRepository1.GetAttr("SPECIFICVOLUME_OVER_TEMPERATURE_Small")
'--------------------------------------------------
' Parameter 1 : (String) "SPECIFICVOLUME_OVER_TEMPERATURE_Small"
' Returned value : (Variant) (Long) 1
'--------------------------------------------------

Dim bSTR4495
bSTR4495 = ""
Dim bSTR4496
bSTR4496 = ""
Dim boolean2248
settingRepository1.GetAttrInfo "SPECIFICVOLUME_OVER_TEMPERATURE_Small", bSTR4495, bSTR4496, boolean2248
'--------------------------------------------------
' Parameter 1 : (String) "SPECIFICVOLUME_OVER_TEMPERATURE_Small"
' Parameter 2 : (String) "Default value"
' Parameter 3 : (String) "Unlocked"
' Parameter 4 : (Boolean) False
'--------------------------------------------------

long2249 = settingRepository1.GetAttr("SPECIFICVOLUME_OVER_TEMPERATURE_ExtraSmall")
'--------------------------------------------------
' Parameter 1 : (String) "SPECIFICVOLUME_OVER_TEMPERATURE_ExtraSmall"
' Returned value : (Variant) (Long) 1
'--------------------------------------------------

Dim bSTR4497
bSTR4497 = ""
Dim bSTR4498
bSTR4498 = ""
Dim boolean2249
settingRepository1.GetAttrInfo "SPECIFICVOLUME_OVER_TEMPERATURE_ExtraSmall", bSTR4497, bSTR4498, boolean2249
'--------------------------------------------------
' Parameter 1 : (String) "SPECIFICVOLUME_OVER_TEMPERATURE_ExtraSmall"
' Parameter 2 : (String) "Default value"
' Parameter 3 : (String) "Unlocked"
' Parameter 4 : (Boolean) False
'--------------------------------------------------

long2250 = settingRepository1.GetAttr("SPECIFICVOLUME_OVER_TEMPERATURE_Nanometric")
'--------------------------------------------------
' Parameter 1 : (String) "SPECIFICVOLUME_OVER_TEMPERATURE_Nanometric"
' Returned value : (Variant) (Long) 1
'--------------------------------------------------

Dim bSTR4499
bSTR4499 = ""
Dim bSTR4500
bSTR4500 = ""
Dim boolean2250
settingRepository1.GetAttrInfo "SPECIFICVOLUME_OVER_TEMPERATURE_Nanometric", bSTR4499, bSTR4500, boolean2250
'--------------------------------------------------
' Parameter 1 : (String) "SPECIFICVOLUME_OVER_TEMPERATURE_Nanometric"
' Parameter 2 : (String) "Default value"
' Parameter 3 : (String) "Unlocked"
' Parameter 4 : (Boolean) False
'--------------------------------------------------

long2251 = settingRepository1.GetAttr("MOLE_PER_MASS")
'--------------------------------------------------
' Parameter 1 : (String) "MOLE_PER_MASS"
' Returned value : (Variant) (Long) 1
'--------------------------------------------------

Dim bSTR4501
bSTR4501 = ""
Dim bSTR4502
bSTR4502 = ""
Dim boolean2251
settingRepository1.GetAttrInfo "MOLE_PER_MASS", bSTR4501, bSTR4502, boolean2251
'--------------------------------------------------
' Parameter 1 : (String) "MOLE_PER_MASS"
' Parameter 2 : (String) "Default value"
' Parameter 3 : (String) "Unlocked"
' Parameter 4 : (Boolean) False
'--------------------------------------------------

long2252 = settingRepository1.GetAttr("MOLE_PER_MASS_Large")
'--------------------------------------------------
' Parameter 1 : (String) "MOLE_PER_MASS_Large"
' Returned value : (Variant) (Long) 1
'--------------------------------------------------

Dim bSTR4503
bSTR4503 = ""
Dim bSTR4504
bSTR4504 = ""
Dim boolean2252
settingRepository1.GetAttrInfo "MOLE_PER_MASS_Large", bSTR4503, bSTR4504, boolean2252
'--------------------------------------------------
' Parameter 1 : (String) "MOLE_PER_MASS_Large"
' Parameter 2 : (String) "Default value"
' Parameter 3 : (String) "Unlocked"
' Parameter 4 : (Boolean) False
'--------------------------------------------------

long2253 = settingRepository1.GetAttr("MOLE_PER_MASS_ExtraLarge")
'--------------------------------------------------
' Parameter 1 : (String) "MOLE_PER_MASS_ExtraLarge"
' Returned value : (Variant) (Long) 1
'--------------------------------------------------

Dim bSTR4505
bSTR4505 = ""
Dim bSTR4506
bSTR4506 = ""
Dim boolean2253
settingRepository1.GetAttrInfo "MOLE_PER_MASS_ExtraLarge", bSTR4505, bSTR4506, boolean2253
'--------------------------------------------------
' Parameter 1 : (String) "MOLE_PER_MASS_ExtraLarge"
' Parameter 2 : (String) "Default value"
' Parameter 3 : (String) "Unlocked"
' Parameter 4 : (Boolean) False
'--------------------------------------------------

long2254 = settingRepository1.GetAttr("MOLE_PER_MASS_Small")
'--------------------------------------------------
' Parameter 1 : (String) "MOLE_PER_MASS_Small"
' Returned value : (Variant) (Long) 1
'--------------------------------------------------

Dim bSTR4507
bSTR4507 = ""
Dim bSTR4508
bSTR4508 = ""
Dim boolean2254
settingRepository1.GetAttrInfo "MOLE_PER_MASS_Small", bSTR4507, bSTR4508, boolean2254
'--------------------------------------------------
' Parameter 1 : (String) "MOLE_PER_MASS_Small"
' Parameter 2 : (String) "Default value"
' Parameter 3 : (String) "Unlocked"
' Parameter 4 : (Boolean) False
'--------------------------------------------------

long2255 = settingRepository1.GetAttr("MOLE_PER_MASS_ExtraSmall")
'--------------------------------------------------
' Parameter 1 : (String) "MOLE_PER_MASS_ExtraSmall"
' Returned value : (Variant) (Long) 1
'--------------------------------------------------

Dim bSTR4509
bSTR4509 = ""
Dim bSTR4510
bSTR4510 = ""
Dim boolean2255
settingRepository1.GetAttrInfo "MOLE_PER_MASS_ExtraSmall", bSTR4509, bSTR4510, boolean2255
'--------------------------------------------------
' Parameter 1 : (String) "MOLE_PER_MASS_ExtraSmall"
' Parameter 2 : (String) "Default value"
' Parameter 3 : (String) "Unlocked"
' Parameter 4 : (Boolean) False
'--------------------------------------------------

long2256 = settingRepository1.GetAttr("MOLE_PER_MASS_Nanometric")
'--------------------------------------------------
' Parameter 1 : (String) "MOLE_PER_MASS_Nanometric"
' Returned value : (Variant) (Long) 1
'--------------------------------------------------

Dim bSTR4511
bSTR4511 = ""
Dim bSTR4512
bSTR4512 = ""
Dim boolean2256
settingRepository1.GetAttrInfo "MOLE_PER_MASS_Nanometric", bSTR4511, bSTR4512, boolean2256
'--------------------------------------------------
' Parameter 1 : (String) "MOLE_PER_MASS_Nanometric"
' Parameter 2 : (String) "Default value"
' Parameter 3 : (String) "Unlocked"
' Parameter 4 : (Boolean) False
'--------------------------------------------------

long2257 = settingRepository1.GetAttr("MASS_DIFFUSIVITY")
'--------------------------------------------------
' Parameter 1 : (String) "MASS_DIFFUSIVITY"
' Returned value : (Variant) (Long) 1
'--------------------------------------------------

Dim bSTR4513
bSTR4513 = ""
Dim bSTR4514
bSTR4514 = ""
Dim boolean2257
settingRepository1.GetAttrInfo "MASS_DIFFUSIVITY", bSTR4513, bSTR4514, boolean2257
'--------------------------------------------------
' Parameter 1 : (String) "MASS_DIFFUSIVITY"
' Parameter 2 : (String) "Default value"
' Parameter 3 : (String) "Unlocked"
' Parameter 4 : (Boolean) False
'--------------------------------------------------

long2258 = settingRepository1.GetAttr("MASS_DIFFUSIVITY_Large")
'--------------------------------------------------
' Parameter 1 : (String) "MASS_DIFFUSIVITY_Large"
' Returned value : (Variant) (Long) 1
'--------------------------------------------------

Dim bSTR4515
bSTR4515 = ""
Dim bSTR4516
bSTR4516 = ""
Dim boolean2258
settingRepository1.GetAttrInfo "MASS_DIFFUSIVITY_Large", bSTR4515, bSTR4516, boolean2258
'--------------------------------------------------
' Parameter 1 : (String) "MASS_DIFFUSIVITY_Large"
' Parameter 2 : (String) "Default value"
' Parameter 3 : (String) "Unlocked"
' Parameter 4 : (Boolean) False
'--------------------------------------------------

long2259 = settingRepository1.GetAttr("MASS_DIFFUSIVITY_ExtraLarge")
'--------------------------------------------------
' Parameter 1 : (String) "MASS_DIFFUSIVITY_ExtraLarge"
' Returned value : (Variant) (Long) 1
'--------------------------------------------------

Dim bSTR4517
bSTR4517 = ""
Dim bSTR4518
bSTR4518 = ""
Dim boolean2259
settingRepository1.GetAttrInfo "MASS_DIFFUSIVITY_ExtraLarge", bSTR4517, bSTR4518, boolean2259
'--------------------------------------------------
' Parameter 1 : (String) "MASS_DIFFUSIVITY_ExtraLarge"
' Parameter 2 : (String) "Default value"
' Parameter 3 : (String) "Unlocked"
' Parameter 4 : (Boolean) False
'--------------------------------------------------

long2260 = settingRepository1.GetAttr("MASS_DIFFUSIVITY_Small")
'--------------------------------------------------
' Parameter 1 : (String) "MASS_DIFFUSIVITY_Small"
' Returned value : (Variant) (Long) 1
'--------------------------------------------------

Dim bSTR4519
bSTR4519 = ""
Dim bSTR4520
bSTR4520 = ""
Dim boolean2260
settingRepository1.GetAttrInfo "MASS_DIFFUSIVITY_Small", bSTR4519, bSTR4520, boolean2260
'--------------------------------------------------
' Parameter 1 : (String) "MASS_DIFFUSIVITY_Small"
' Parameter 2 : (String) "Default value"
' Parameter 3 : (String) "Unlocked"
' Parameter 4 : (Boolean) False
'--------------------------------------------------

long2261 = settingRepository1.GetAttr("MASS_DIFFUSIVITY_ExtraSmall")
'--------------------------------------------------
' Parameter 1 : (String) "MASS_DIFFUSIVITY_ExtraSmall"
' Returned value : (Variant) (Long) 1
'--------------------------------------------------

Dim bSTR4521
bSTR4521 = ""
Dim bSTR4522
bSTR4522 = ""
Dim boolean2261
settingRepository1.GetAttrInfo "MASS_DIFFUSIVITY_ExtraSmall", bSTR4521, bSTR4522, boolean2261
'--------------------------------------------------
' Parameter 1 : (String) "MASS_DIFFUSIVITY_ExtraSmall"
' Parameter 2 : (String) "Default value"
' Parameter 3 : (String) "Unlocked"
' Parameter 4 : (Boolean) False
'--------------------------------------------------

long2262 = settingRepository1.GetAttr("MASS_DIFFUSIVITY_Nanometric")
'--------------------------------------------------
' Parameter 1 : (String) "MASS_DIFFUSIVITY_Nanometric"
' Returned value : (Variant) (Long) 1
'--------------------------------------------------

Dim bSTR4523
bSTR4523 = ""
Dim bSTR4524
bSTR4524 = ""
Dim boolean2262
settingRepository1.GetAttrInfo "MASS_DIFFUSIVITY_Nanometric", bSTR4523, bSTR4524, boolean2262
'--------------------------------------------------
' Parameter 1 : (String) "MASS_DIFFUSIVITY_Nanometric"
' Parameter 2 : (String) "Default value"
' Parameter 3 : (String) "Unlocked"
' Parameter 4 : (Boolean) False
'--------------------------------------------------

long2263 = settingRepository1.GetAttr("MASS_FLOW_PER_VOLUME")
'--------------------------------------------------
' Parameter 1 : (String) "MASS_FLOW_PER_VOLUME"
' Returned value : (Variant) (Long) 1
'--------------------------------------------------

Dim bSTR4525
bSTR4525 = ""
Dim bSTR4526
bSTR4526 = ""
Dim boolean2263
settingRepository1.GetAttrInfo "MASS_FLOW_PER_VOLUME", bSTR4525, bSTR4526, boolean2263
'--------------------------------------------------
' Parameter 1 : (String) "MASS_FLOW_PER_VOLUME"
' Parameter 2 : (String) "Default value"
' Parameter 3 : (String) "Unlocked"
' Parameter 4 : (Boolean) False
'--------------------------------------------------

long2264 = settingRepository1.GetAttr("MASS_FLOW_PER_VOLUME_Large")
'--------------------------------------------------
' Parameter 1 : (String) "MASS_FLOW_PER_VOLUME_Large"
' Returned value : (Variant) (Long) 1
'--------------------------------------------------

Dim bSTR4527
bSTR4527 = ""
Dim bSTR4528
bSTR4528 = ""
Dim boolean2264
settingRepository1.GetAttrInfo "MASS_FLOW_PER_VOLUME_Large", bSTR4527, bSTR4528, boolean2264
'--------------------------------------------------
' Parameter 1 : (String) "MASS_FLOW_PER_VOLUME_Large"
' Parameter 2 : (String) "Default value"
' Parameter 3 : (String) "Unlocked"
' Parameter 4 : (Boolean) False
'--------------------------------------------------

long2265 = settingRepository1.GetAttr("MASS_FLOW_PER_VOLUME_ExtraLarge")
'--------------------------------------------------
' Parameter 1 : (String) "MASS_FLOW_PER_VOLUME_ExtraLarge"
' Returned value : (Variant) (Long) 1
'--------------------------------------------------

Dim bSTR4529
bSTR4529 = ""
Dim bSTR4530
bSTR4530 = ""
Dim boolean2265
settingRepository1.GetAttrInfo "MASS_FLOW_PER_VOLUME_ExtraLarge", bSTR4529, bSTR4530, boolean2265
'--------------------------------------------------
' Parameter 1 : (String) "MASS_FLOW_PER_VOLUME_ExtraLarge"
' Parameter 2 : (String) "Default value"
' Parameter 3 : (String) "Unlocked"
' Parameter 4 : (Boolean) False
'--------------------------------------------------

long2266 = settingRepository1.GetAttr("MASS_FLOW_PER_VOLUME_Small")
'--------------------------------------------------
' Parameter 1 : (String) "MASS_FLOW_PER_VOLUME_Small"
' Returned value : (Variant) (Long) 1
'--------------------------------------------------

Dim bSTR4531
bSTR4531 = ""
Dim bSTR4532
bSTR4532 = ""
Dim boolean2266
settingRepository1.GetAttrInfo "MASS_FLOW_PER_VOLUME_Small", bSTR4531, bSTR4532, boolean2266
'--------------------------------------------------
' Parameter 1 : (String) "MASS_FLOW_PER_VOLUME_Small"
' Parameter 2 : (String) "Default value"
' Parameter 3 : (String) "Unlocked"
' Parameter 4 : (Boolean) False
'--------------------------------------------------

long2267 = settingRepository1.GetAttr("MASS_FLOW_PER_VOLUME_ExtraSmall")
'--------------------------------------------------
' Parameter 1 : (String) "MASS_FLOW_PER_VOLUME_ExtraSmall"
' Returned value : (Variant) (Long) 1
'--------------------------------------------------

Dim bSTR4533
bSTR4533 = ""
Dim bSTR4534
bSTR4534 = ""
Dim boolean2267
settingRepository1.GetAttrInfo "MASS_FLOW_PER_VOLUME_ExtraSmall", bSTR4533, bSTR4534, boolean2267
'--------------------------------------------------
' Parameter 1 : (String) "MASS_FLOW_PER_VOLUME_ExtraSmall"
' Parameter 2 : (String) "Default value"
' Parameter 3 : (String) "Unlocked"
' Parameter 4 : (Boolean) False
'--------------------------------------------------

long2268 = settingRepository1.GetAttr("MASS_FLOW_PER_VOLUME_Nanometric")
'--------------------------------------------------
' Parameter 1 : (String) "MASS_FLOW_PER_VOLUME_Nanometric"
' Returned value : (Variant) (Long) 1
'--------------------------------------------------

Dim bSTR4535
bSTR4535 = ""
Dim bSTR4536
bSTR4536 = ""
Dim boolean2268
settingRepository1.GetAttrInfo "MASS_FLOW_PER_VOLUME_Nanometric", bSTR4535, bSTR4536, boolean2268
'--------------------------------------------------
' Parameter 1 : (String) "MASS_FLOW_PER_VOLUME_Nanometric"
' Parameter 2 : (String) "Default value"
' Parameter 3 : (String) "Unlocked"
' Parameter 4 : (Boolean) False
'--------------------------------------------------

long2269 = settingRepository1.GetAttr("DENSITY_SQUARE_ANGULAR_SPEED")
'--------------------------------------------------
' Parameter 1 : (String) "DENSITY_SQUARE_ANGULAR_SPEED"
' Returned value : (Variant) (Long) 1
'--------------------------------------------------

Dim bSTR4537
bSTR4537 = ""
Dim bSTR4538
bSTR4538 = ""
Dim boolean2269
settingRepository1.GetAttrInfo "DENSITY_SQUARE_ANGULAR_SPEED", bSTR4537, bSTR4538, boolean2269
'--------------------------------------------------
' Parameter 1 : (String) "DENSITY_SQUARE_ANGULAR_SPEED"
' Parameter 2 : (String) "Default value"
' Parameter 3 : (String) "Unlocked"
' Parameter 4 : (Boolean) False
'--------------------------------------------------

long2270 = settingRepository1.GetAttr("DENSITY_SQUARE_ANGULAR_SPEED_Large")
'--------------------------------------------------
' Parameter 1 : (String) "DENSITY_SQUARE_ANGULAR_SPEED_Large"
' Returned value : (Variant) (Long) 1
'--------------------------------------------------

Dim bSTR4539
bSTR4539 = ""
Dim bSTR4540
bSTR4540 = ""
Dim boolean2270
settingRepository1.GetAttrInfo "DENSITY_SQUARE_ANGULAR_SPEED_Large", bSTR4539, bSTR4540, boolean2270
'--------------------------------------------------
' Parameter 1 : (String) "DENSITY_SQUARE_ANGULAR_SPEED_Large"
' Parameter 2 : (String) "Default value"
' Parameter 3 : (String) "Unlocked"
' Parameter 4 : (Boolean) False
'--------------------------------------------------

long2271 = settingRepository1.GetAttr("DENSITY_SQUARE_ANGULAR_SPEED_ExtraLarge")
'--------------------------------------------------
' Parameter 1 : (String) "DENSITY_SQUARE_ANGULAR_SPEED_ExtraLarge"
' Returned value : (Variant) (Long) 1
'--------------------------------------------------

Dim bSTR4541
bSTR4541 = ""
Dim bSTR4542
bSTR4542 = ""
Dim boolean2271
settingRepository1.GetAttrInfo "DENSITY_SQUARE_ANGULAR_SPEED_ExtraLarge", bSTR4541, bSTR4542, boolean2271
'--------------------------------------------------
' Parameter 1 : (String) "DENSITY_SQUARE_ANGULAR_SPEED_ExtraLarge"
' Parameter 2 : (String) "Default value"
' Parameter 3 : (String) "Unlocked"
' Parameter 4 : (Boolean) False
'--------------------------------------------------

long2272 = settingRepository1.GetAttr("DENSITY_SQUARE_ANGULAR_SPEED_Small")
'--------------------------------------------------
' Parameter 1 : (String) "DENSITY_SQUARE_ANGULAR_SPEED_Small"
' Returned value : (Variant) (Long) 1
'--------------------------------------------------

Dim bSTR4543
bSTR4543 = ""
Dim bSTR4544
bSTR4544 = ""
Dim boolean2272
settingRepository1.GetAttrInfo "DENSITY_SQUARE_ANGULAR_SPEED_Small", bSTR4543, bSTR4544, boolean2272
'--------------------------------------------------
' Parameter 1 : (String) "DENSITY_SQUARE_ANGULAR_SPEED_Small"
' Parameter 2 : (String) "Default value"
' Parameter 3 : (String) "Unlocked"
' Parameter 4 : (Boolean) False
'--------------------------------------------------

long2273 = settingRepository1.GetAttr("DENSITY_SQUARE_ANGULAR_SPEED_ExtraSmall")
'--------------------------------------------------
' Parameter 1 : (String) "DENSITY_SQUARE_ANGULAR_SPEED_ExtraSmall"
' Returned value : (Variant) (Long) 1
'--------------------------------------------------

Dim bSTR4545
bSTR4545 = ""
Dim bSTR4546
bSTR4546 = ""
Dim boolean2273
settingRepository1.GetAttrInfo "DENSITY_SQUARE_ANGULAR_SPEED_ExtraSmall", bSTR4545, bSTR4546, boolean2273
'--------------------------------------------------
' Parameter 1 : (String) "DENSITY_SQUARE_ANGULAR_SPEED_ExtraSmall"
' Parameter 2 : (String) "Default value"
' Parameter 3 : (String) "Unlocked"
' Parameter 4 : (Boolean) False
'--------------------------------------------------

long2274 = settingRepository1.GetAttr("DENSITY_SQUARE_ANGULAR_SPEED_Nanometric")
'--------------------------------------------------
' Parameter 1 : (String) "DENSITY_SQUARE_ANGULAR_SPEED_Nanometric"
' Returned value : (Variant) (Long) 1
'--------------------------------------------------

Dim bSTR4547
bSTR4547 = ""
Dim bSTR4548
bSTR4548 = ""
Dim boolean2274
settingRepository1.GetAttrInfo "DENSITY_SQUARE_ANGULAR_SPEED_Nanometric", bSTR4547, bSTR4548, boolean2274
'--------------------------------------------------
' Parameter 1 : (String) "DENSITY_SQUARE_ANGULAR_SPEED_Nanometric"
' Parameter 2 : (String) "Default value"
' Parameter 3 : (String) "Unlocked"
' Parameter 4 : (Boolean) False
'--------------------------------------------------

long2275 = settingRepository1.GetAttr("DENSITY_ANGULAR_SPEED")
'--------------------------------------------------
' Parameter 1 : (String) "DENSITY_ANGULAR_SPEED"
' Returned value : (Variant) (Long) 1
'--------------------------------------------------

Dim bSTR4549
bSTR4549 = ""
Dim bSTR4550
bSTR4550 = ""
Dim boolean2275
settingRepository1.GetAttrInfo "DENSITY_ANGULAR_SPEED", bSTR4549, bSTR4550, boolean2275
'--------------------------------------------------
' Parameter 1 : (String) "DENSITY_ANGULAR_SPEED"
' Parameter 2 : (String) "Default value"
' Parameter 3 : (String) "Unlocked"
' Parameter 4 : (Boolean) False
'--------------------------------------------------

long2276 = settingRepository1.GetAttr("DENSITY_ANGULAR_SPEED_Large")
'--------------------------------------------------
' Parameter 1 : (String) "DENSITY_ANGULAR_SPEED_Large"
' Returned value : (Variant) (Long) 1
'--------------------------------------------------

Dim bSTR4551
bSTR4551 = ""
Dim bSTR4552
bSTR4552 = ""
Dim boolean2276
settingRepository1.GetAttrInfo "DENSITY_ANGULAR_SPEED_Large", bSTR4551, bSTR4552, boolean2276
'--------------------------------------------------
' Parameter 1 : (String) "DENSITY_ANGULAR_SPEED_Large"
' Parameter 2 : (String) "Default value"
' Parameter 3 : (String) "Unlocked"
' Parameter 4 : (Boolean) False
'--------------------------------------------------

long2277 = settingRepository1.GetAttr("DENSITY_ANGULAR_SPEED_ExtraLarge")
'--------------------------------------------------
' Parameter 1 : (String) "DENSITY_ANGULAR_SPEED_ExtraLarge"
' Returned value : (Variant) (Long) 1
'--------------------------------------------------

Dim bSTR4553
bSTR4553 = ""
Dim bSTR4554
bSTR4554 = ""
Dim boolean2277
settingRepository1.GetAttrInfo "DENSITY_ANGULAR_SPEED_ExtraLarge", bSTR4553, bSTR4554, boolean2277
'--------------------------------------------------
' Parameter 1 : (String) "DENSITY_ANGULAR_SPEED_ExtraLarge"
' Parameter 2 : (String) "Default value"
' Parameter 3 : (String) "Unlocked"
' Parameter 4 : (Boolean) False
'--------------------------------------------------

long2278 = settingRepository1.GetAttr("DENSITY_ANGULAR_SPEED_Small")
'--------------------------------------------------
' Parameter 1 : (String) "DENSITY_ANGULAR_SPEED_Small"
' Returned value : (Variant) (Long) 1
'--------------------------------------------------

Dim bSTR4555
bSTR4555 = ""
Dim bSTR4556
bSTR4556 = ""
Dim boolean2278
settingRepository1.GetAttrInfo "DENSITY_ANGULAR_SPEED_Small", bSTR4555, bSTR4556, boolean2278
'--------------------------------------------------
' Parameter 1 : (String) "DENSITY_ANGULAR_SPEED_Small"
' Parameter 2 : (String) "Default value"
' Parameter 3 : (String) "Unlocked"
' Parameter 4 : (Boolean) False
'--------------------------------------------------

long2279 = settingRepository1.GetAttr("DENSITY_ANGULAR_SPEED_ExtraSmall")
'--------------------------------------------------
' Parameter 1 : (String) "DENSITY_ANGULAR_SPEED_ExtraSmall"
' Returned value : (Variant) (Long) 1
'--------------------------------------------------

Dim bSTR4557
bSTR4557 = ""
Dim bSTR4558
bSTR4558 = ""
Dim boolean2279
settingRepository1.GetAttrInfo "DENSITY_ANGULAR_SPEED_ExtraSmall", bSTR4557, bSTR4558, boolean2279
'--------------------------------------------------
' Parameter 1 : (String) "DENSITY_ANGULAR_SPEED_ExtraSmall"
' Parameter 2 : (String) "Default value"
' Parameter 3 : (String) "Unlocked"
' Parameter 4 : (Boolean) False
'--------------------------------------------------

long2280 = settingRepository1.GetAttr("DENSITY_ANGULAR_SPEED_Nanometric")
'--------------------------------------------------
' Parameter 1 : (String) "DENSITY_ANGULAR_SPEED_Nanometric"
' Returned value : (Variant) (Long) 1
'--------------------------------------------------

Dim bSTR4559
bSTR4559 = ""
Dim bSTR4560
bSTR4560 = ""
Dim boolean2280
settingRepository1.GetAttrInfo "DENSITY_ANGULAR_SPEED_Nanometric", bSTR4559, bSTR4560, boolean2280
'--------------------------------------------------
' Parameter 1 : (String) "DENSITY_ANGULAR_SPEED_Nanometric"
' Parameter 2 : (String) "Default value"
' Parameter 3 : (String) "Unlocked"
' Parameter 4 : (Boolean) False
'--------------------------------------------------

long2281 = settingRepository1.GetAttr("PRESSURE_OVER_SQUARE_TIME")
'--------------------------------------------------
' Parameter 1 : (String) "PRESSURE_OVER_SQUARE_TIME"
' Returned value : (Variant) (Long) 1
'--------------------------------------------------

Dim bSTR4561
bSTR4561 = ""
Dim bSTR4562
bSTR4562 = ""
Dim boolean2281
settingRepository1.GetAttrInfo "PRESSURE_OVER_SQUARE_TIME", bSTR4561, bSTR4562, boolean2281
'--------------------------------------------------
' Parameter 1 : (String) "PRESSURE_OVER_SQUARE_TIME"
' Parameter 2 : (String) "Default value"
' Parameter 3 : (String) "Unlocked"
' Parameter 4 : (Boolean) False
'--------------------------------------------------

long2282 = settingRepository1.GetAttr("PRESSURE_OVER_SQUARE_TIME_Large")
'--------------------------------------------------
' Parameter 1 : (String) "PRESSURE_OVER_SQUARE_TIME_Large"
' Returned value : (Variant) (Long) 1
'--------------------------------------------------

Dim bSTR4563
bSTR4563 = ""
Dim bSTR4564
bSTR4564 = ""
Dim boolean2282
settingRepository1.GetAttrInfo "PRESSURE_OVER_SQUARE_TIME_Large", bSTR4563, bSTR4564, boolean2282
'--------------------------------------------------
' Parameter 1 : (String) "PRESSURE_OVER_SQUARE_TIME_Large"
' Parameter 2 : (String) "Default value"
' Parameter 3 : (String) "Unlocked"
' Parameter 4 : (Boolean) False
'--------------------------------------------------

long2283 = settingRepository1.GetAttr("PRESSURE_OVER_SQUARE_TIME_ExtraLarge")
'--------------------------------------------------
' Parameter 1 : (String) "PRESSURE_OVER_SQUARE_TIME_ExtraLarge"
' Returned value : (Variant) (Long) 1
'--------------------------------------------------

Dim bSTR4565
bSTR4565 = ""
Dim bSTR4566
bSTR4566 = ""
Dim boolean2283
settingRepository1.GetAttrInfo "PRESSURE_OVER_SQUARE_TIME_ExtraLarge", bSTR4565, bSTR4566, boolean2283
'--------------------------------------------------
' Parameter 1 : (String) "PRESSURE_OVER_SQUARE_TIME_ExtraLarge"
' Parameter 2 : (String) "Default value"
' Parameter 3 : (String) "Unlocked"
' Parameter 4 : (Boolean) False
'--------------------------------------------------

long2284 = settingRepository1.GetAttr("PRESSURE_OVER_SQUARE_TIME_Small")
'--------------------------------------------------
' Parameter 1 : (String) "PRESSURE_OVER_SQUARE_TIME_Small"
' Returned value : (Variant) (Long) 1
'--------------------------------------------------

Dim bSTR4567
bSTR4567 = ""
Dim bSTR4568
bSTR4568 = ""
Dim boolean2284
settingRepository1.GetAttrInfo "PRESSURE_OVER_SQUARE_TIME_Small", bSTR4567, bSTR4568, boolean2284
'--------------------------------------------------
' Parameter 1 : (String) "PRESSURE_OVER_SQUARE_TIME_Small"
' Parameter 2 : (String) "Default value"
' Parameter 3 : (String) "Unlocked"
' Parameter 4 : (Boolean) False
'--------------------------------------------------

long2285 = settingRepository1.GetAttr("PRESSURE_OVER_SQUARE_TIME_ExtraSmall")
'--------------------------------------------------
' Parameter 1 : (String) "PRESSURE_OVER_SQUARE_TIME_ExtraSmall"
' Returned value : (Variant) (Long) 1
'--------------------------------------------------

Dim bSTR4569
bSTR4569 = ""
Dim bSTR4570
bSTR4570 = ""
Dim boolean2285
settingRepository1.GetAttrInfo "PRESSURE_OVER_SQUARE_TIME_ExtraSmall", bSTR4569, bSTR4570, boolean2285
'--------------------------------------------------
' Parameter 1 : (String) "PRESSURE_OVER_SQUARE_TIME_ExtraSmall"
' Parameter 2 : (String) "Default value"
' Parameter 3 : (String) "Unlocked"
' Parameter 4 : (Boolean) False
'--------------------------------------------------

long2286 = settingRepository1.GetAttr("PRESSURE_OVER_SQUARE_TIME_Nanometric")
'--------------------------------------------------
' Parameter 1 : (String) "PRESSURE_OVER_SQUARE_TIME_Nanometric"
' Returned value : (Variant) (Long) 1
'--------------------------------------------------

Dim bSTR4571
bSTR4571 = ""
Dim bSTR4572
bSTR4572 = ""
Dim boolean2286
settingRepository1.GetAttrInfo "PRESSURE_OVER_SQUARE_TIME_Nanometric", bSTR4571, bSTR4572, boolean2286
'--------------------------------------------------
' Parameter 1 : (String) "PRESSURE_OVER_SQUARE_TIME_Nanometric"
' Parameter 2 : (String) "Default value"
' Parameter 3 : (String) "Unlocked"
' Parameter 4 : (Boolean) False
'--------------------------------------------------

long2287 = settingRepository1.GetAttr("ACOUSTIC_INTENSITY")
'--------------------------------------------------
' Parameter 1 : (String) "ACOUSTIC_INTENSITY"
' Returned value : (Variant) (Long) 1
'--------------------------------------------------

Dim bSTR4573
bSTR4573 = ""
Dim bSTR4574
bSTR4574 = ""
Dim boolean2287
settingRepository1.GetAttrInfo "ACOUSTIC_INTENSITY", bSTR4573, bSTR4574, boolean2287
'--------------------------------------------------
' Parameter 1 : (String) "ACOUSTIC_INTENSITY"
' Parameter 2 : (String) "Default value"
' Parameter 3 : (String) "Unlocked"
' Parameter 4 : (Boolean) False
'--------------------------------------------------

long2288 = settingRepository1.GetAttr("ACOUSTIC_INTENSITY_Large")
'--------------------------------------------------
' Parameter 1 : (String) "ACOUSTIC_INTENSITY_Large"
' Returned value : (Variant) (Long) 1
'--------------------------------------------------

Dim bSTR4575
bSTR4575 = ""
Dim bSTR4576
bSTR4576 = ""
Dim boolean2288
settingRepository1.GetAttrInfo "ACOUSTIC_INTENSITY_Large", bSTR4575, bSTR4576, boolean2288
'--------------------------------------------------
' Parameter 1 : (String) "ACOUSTIC_INTENSITY_Large"
' Parameter 2 : (String) "Default value"
' Parameter 3 : (String) "Unlocked"
' Parameter 4 : (Boolean) False
'--------------------------------------------------

long2289 = settingRepository1.GetAttr("ACOUSTIC_INTENSITY_ExtraLarge")
'--------------------------------------------------
' Parameter 1 : (String) "ACOUSTIC_INTENSITY_ExtraLarge"
' Returned value : (Variant) (Long) 1
'--------------------------------------------------

Dim bSTR4577
bSTR4577 = ""
Dim bSTR4578
bSTR4578 = ""
Dim boolean2289
settingRepository1.GetAttrInfo "ACOUSTIC_INTENSITY_ExtraLarge", bSTR4577, bSTR4578, boolean2289
'--------------------------------------------------
' Parameter 1 : (String) "ACOUSTIC_INTENSITY_ExtraLarge"
' Parameter 2 : (String) "Default value"
' Parameter 3 : (String) "Unlocked"
' Parameter 4 : (Boolean) False
'--------------------------------------------------

long2290 = settingRepository1.GetAttr("ACOUSTIC_INTENSITY_Small")
'--------------------------------------------------
' Parameter 1 : (String) "ACOUSTIC_INTENSITY_Small"
' Returned value : (Variant) (Long) 1
'--------------------------------------------------

Dim bSTR4579
bSTR4579 = ""
Dim bSTR4580
bSTR4580 = ""
Dim boolean2290
settingRepository1.GetAttrInfo "ACOUSTIC_INTENSITY_Small", bSTR4579, bSTR4580, boolean2290
'--------------------------------------------------
' Parameter 1 : (String) "ACOUSTIC_INTENSITY_Small"
' Parameter 2 : (String) "Default value"
' Parameter 3 : (String) "Unlocked"
' Parameter 4 : (Boolean) False
'--------------------------------------------------

long2291 = settingRepository1.GetAttr("ACOUSTIC_INTENSITY_ExtraSmall")
'--------------------------------------------------
' Parameter 1 : (String) "ACOUSTIC_INTENSITY_ExtraSmall"
' Returned value : (Variant) (Long) 1
'--------------------------------------------------

Dim bSTR4581
bSTR4581 = ""
Dim bSTR4582
bSTR4582 = ""
Dim boolean2291
settingRepository1.GetAttrInfo "ACOUSTIC_INTENSITY_ExtraSmall", bSTR4581, bSTR4582, boolean2291
'--------------------------------------------------
' Parameter 1 : (String) "ACOUSTIC_INTENSITY_ExtraSmall"
' Parameter 2 : (String) "Default value"
' Parameter 3 : (String) "Unlocked"
' Parameter 4 : (Boolean) False
'--------------------------------------------------

long2292 = settingRepository1.GetAttr("ACOUSTIC_INTENSITY_Nanometric")
'--------------------------------------------------
' Parameter 1 : (String) "ACOUSTIC_INTENSITY_Nanometric"
' Returned value : (Variant) (Long) 1
'--------------------------------------------------

Dim bSTR4583
bSTR4583 = ""
Dim bSTR4584
bSTR4584 = ""
Dim boolean2292
settingRepository1.GetAttrInfo "ACOUSTIC_INTENSITY_Nanometric", bSTR4583, bSTR4584, boolean2292
'--------------------------------------------------
' Parameter 1 : (String) "ACOUSTIC_INTENSITY_Nanometric"
' Parameter 2 : (String) "Default value"
' Parameter 3 : (String) "Unlocked"
' Parameter 4 : (Boolean) False
'--------------------------------------------------

long2293 = settingRepository1.GetAttr("HEAT_FLUX_AREA")
'--------------------------------------------------
' Parameter 1 : (String) "HEAT_FLUX_AREA"
' Returned value : (Variant) (Long) 1
'--------------------------------------------------

Dim bSTR4585
bSTR4585 = ""
Dim bSTR4586
bSTR4586 = ""
Dim boolean2293
settingRepository1.GetAttrInfo "HEAT_FLUX_AREA", bSTR4585, bSTR4586, boolean2293
'--------------------------------------------------
' Parameter 1 : (String) "HEAT_FLUX_AREA"
' Parameter 2 : (String) "Default value"
' Parameter 3 : (String) "Unlocked"
' Parameter 4 : (Boolean) False
'--------------------------------------------------

long2294 = settingRepository1.GetAttr("HEAT_FLUX_AREA_Large")
'--------------------------------------------------
' Parameter 1 : (String) "HEAT_FLUX_AREA_Large"
' Returned value : (Variant) (Long) 1
'--------------------------------------------------

Dim bSTR4587
bSTR4587 = ""
Dim bSTR4588
bSTR4588 = ""
Dim boolean2294
settingRepository1.GetAttrInfo "HEAT_FLUX_AREA_Large", bSTR4587, bSTR4588, boolean2294
'--------------------------------------------------
' Parameter 1 : (String) "HEAT_FLUX_AREA_Large"
' Parameter 2 : (String) "Default value"
' Parameter 3 : (String) "Unlocked"
' Parameter 4 : (Boolean) False
'--------------------------------------------------

long2295 = settingRepository1.GetAttr("HEAT_FLUX_AREA_ExtraLarge")
'--------------------------------------------------
' Parameter 1 : (String) "HEAT_FLUX_AREA_ExtraLarge"
' Returned value : (Variant) (Long) 1
'--------------------------------------------------

Dim bSTR4589
bSTR4589 = ""
Dim bSTR4590
bSTR4590 = ""
Dim boolean2295
settingRepository1.GetAttrInfo "HEAT_FLUX_AREA_ExtraLarge", bSTR4589, bSTR4590, boolean2295
'--------------------------------------------------
' Parameter 1 : (String) "HEAT_FLUX_AREA_ExtraLarge"
' Parameter 2 : (String) "Default value"
' Parameter 3 : (String) "Unlocked"
' Parameter 4 : (Boolean) False
'--------------------------------------------------

long2296 = settingRepository1.GetAttr("HEAT_FLUX_AREA_Small")
'--------------------------------------------------
' Parameter 1 : (String) "HEAT_FLUX_AREA_Small"
' Returned value : (Variant) (Long) 1
'--------------------------------------------------

Dim bSTR4591
bSTR4591 = ""
Dim bSTR4592
bSTR4592 = ""
Dim boolean2296
settingRepository1.GetAttrInfo "HEAT_FLUX_AREA_Small", bSTR4591, bSTR4592, boolean2296
'--------------------------------------------------
' Parameter 1 : (String) "HEAT_FLUX_AREA_Small"
' Parameter 2 : (String) "Default value"
' Parameter 3 : (String) "Unlocked"
' Parameter 4 : (Boolean) False
'--------------------------------------------------

long2297 = settingRepository1.GetAttr("HEAT_FLUX_AREA_ExtraSmall")
'--------------------------------------------------
' Parameter 1 : (String) "HEAT_FLUX_AREA_ExtraSmall"
' Returned value : (Variant) (Long) 1
'--------------------------------------------------

Dim bSTR4593
bSTR4593 = ""
Dim bSTR4594
bSTR4594 = ""
Dim boolean2297
settingRepository1.GetAttrInfo "HEAT_FLUX_AREA_ExtraSmall", bSTR4593, bSTR4594, boolean2297
'--------------------------------------------------
' Parameter 1 : (String) "HEAT_FLUX_AREA_ExtraSmall"
' Parameter 2 : (String) "Default value"
' Parameter 3 : (String) "Unlocked"
' Parameter 4 : (Boolean) False
'--------------------------------------------------

long2298 = settingRepository1.GetAttr("HEAT_FLUX_AREA_Nanometric")
'--------------------------------------------------
' Parameter 1 : (String) "HEAT_FLUX_AREA_Nanometric"
' Returned value : (Variant) (Long) 1
'--------------------------------------------------

Dim bSTR4595
bSTR4595 = ""
Dim bSTR4596
bSTR4596 = ""
Dim boolean2298
settingRepository1.GetAttrInfo "HEAT_FLUX_AREA_Nanometric", bSTR4595, bSTR4596, boolean2298
'--------------------------------------------------
' Parameter 1 : (String) "HEAT_FLUX_AREA_Nanometric"
' Parameter 2 : (String) "Default value"
' Parameter 3 : (String) "Unlocked"
' Parameter 4 : (Boolean) False
'--------------------------------------------------

long2299 = settingRepository1.GetAttr("ARC_LENGTH")
'--------------------------------------------------
' Parameter 1 : (String) "ARC_LENGTH"
' Returned value : (Variant) (Long) 1
'--------------------------------------------------

Dim bSTR4597
bSTR4597 = ""
Dim bSTR4598
bSTR4598 = ""
Dim boolean2299
settingRepository1.GetAttrInfo "ARC_LENGTH", bSTR4597, bSTR4598, boolean2299
'--------------------------------------------------
' Parameter 1 : (String) "ARC_LENGTH"
' Parameter 2 : (String) "Default value"
' Parameter 3 : (String) "Unlocked"
' Parameter 4 : (Boolean) False
'--------------------------------------------------

long2300 = settingRepository1.GetAttr("ARC_LENGTH_Large")
'--------------------------------------------------
' Parameter 1 : (String) "ARC_LENGTH_Large"
' Returned value : (Variant) (Long) 1
'--------------------------------------------------

Dim bSTR4599
bSTR4599 = ""
Dim bSTR4600
bSTR4600 = ""
Dim boolean2300
settingRepository1.GetAttrInfo "ARC_LENGTH_Large", bSTR4599, bSTR4600, boolean2300
'--------------------------------------------------
' Parameter 1 : (String) "ARC_LENGTH_Large"
' Parameter 2 : (String) "Default value"
' Parameter 3 : (String) "Unlocked"
' Parameter 4 : (Boolean) False
'--------------------------------------------------

long2301 = settingRepository1.GetAttr("ARC_LENGTH_ExtraLarge")
'--------------------------------------------------
' Parameter 1 : (String) "ARC_LENGTH_ExtraLarge"
' Returned value : (Variant) (Long) 1
'--------------------------------------------------

Dim bSTR4601
bSTR4601 = ""
Dim bSTR4602
bSTR4602 = ""
Dim boolean2301
settingRepository1.GetAttrInfo "ARC_LENGTH_ExtraLarge", bSTR4601, bSTR4602, boolean2301
'--------------------------------------------------
' Parameter 1 : (String) "ARC_LENGTH_ExtraLarge"
' Parameter 2 : (String) "Default value"
' Parameter 3 : (String) "Unlocked"
' Parameter 4 : (Boolean) False
'--------------------------------------------------

long2302 = settingRepository1.GetAttr("ARC_LENGTH_Small")
'--------------------------------------------------
' Parameter 1 : (String) "ARC_LENGTH_Small"
' Returned value : (Variant) (Long) 1
'--------------------------------------------------

Dim bSTR4603
bSTR4603 = ""
Dim bSTR4604
bSTR4604 = ""
Dim boolean2302
settingRepository1.GetAttrInfo "ARC_LENGTH_Small", bSTR4603, bSTR4604, boolean2302
'--------------------------------------------------
' Parameter 1 : (String) "ARC_LENGTH_Small"
' Parameter 2 : (String) "Default value"
' Parameter 3 : (String) "Unlocked"
' Parameter 4 : (Boolean) False
'--------------------------------------------------

long2303 = settingRepository1.GetAttr("ARC_LENGTH_ExtraSmall")
'--------------------------------------------------
' Parameter 1 : (String) "ARC_LENGTH_ExtraSmall"
' Returned value : (Variant) (Long) 1
'--------------------------------------------------

Dim bSTR4605
bSTR4605 = ""
Dim bSTR4606
bSTR4606 = ""
Dim boolean2303
settingRepository1.GetAttrInfo "ARC_LENGTH_ExtraSmall", bSTR4605, bSTR4606, boolean2303
'--------------------------------------------------
' Parameter 1 : (String) "ARC_LENGTH_ExtraSmall"
' Parameter 2 : (String) "Default value"
' Parameter 3 : (String) "Unlocked"
' Parameter 4 : (Boolean) False
'--------------------------------------------------

long2304 = settingRepository1.GetAttr("ARC_LENGTH_Nanometric")
'--------------------------------------------------
' Parameter 1 : (String) "ARC_LENGTH_Nanometric"
' Returned value : (Variant) (Long) 1
'--------------------------------------------------

Dim bSTR4607
bSTR4607 = ""
Dim bSTR4608
bSTR4608 = ""
Dim boolean2304
settingRepository1.GetAttrInfo "ARC_LENGTH_Nanometric", bSTR4607, bSTR4608, boolean2304
'--------------------------------------------------
' Parameter 1 : (String) "ARC_LENGTH_Nanometric"
' Parameter 2 : (String) "Default value"
' Parameter 3 : (String) "Unlocked"
' Parameter 4 : (Boolean) False
'--------------------------------------------------

long2305 = settingRepository1.GetAttr("DISPLACEMENT")
'--------------------------------------------------
' Parameter 1 : (String) "DISPLACEMENT"
' Returned value : (Variant) (Long) 1
'--------------------------------------------------

Dim bSTR4609
bSTR4609 = ""
Dim bSTR4610
bSTR4610 = ""
Dim boolean2305
settingRepository1.GetAttrInfo "DISPLACEMENT", bSTR4609, bSTR4610, boolean2305
'--------------------------------------------------
' Parameter 1 : (String) "DISPLACEMENT"
' Parameter 2 : (String) "Default value"
' Parameter 3 : (String) "Unlocked"
' Parameter 4 : (Boolean) False
'--------------------------------------------------

long2306 = settingRepository1.GetAttr("DISPLACEMENT_Large")
'--------------------------------------------------
' Parameter 1 : (String) "DISPLACEMENT_Large"
' Returned value : (Variant) (Long) 1
'--------------------------------------------------

Dim bSTR4611
bSTR4611 = ""
Dim bSTR4612
bSTR4612 = ""
Dim boolean2306
settingRepository1.GetAttrInfo "DISPLACEMENT_Large", bSTR4611, bSTR4612, boolean2306
'--------------------------------------------------
' Parameter 1 : (String) "DISPLACEMENT_Large"
' Parameter 2 : (String) "Default value"
' Parameter 3 : (String) "Unlocked"
' Parameter 4 : (Boolean) False
'--------------------------------------------------

long2307 = settingRepository1.GetAttr("DISPLACEMENT_ExtraLarge")
'--------------------------------------------------
' Parameter 1 : (String) "DISPLACEMENT_ExtraLarge"
' Returned value : (Variant) (Long) 1
'--------------------------------------------------

Dim bSTR4613
bSTR4613 = ""
Dim bSTR4614
bSTR4614 = ""
Dim boolean2307
settingRepository1.GetAttrInfo "DISPLACEMENT_ExtraLarge", bSTR4613, bSTR4614, boolean2307
'--------------------------------------------------
' Parameter 1 : (String) "DISPLACEMENT_ExtraLarge"
' Parameter 2 : (String) "Default value"
' Parameter 3 : (String) "Unlocked"
' Parameter 4 : (Boolean) False
'--------------------------------------------------

long2308 = settingRepository1.GetAttr("DISPLACEMENT_Small")
'--------------------------------------------------
' Parameter 1 : (String) "DISPLACEMENT_Small"
' Returned value : (Variant) (Long) 1
'--------------------------------------------------

Dim bSTR4615
bSTR4615 = ""
Dim bSTR4616
bSTR4616 = ""
Dim boolean2308
settingRepository1.GetAttrInfo "DISPLACEMENT_Small", bSTR4615, bSTR4616, boolean2308
'--------------------------------------------------
' Parameter 1 : (String) "DISPLACEMENT_Small"
' Parameter 2 : (String) "Default value"
' Parameter 3 : (String) "Unlocked"
' Parameter 4 : (Boolean) False
'--------------------------------------------------

long2309 = settingRepository1.GetAttr("DISPLACEMENT_ExtraSmall")
'--------------------------------------------------
' Parameter 1 : (String) "DISPLACEMENT_ExtraSmall"
' Returned value : (Variant) (Long) 1
'--------------------------------------------------

Dim bSTR4617
bSTR4617 = ""
Dim bSTR4618
bSTR4618 = ""
Dim boolean2309
settingRepository1.GetAttrInfo "DISPLACEMENT_ExtraSmall", bSTR4617, bSTR4618, boolean2309
'--------------------------------------------------
' Parameter 1 : (String) "DISPLACEMENT_ExtraSmall"
' Parameter 2 : (String) "Default value"
' Parameter 3 : (String) "Unlocked"
' Parameter 4 : (Boolean) False
'--------------------------------------------------

long2310 = settingRepository1.GetAttr("DISPLACEMENT_Nanometric")
'--------------------------------------------------
' Parameter 1 : (String) "DISPLACEMENT_Nanometric"
' Returned value : (Variant) (Long) 1
'--------------------------------------------------

Dim bSTR4619
bSTR4619 = ""
Dim bSTR4620
bSTR4620 = ""
Dim boolean2310
settingRepository1.GetAttrInfo "DISPLACEMENT_Nanometric", bSTR4619, bSTR4620, boolean2310
'--------------------------------------------------
' Parameter 1 : (String) "DISPLACEMENT_Nanometric"
' Parameter 2 : (String) "Default value"
' Parameter 3 : (String) "Unlocked"
' Parameter 4 : (Boolean) False
'--------------------------------------------------

long2311 = settingRepository1.GetAttr("THICKNESS")
'--------------------------------------------------
' Parameter 1 : (String) "THICKNESS"
' Returned value : (Variant) (Long) 1
'--------------------------------------------------

Dim bSTR4621
bSTR4621 = ""
Dim bSTR4622
bSTR4622 = ""
Dim boolean2311
settingRepository1.GetAttrInfo "THICKNESS", bSTR4621, bSTR4622, boolean2311
'--------------------------------------------------
' Parameter 1 : (String) "THICKNESS"
' Parameter 2 : (String) "Default value"
' Parameter 3 : (String) "Unlocked"
' Parameter 4 : (Boolean) False
'--------------------------------------------------

long2312 = settingRepository1.GetAttr("THICKNESS_Large")
'--------------------------------------------------
' Parameter 1 : (String) "THICKNESS_Large"
' Returned value : (Variant) (Long) 1
'--------------------------------------------------

Dim bSTR4623
bSTR4623 = ""
Dim bSTR4624
bSTR4624 = ""
Dim boolean2312
settingRepository1.GetAttrInfo "THICKNESS_Large", bSTR4623, bSTR4624, boolean2312
'--------------------------------------------------
' Parameter 1 : (String) "THICKNESS_Large"
' Parameter 2 : (String) "Default value"
' Parameter 3 : (String) "Unlocked"
' Parameter 4 : (Boolean) False
'--------------------------------------------------

long2313 = settingRepository1.GetAttr("THICKNESS_ExtraLarge")
'--------------------------------------------------
' Parameter 1 : (String) "THICKNESS_ExtraLarge"
' Returned value : (Variant) (Long) 1
'--------------------------------------------------

Dim bSTR4625
bSTR4625 = ""
Dim bSTR4626
bSTR4626 = ""
Dim boolean2313
settingRepository1.GetAttrInfo "THICKNESS_ExtraLarge", bSTR4625, bSTR4626, boolean2313
'--------------------------------------------------
' Parameter 1 : (String) "THICKNESS_ExtraLarge"
' Parameter 2 : (String) "Default value"
' Parameter 3 : (String) "Unlocked"
' Parameter 4 : (Boolean) False
'--------------------------------------------------

long2314 = settingRepository1.GetAttr("THICKNESS_Small")
'--------------------------------------------------
' Parameter 1 : (String) "THICKNESS_Small"
' Returned value : (Variant) (Long) 1
'--------------------------------------------------

Dim bSTR4627
bSTR4627 = ""
Dim bSTR4628
bSTR4628 = ""
Dim boolean2314
settingRepository1.GetAttrInfo "THICKNESS_Small", bSTR4627, bSTR4628, boolean2314
'--------------------------------------------------
' Parameter 1 : (String) "THICKNESS_Small"
' Parameter 2 : (String) "Default value"
' Parameter 3 : (String) "Unlocked"
' Parameter 4 : (Boolean) False
'--------------------------------------------------

long2315 = settingRepository1.GetAttr("THICKNESS_ExtraSmall")
'--------------------------------------------------
' Parameter 1 : (String) "THICKNESS_ExtraSmall"
' Returned value : (Variant) (Long) 1
'--------------------------------------------------

Dim bSTR4629
bSTR4629 = ""
Dim bSTR4630
bSTR4630 = ""
Dim boolean2315
settingRepository1.GetAttrInfo "THICKNESS_ExtraSmall", bSTR4629, bSTR4630, boolean2315
'--------------------------------------------------
' Parameter 1 : (String) "THICKNESS_ExtraSmall"
' Parameter 2 : (String) "Default value"
' Parameter 3 : (String) "Unlocked"
' Parameter 4 : (Boolean) False
'--------------------------------------------------

long2316 = settingRepository1.GetAttr("THICKNESS_Nanometric")
'--------------------------------------------------
' Parameter 1 : (String) "THICKNESS_Nanometric"
' Returned value : (Variant) (Long) 1
'--------------------------------------------------

Dim bSTR4631
bSTR4631 = ""
Dim bSTR4632
bSTR4632 = ""
Dim boolean2316
settingRepository1.GetAttrInfo "THICKNESS_Nanometric", bSTR4631, bSTR4632, boolean2316
'--------------------------------------------------
' Parameter 1 : (String) "THICKNESS_Nanometric"
' Parameter 2 : (String) "Default value"
' Parameter 3 : (String) "Unlocked"
' Parameter 4 : (Boolean) False
'--------------------------------------------------

long2317 = settingRepository1.GetAttr("STRESS")
'--------------------------------------------------
' Parameter 1 : (String) "STRESS"
' Returned value : (Variant) (Long) 1
'--------------------------------------------------

Dim bSTR4633
bSTR4633 = ""
Dim bSTR4634
bSTR4634 = ""
Dim boolean2317
settingRepository1.GetAttrInfo "STRESS", bSTR4633, bSTR4634, boolean2317
'--------------------------------------------------
' Parameter 1 : (String) "STRESS"
' Parameter 2 : (String) "Default value"
' Parameter 3 : (String) "Unlocked"
' Parameter 4 : (Boolean) False
'--------------------------------------------------

long2318 = settingRepository1.GetAttr("STRESS_Large")
'--------------------------------------------------
' Parameter 1 : (String) "STRESS_Large"
' Returned value : (Variant) (Long) 1
'--------------------------------------------------

Dim bSTR4635
bSTR4635 = ""
Dim bSTR4636
bSTR4636 = ""
Dim boolean2318
settingRepository1.GetAttrInfo "STRESS_Large", bSTR4635, bSTR4636, boolean2318
'--------------------------------------------------
' Parameter 1 : (String) "STRESS_Large"
' Parameter 2 : (String) "Default value"
' Parameter 3 : (String) "Unlocked"
' Parameter 4 : (Boolean) False
'--------------------------------------------------

long2319 = settingRepository1.GetAttr("STRESS_ExtraLarge")
'--------------------------------------------------
' Parameter 1 : (String) "STRESS_ExtraLarge"
' Returned value : (Variant) (Long) 1
'--------------------------------------------------

Dim bSTR4637
bSTR4637 = ""
Dim bSTR4638
bSTR4638 = ""
Dim boolean2319
settingRepository1.GetAttrInfo "STRESS_ExtraLarge", bSTR4637, bSTR4638, boolean2319
'--------------------------------------------------
' Parameter 1 : (String) "STRESS_ExtraLarge"
' Parameter 2 : (String) "Default value"
' Parameter 3 : (String) "Unlocked"
' Parameter 4 : (Boolean) False
'--------------------------------------------------

long2320 = settingRepository1.GetAttr("STRESS_Small")
'--------------------------------------------------
' Parameter 1 : (String) "STRESS_Small"
' Returned value : (Variant) (Long) 1
'--------------------------------------------------

Dim bSTR4639
bSTR4639 = ""
Dim bSTR4640
bSTR4640 = ""
Dim boolean2320
settingRepository1.GetAttrInfo "STRESS_Small", bSTR4639, bSTR4640, boolean2320
'--------------------------------------------------
' Parameter 1 : (String) "STRESS_Small"
' Parameter 2 : (String) "Default value"
' Parameter 3 : (String) "Unlocked"
' Parameter 4 : (Boolean) False
'--------------------------------------------------

long2321 = settingRepository1.GetAttr("STRESS_ExtraSmall")
'--------------------------------------------------
' Parameter 1 : (String) "STRESS_ExtraSmall"
' Returned value : (Variant) (Long) 1
'--------------------------------------------------

Dim bSTR4641
bSTR4641 = ""
Dim bSTR4642
bSTR4642 = ""
Dim boolean2321
settingRepository1.GetAttrInfo "STRESS_ExtraSmall", bSTR4641, bSTR4642, boolean2321
'--------------------------------------------------
' Parameter 1 : (String) "STRESS_ExtraSmall"
' Parameter 2 : (String) "Default value"
' Parameter 3 : (String) "Unlocked"
' Parameter 4 : (Boolean) False
'--------------------------------------------------

long2322 = settingRepository1.GetAttr("STRESS_Nanometric")
'--------------------------------------------------
' Parameter 1 : (String) "STRESS_Nanometric"
' Returned value : (Variant) (Long) 1
'--------------------------------------------------

Dim bSTR4643
bSTR4643 = ""
Dim bSTR4644
bSTR4644 = ""
Dim boolean2322
settingRepository1.GetAttrInfo "STRESS_Nanometric", bSTR4643, bSTR4644, boolean2322
'--------------------------------------------------
' Parameter 1 : (String) "STRESS_Nanometric"
' Parameter 2 : (String) "Default value"
' Parameter 3 : (String) "Unlocked"
' Parameter 4 : (Boolean) False
'--------------------------------------------------

long2323 = settingRepository1.GetAttr("TURBULENT_ENERGY_DISSIPATION_RATE")
'--------------------------------------------------
' Parameter 1 : (String) "TURBULENT_ENERGY_DISSIPATION_RATE"
' Returned value : (Variant) (Long) 1
'--------------------------------------------------

Dim bSTR4645
bSTR4645 = ""
Dim bSTR4646
bSTR4646 = ""
Dim boolean2323
settingRepository1.GetAttrInfo "TURBULENT_ENERGY_DISSIPATION_RATE", bSTR4645, bSTR4646, boolean2323
'--------------------------------------------------
' Parameter 1 : (String) "TURBULENT_ENERGY_DISSIPATION_RATE"
' Parameter 2 : (String) "Default value"
' Parameter 3 : (String) "Unlocked"
' Parameter 4 : (Boolean) False
'--------------------------------------------------

long2324 = settingRepository1.GetAttr("TURBULENT_ENERGY_DISSIPATION_RATE_Large")
'--------------------------------------------------
' Parameter 1 : (String) "TURBULENT_ENERGY_DISSIPATION_RATE_Large"
' Returned value : (Variant) (Long) 1
'--------------------------------------------------

Dim bSTR4647
bSTR4647 = ""
Dim bSTR4648
bSTR4648 = ""
Dim boolean2324
settingRepository1.GetAttrInfo "TURBULENT_ENERGY_DISSIPATION_RATE_Large", bSTR4647, bSTR4648, boolean2324
'--------------------------------------------------
' Parameter 1 : (String) "TURBULENT_ENERGY_DISSIPATION_RATE_Large"
' Parameter 2 : (String) "Default value"
' Parameter 3 : (String) "Unlocked"
' Parameter 4 : (Boolean) False
'--------------------------------------------------

long2325 = settingRepository1.GetAttr("TURBULENT_ENERGY_DISSIPATION_RATE_ExtraLarge")
'--------------------------------------------------
' Parameter 1 : (String) "TURBULENT_ENERGY_DISSIPATION_RATE_ExtraLarge"
' Returned value : (Variant) (Long) 1
'--------------------------------------------------

Dim bSTR4649
bSTR4649 = ""
Dim bSTR4650
bSTR4650 = ""
Dim boolean2325
settingRepository1.GetAttrInfo "TURBULENT_ENERGY_DISSIPATION_RATE_ExtraLarge", bSTR4649, bSTR4650, boolean2325
'--------------------------------------------------
' Parameter 1 : (String) "TURBULENT_ENERGY_DISSIPATION_RATE_ExtraLarge"
' Parameter 2 : (String) "Default value"
' Parameter 3 : (String) "Unlocked"
' Parameter 4 : (Boolean) False
'--------------------------------------------------

long2326 = settingRepository1.GetAttr("TURBULENT_ENERGY_DISSIPATION_RATE_Small")
'--------------------------------------------------
' Parameter 1 : (String) "TURBULENT_ENERGY_DISSIPATION_RATE_Small"
' Returned value : (Variant) (Long) 1
'--------------------------------------------------

Dim bSTR4651
bSTR4651 = ""
Dim bSTR4652
bSTR4652 = ""
Dim boolean2326
settingRepository1.GetAttrInfo "TURBULENT_ENERGY_DISSIPATION_RATE_Small", bSTR4651, bSTR4652, boolean2326
'--------------------------------------------------
' Parameter 1 : (String) "TURBULENT_ENERGY_DISSIPATION_RATE_Small"
' Parameter 2 : (String) "Default value"
' Parameter 3 : (String) "Unlocked"
' Parameter 4 : (Boolean) False
'--------------------------------------------------

long2327 = settingRepository1.GetAttr("TURBULENT_ENERGY_DISSIPATION_RATE_ExtraSmall")
'--------------------------------------------------
' Parameter 1 : (String) "TURBULENT_ENERGY_DISSIPATION_RATE_ExtraSmall"
' Returned value : (Variant) (Long) 1
'--------------------------------------------------

Dim bSTR4653
bSTR4653 = ""
Dim bSTR4654
bSTR4654 = ""
Dim boolean2327
settingRepository1.GetAttrInfo "TURBULENT_ENERGY_DISSIPATION_RATE_ExtraSmall", bSTR4653, bSTR4654, boolean2327
'--------------------------------------------------
' Parameter 1 : (String) "TURBULENT_ENERGY_DISSIPATION_RATE_ExtraSmall"
' Parameter 2 : (String) "Default value"
' Parameter 3 : (String) "Unlocked"
' Parameter 4 : (Boolean) False
'--------------------------------------------------

long2328 = settingRepository1.GetAttr("TURBULENT_ENERGY_DISSIPATION_RATE_Nanometric")
'--------------------------------------------------
' Parameter 1 : (String) "TURBULENT_ENERGY_DISSIPATION_RATE_Nanometric"
' Returned value : (Variant) (Long) 1
'--------------------------------------------------

Dim bSTR4655
bSTR4655 = ""
Dim bSTR4656
bSTR4656 = ""
Dim boolean2328
settingRepository1.GetAttrInfo "TURBULENT_ENERGY_DISSIPATION_RATE_Nanometric", bSTR4655, bSTR4656, boolean2328
'--------------------------------------------------
' Parameter 1 : (String) "TURBULENT_ENERGY_DISSIPATION_RATE_Nanometric"
' Parameter 2 : (String) "Default value"
' Parameter 3 : (String) "Unlocked"
' Parameter 4 : (Boolean) False
'--------------------------------------------------

long2329 = settingRepository1.GetAttr("ENERGY_RELEASE_RATE")
'--------------------------------------------------
' Parameter 1 : (String) "ENERGY_RELEASE_RATE"
' Returned value : (Variant) (Long) 1
'--------------------------------------------------

Dim bSTR4657
bSTR4657 = ""
Dim bSTR4658
bSTR4658 = ""
Dim boolean2329
settingRepository1.GetAttrInfo "ENERGY_RELEASE_RATE", bSTR4657, bSTR4658, boolean2329
'--------------------------------------------------
' Parameter 1 : (String) "ENERGY_RELEASE_RATE"
' Parameter 2 : (String) "Default value"
' Parameter 3 : (String) "Unlocked"
' Parameter 4 : (Boolean) False
'--------------------------------------------------

long2330 = settingRepository1.GetAttr("ENERGY_RELEASE_RATE_Large")
'--------------------------------------------------
' Parameter 1 : (String) "ENERGY_RELEASE_RATE_Large"
' Returned value : (Variant) (Long) 1
'--------------------------------------------------

Dim bSTR4659
bSTR4659 = ""
Dim bSTR4660
bSTR4660 = ""
Dim boolean2330
settingRepository1.GetAttrInfo "ENERGY_RELEASE_RATE_Large", bSTR4659, bSTR4660, boolean2330
'--------------------------------------------------
' Parameter 1 : (String) "ENERGY_RELEASE_RATE_Large"
' Parameter 2 : (String) "Default value"
' Parameter 3 : (String) "Unlocked"
' Parameter 4 : (Boolean) False
'--------------------------------------------------

long2331 = settingRepository1.GetAttr("ENERGY_RELEASE_RATE_ExtraLarge")
'--------------------------------------------------
' Parameter 1 : (String) "ENERGY_RELEASE_RATE_ExtraLarge"
' Returned value : (Variant) (Long) 1
'--------------------------------------------------

Dim bSTR4661
bSTR4661 = ""
Dim bSTR4662
bSTR4662 = ""
Dim boolean2331
settingRepository1.GetAttrInfo "ENERGY_RELEASE_RATE_ExtraLarge", bSTR4661, bSTR4662, boolean2331
'--------------------------------------------------
' Parameter 1 : (String) "ENERGY_RELEASE_RATE_ExtraLarge"
' Parameter 2 : (String) "Default value"
' Parameter 3 : (String) "Unlocked"
' Parameter 4 : (Boolean) False
'--------------------------------------------------

long2332 = settingRepository1.GetAttr("ENERGY_RELEASE_RATE_Small")
'--------------------------------------------------
' Parameter 1 : (String) "ENERGY_RELEASE_RATE_Small"
' Returned value : (Variant) (Long) 1
'--------------------------------------------------

Dim bSTR4663
bSTR4663 = ""
Dim bSTR4664
bSTR4664 = ""
Dim boolean2332
settingRepository1.GetAttrInfo "ENERGY_RELEASE_RATE_Small", bSTR4663, bSTR4664, boolean2332
'--------------------------------------------------
' Parameter 1 : (String) "ENERGY_RELEASE_RATE_Small"
' Parameter 2 : (String) "Default value"
' Parameter 3 : (String) "Unlocked"
' Parameter 4 : (Boolean) False
'--------------------------------------------------

long2333 = settingRepository1.GetAttr("ENERGY_RELEASE_RATE_ExtraSmall")
'--------------------------------------------------
' Parameter 1 : (String) "ENERGY_RELEASE_RATE_ExtraSmall"
' Returned value : (Variant) (Long) 1
'--------------------------------------------------

Dim bSTR4665
bSTR4665 = ""
Dim bSTR4666
bSTR4666 = ""
Dim boolean2333
settingRepository1.GetAttrInfo "ENERGY_RELEASE_RATE_ExtraSmall", bSTR4665, bSTR4666, boolean2333
'--------------------------------------------------
' Parameter 1 : (String) "ENERGY_RELEASE_RATE_ExtraSmall"
' Parameter 2 : (String) "Default value"
' Parameter 3 : (String) "Unlocked"
' Parameter 4 : (Boolean) False
'--------------------------------------------------

long2334 = settingRepository1.GetAttr("ENERGY_RELEASE_RATE_Nanometric")
'--------------------------------------------------
' Parameter 1 : (String) "ENERGY_RELEASE_RATE_Nanometric"
' Returned value : (Variant) (Long) 1
'--------------------------------------------------

Dim bSTR4667
bSTR4667 = ""
Dim bSTR4668
bSTR4668 = ""
Dim boolean2334
settingRepository1.GetAttrInfo "ENERGY_RELEASE_RATE_Nanometric", bSTR4667, bSTR4668, boolean2334
'--------------------------------------------------
' Parameter 1 : (String) "ENERGY_RELEASE_RATE_Nanometric"
' Parameter 2 : (String) "Default value"
' Parameter 3 : (String) "Unlocked"
' Parameter 4 : (Boolean) False
'--------------------------------------------------

long2335 = settingRepository1.GetAttr("FORCE_PER_LENGTH")
'--------------------------------------------------
' Parameter 1 : (String) "FORCE_PER_LENGTH"
' Returned value : (Variant) (Long) 1
'--------------------------------------------------

Dim bSTR4669
bSTR4669 = ""
Dim bSTR4670
bSTR4670 = ""
Dim boolean2335
settingRepository1.GetAttrInfo "FORCE_PER_LENGTH", bSTR4669, bSTR4670, boolean2335
'--------------------------------------------------
' Parameter 1 : (String) "FORCE_PER_LENGTH"
' Parameter 2 : (String) "Default value"
' Parameter 3 : (String) "Unlocked"
' Parameter 4 : (Boolean) False
'--------------------------------------------------

long2336 = settingRepository1.GetAttr("FORCE_PER_LENGTH_Large")
'--------------------------------------------------
' Parameter 1 : (String) "FORCE_PER_LENGTH_Large"
' Returned value : (Variant) (Long) 1
'--------------------------------------------------

Dim bSTR4671
bSTR4671 = ""
Dim bSTR4672
bSTR4672 = ""
Dim boolean2336
settingRepository1.GetAttrInfo "FORCE_PER_LENGTH_Large", bSTR4671, bSTR4672, boolean2336
'--------------------------------------------------
' Parameter 1 : (String) "FORCE_PER_LENGTH_Large"
' Parameter 2 : (String) "Default value"
' Parameter 3 : (String) "Unlocked"
' Parameter 4 : (Boolean) False
'--------------------------------------------------

long2337 = settingRepository1.GetAttr("FORCE_PER_LENGTH_ExtraLarge")
'--------------------------------------------------
' Parameter 1 : (String) "FORCE_PER_LENGTH_ExtraLarge"
' Returned value : (Variant) (Long) 1
'--------------------------------------------------

Dim bSTR4673
bSTR4673 = ""
Dim bSTR4674
bSTR4674 = ""
Dim boolean2337
settingRepository1.GetAttrInfo "FORCE_PER_LENGTH_ExtraLarge", bSTR4673, bSTR4674, boolean2337
'--------------------------------------------------
' Parameter 1 : (String) "FORCE_PER_LENGTH_ExtraLarge"
' Parameter 2 : (String) "Default value"
' Parameter 3 : (String) "Unlocked"
' Parameter 4 : (Boolean) False
'--------------------------------------------------

long2338 = settingRepository1.GetAttr("FORCE_PER_LENGTH_Small")
'--------------------------------------------------
' Parameter 1 : (String) "FORCE_PER_LENGTH_Small"
' Returned value : (Variant) (Long) 1
'--------------------------------------------------

Dim bSTR4675
bSTR4675 = ""
Dim bSTR4676
bSTR4676 = ""
Dim boolean2338
settingRepository1.GetAttrInfo "FORCE_PER_LENGTH_Small", bSTR4675, bSTR4676, boolean2338
'--------------------------------------------------
' Parameter 1 : (String) "FORCE_PER_LENGTH_Small"
' Parameter 2 : (String) "Default value"
' Parameter 3 : (String) "Unlocked"
' Parameter 4 : (Boolean) False
'--------------------------------------------------

long2339 = settingRepository1.GetAttr("FORCE_PER_LENGTH_ExtraSmall")
'--------------------------------------------------
' Parameter 1 : (String) "FORCE_PER_LENGTH_ExtraSmall"
' Returned value : (Variant) (Long) 1
'--------------------------------------------------

Dim bSTR4677
bSTR4677 = ""
Dim bSTR4678
bSTR4678 = ""
Dim boolean2339
settingRepository1.GetAttrInfo "FORCE_PER_LENGTH_ExtraSmall", bSTR4677, bSTR4678, boolean2339
'--------------------------------------------------
' Parameter 1 : (String) "FORCE_PER_LENGTH_ExtraSmall"
' Parameter 2 : (String) "Default value"
' Parameter 3 : (String) "Unlocked"
' Parameter 4 : (Boolean) False
'--------------------------------------------------

long2340 = settingRepository1.GetAttr("FORCE_PER_LENGTH_Nanometric")
'--------------------------------------------------
' Parameter 1 : (String) "FORCE_PER_LENGTH_Nanometric"
' Returned value : (Variant) (Long) 1
'--------------------------------------------------

Dim bSTR4679
bSTR4679 = ""
Dim bSTR4680
bSTR4680 = ""
Dim boolean2340
settingRepository1.GetAttrInfo "FORCE_PER_LENGTH_Nanometric", bSTR4679, bSTR4680, boolean2340
'--------------------------------------------------
' Parameter 1 : (String) "FORCE_PER_LENGTH_Nanometric"
' Parameter 2 : (String) "Default value"
' Parameter 3 : (String) "Unlocked"
' Parameter 4 : (Boolean) False
'--------------------------------------------------

long2341 = settingRepository1.GetAttr("HEAT_GENERATION_DENSITY")
'--------------------------------------------------
' Parameter 1 : (String) "HEAT_GENERATION_DENSITY"
' Returned value : (Variant) (Long) 1
'--------------------------------------------------

Dim bSTR4681
bSTR4681 = ""
Dim bSTR4682
bSTR4682 = ""
Dim boolean2341
settingRepository1.GetAttrInfo "HEAT_GENERATION_DENSITY", bSTR4681, bSTR4682, boolean2341
'--------------------------------------------------
' Parameter 1 : (String) "HEAT_GENERATION_DENSITY"
' Parameter 2 : (String) "Default value"
' Parameter 3 : (String) "Unlocked"
' Parameter 4 : (Boolean) False
'--------------------------------------------------

long2342 = settingRepository1.GetAttr("HEAT_GENERATION_DENSITY_Large")
'--------------------------------------------------
' Parameter 1 : (String) "HEAT_GENERATION_DENSITY_Large"
' Returned value : (Variant) (Long) 1
'--------------------------------------------------

Dim bSTR4683
bSTR4683 = ""
Dim bSTR4684
bSTR4684 = ""
Dim boolean2342
settingRepository1.GetAttrInfo "HEAT_GENERATION_DENSITY_Large", bSTR4683, bSTR4684, boolean2342
'--------------------------------------------------
' Parameter 1 : (String) "HEAT_GENERATION_DENSITY_Large"
' Parameter 2 : (String) "Default value"
' Parameter 3 : (String) "Unlocked"
' Parameter 4 : (Boolean) False
'--------------------------------------------------

long2343 = settingRepository1.GetAttr("HEAT_GENERATION_DENSITY_ExtraLarge")
'--------------------------------------------------
' Parameter 1 : (String) "HEAT_GENERATION_DENSITY_ExtraLarge"
' Returned value : (Variant) (Long) 1
'--------------------------------------------------

Dim bSTR4685
bSTR4685 = ""
Dim bSTR4686
bSTR4686 = ""
Dim boolean2343
settingRepository1.GetAttrInfo "HEAT_GENERATION_DENSITY_ExtraLarge", bSTR4685, bSTR4686, boolean2343
'--------------------------------------------------
' Parameter 1 : (String) "HEAT_GENERATION_DENSITY_ExtraLarge"
' Parameter 2 : (String) "Default value"
' Parameter 3 : (String) "Unlocked"
' Parameter 4 : (Boolean) False
'--------------------------------------------------

long2344 = settingRepository1.GetAttr("HEAT_GENERATION_DENSITY_Small")
'--------------------------------------------------
' Parameter 1 : (String) "HEAT_GENERATION_DENSITY_Small"
' Returned value : (Variant) (Long) 1
'--------------------------------------------------

Dim bSTR4687
bSTR4687 = ""
Dim bSTR4688
bSTR4688 = ""
Dim boolean2344
settingRepository1.GetAttrInfo "HEAT_GENERATION_DENSITY_Small", bSTR4687, bSTR4688, boolean2344
'--------------------------------------------------
' Parameter 1 : (String) "HEAT_GENERATION_DENSITY_Small"
' Parameter 2 : (String) "Default value"
' Parameter 3 : (String) "Unlocked"
' Parameter 4 : (Boolean) False
'--------------------------------------------------

long2345 = settingRepository1.GetAttr("HEAT_GENERATION_DENSITY_ExtraSmall")
'--------------------------------------------------
' Parameter 1 : (String) "HEAT_GENERATION_DENSITY_ExtraSmall"
' Returned value : (Variant) (Long) 1
'--------------------------------------------------

Dim bSTR4689
bSTR4689 = ""
Dim bSTR4690
bSTR4690 = ""
Dim boolean2345
settingRepository1.GetAttrInfo "HEAT_GENERATION_DENSITY_ExtraSmall", bSTR4689, bSTR4690, boolean2345
'--------------------------------------------------
' Parameter 1 : (String) "HEAT_GENERATION_DENSITY_ExtraSmall"
' Parameter 2 : (String) "Default value"
' Parameter 3 : (String) "Unlocked"
' Parameter 4 : (Boolean) False
'--------------------------------------------------

long2346 = settingRepository1.GetAttr("HEAT_GENERATION_DENSITY_Nanometric")
'--------------------------------------------------
' Parameter 1 : (String) "HEAT_GENERATION_DENSITY_Nanometric"
' Returned value : (Variant) (Long) 1
'--------------------------------------------------

Dim bSTR4691
bSTR4691 = ""
Dim bSTR4692
bSTR4692 = ""
Dim boolean2346
settingRepository1.GetAttrInfo "HEAT_GENERATION_DENSITY_Nanometric", bSTR4691, bSTR4692, boolean2346
'--------------------------------------------------
' Parameter 1 : (String) "HEAT_GENERATION_DENSITY_Nanometric"
' Parameter 2 : (String) "Default value"
' Parameter 3 : (String) "Unlocked"
' Parameter 4 : (Boolean) False
'--------------------------------------------------

long2347 = settingRepository1.GetAttr("MASS_FLUX")
'--------------------------------------------------
' Parameter 1 : (String) "MASS_FLUX"
' Returned value : (Variant) (Long) 1
'--------------------------------------------------

Dim bSTR4693
bSTR4693 = ""
Dim bSTR4694
bSTR4694 = ""
Dim boolean2347
settingRepository1.GetAttrInfo "MASS_FLUX", bSTR4693, bSTR4694, boolean2347
'--------------------------------------------------
' Parameter 1 : (String) "MASS_FLUX"
' Parameter 2 : (String) "Default value"
' Parameter 3 : (String) "Unlocked"
' Parameter 4 : (Boolean) False
'--------------------------------------------------

long2348 = settingRepository1.GetAttr("MASS_FLUX_Large")
'--------------------------------------------------
' Parameter 1 : (String) "MASS_FLUX_Large"
' Returned value : (Variant) (Long) 1
'--------------------------------------------------

Dim bSTR4695
bSTR4695 = ""
Dim bSTR4696
bSTR4696 = ""
Dim boolean2348
settingRepository1.GetAttrInfo "MASS_FLUX_Large", bSTR4695, bSTR4696, boolean2348
'--------------------------------------------------
' Parameter 1 : (String) "MASS_FLUX_Large"
' Parameter 2 : (String) "Default value"
' Parameter 3 : (String) "Unlocked"
' Parameter 4 : (Boolean) False
'--------------------------------------------------

long2349 = settingRepository1.GetAttr("MASS_FLUX_ExtraLarge")
'--------------------------------------------------
' Parameter 1 : (String) "MASS_FLUX_ExtraLarge"
' Returned value : (Variant) (Long) 1
'--------------------------------------------------

Dim bSTR4697
bSTR4697 = ""
Dim bSTR4698
bSTR4698 = ""
Dim boolean2349
settingRepository1.GetAttrInfo "MASS_FLUX_ExtraLarge", bSTR4697, bSTR4698, boolean2349
'--------------------------------------------------
' Parameter 1 : (String) "MASS_FLUX_ExtraLarge"
' Parameter 2 : (String) "Default value"
' Parameter 3 : (String) "Unlocked"
' Parameter 4 : (Boolean) False
'--------------------------------------------------

long2350 = settingRepository1.GetAttr("MASS_FLUX_Small")
'--------------------------------------------------
' Parameter 1 : (String) "MASS_FLUX_Small"
' Returned value : (Variant) (Long) 1
'--------------------------------------------------

Dim bSTR4699
bSTR4699 = ""
Dim bSTR4700
bSTR4700 = ""
Dim boolean2350
settingRepository1.GetAttrInfo "MASS_FLUX_Small", bSTR4699, bSTR4700, boolean2350
'--------------------------------------------------
' Parameter 1 : (String) "MASS_FLUX_Small"
' Parameter 2 : (String) "Default value"
' Parameter 3 : (String) "Unlocked"
' Parameter 4 : (Boolean) False
'--------------------------------------------------

long2351 = settingRepository1.GetAttr("MASS_FLUX_ExtraSmall")
'--------------------------------------------------
' Parameter 1 : (String) "MASS_FLUX_ExtraSmall"
' Returned value : (Variant) (Long) 1
'--------------------------------------------------

Dim bSTR4701
bSTR4701 = ""
Dim bSTR4702
bSTR4702 = ""
Dim boolean2351
settingRepository1.GetAttrInfo "MASS_FLUX_ExtraSmall", bSTR4701, bSTR4702, boolean2351
'--------------------------------------------------
' Parameter 1 : (String) "MASS_FLUX_ExtraSmall"
' Parameter 2 : (String) "Default value"
' Parameter 3 : (String) "Unlocked"
' Parameter 4 : (Boolean) False
'--------------------------------------------------

long2352 = settingRepository1.GetAttr("MASS_FLUX_Nanometric")
'--------------------------------------------------
' Parameter 1 : (String) "MASS_FLUX_Nanometric"
' Returned value : (Variant) (Long) 1
'--------------------------------------------------

Dim bSTR4703
bSTR4703 = ""
Dim bSTR4704
bSTR4704 = ""
Dim boolean2352
settingRepository1.GetAttrInfo "MASS_FLUX_Nanometric", bSTR4703, bSTR4704, boolean2352
'--------------------------------------------------
' Parameter 1 : (String) "MASS_FLUX_Nanometric"
' Parameter 2 : (String) "Default value"
' Parameter 3 : (String) "Unlocked"
' Parameter 4 : (Boolean) False
'--------------------------------------------------

long2353 = settingRepository1.GetAttr("OMEGA_SQUARED")
'--------------------------------------------------
' Parameter 1 : (String) "OMEGA_SQUARED"
' Returned value : (Variant) (Long) 1
'--------------------------------------------------

Dim bSTR4705
bSTR4705 = ""
Dim bSTR4706
bSTR4706 = ""
Dim boolean2353
settingRepository1.GetAttrInfo "OMEGA_SQUARED", bSTR4705, bSTR4706, boolean2353
'--------------------------------------------------
' Parameter 1 : (String) "OMEGA_SQUARED"
' Parameter 2 : (String) "Default value"
' Parameter 3 : (String) "Unlocked"
' Parameter 4 : (Boolean) False
'--------------------------------------------------

long2354 = settingRepository1.GetAttr("OMEGA_SQUARED_Large")
'--------------------------------------------------
' Parameter 1 : (String) "OMEGA_SQUARED_Large"
' Returned value : (Variant) (Long) 1
'--------------------------------------------------

Dim bSTR4707
bSTR4707 = ""
Dim bSTR4708
bSTR4708 = ""
Dim boolean2354
settingRepository1.GetAttrInfo "OMEGA_SQUARED_Large", bSTR4707, bSTR4708, boolean2354
'--------------------------------------------------
' Parameter 1 : (String) "OMEGA_SQUARED_Large"
' Parameter 2 : (String) "Default value"
' Parameter 3 : (String) "Unlocked"
' Parameter 4 : (Boolean) False
'--------------------------------------------------

long2355 = settingRepository1.GetAttr("OMEGA_SQUARED_ExtraLarge")
'--------------------------------------------------
' Parameter 1 : (String) "OMEGA_SQUARED_ExtraLarge"
' Returned value : (Variant) (Long) 1
'--------------------------------------------------

Dim bSTR4709
bSTR4709 = ""
Dim bSTR4710
bSTR4710 = ""
Dim boolean2355
settingRepository1.GetAttrInfo "OMEGA_SQUARED_ExtraLarge", bSTR4709, bSTR4710, boolean2355
'--------------------------------------------------
' Parameter 1 : (String) "OMEGA_SQUARED_ExtraLarge"
' Parameter 2 : (String) "Default value"
' Parameter 3 : (String) "Unlocked"
' Parameter 4 : (Boolean) False
'--------------------------------------------------

long2356 = settingRepository1.GetAttr("OMEGA_SQUARED_Small")
'--------------------------------------------------
' Parameter 1 : (String) "OMEGA_SQUARED_Small"
' Returned value : (Variant) (Long) 1
'--------------------------------------------------

Dim bSTR4711
bSTR4711 = ""
Dim bSTR4712
bSTR4712 = ""
Dim boolean2356
settingRepository1.GetAttrInfo "OMEGA_SQUARED_Small", bSTR4711, bSTR4712, boolean2356
'--------------------------------------------------
' Parameter 1 : (String) "OMEGA_SQUARED_Small"
' Parameter 2 : (String) "Default value"
' Parameter 3 : (String) "Unlocked"
' Parameter 4 : (Boolean) False
'--------------------------------------------------

long2357 = settingRepository1.GetAttr("OMEGA_SQUARED_ExtraSmall")
'--------------------------------------------------
' Parameter 1 : (String) "OMEGA_SQUARED_ExtraSmall"
' Returned value : (Variant) (Long) 1
'--------------------------------------------------

Dim bSTR4713
bSTR4713 = ""
Dim bSTR4714
bSTR4714 = ""
Dim boolean2357
settingRepository1.GetAttrInfo "OMEGA_SQUARED_ExtraSmall", bSTR4713, bSTR4714, boolean2357
'--------------------------------------------------
' Parameter 1 : (String) "OMEGA_SQUARED_ExtraSmall"
' Parameter 2 : (String) "Default value"
' Parameter 3 : (String) "Unlocked"
' Parameter 4 : (Boolean) False
'--------------------------------------------------

long2358 = settingRepository1.GetAttr("OMEGA_SQUARED_Nanometric")
'--------------------------------------------------
' Parameter 1 : (String) "OMEGA_SQUARED_Nanometric"
' Returned value : (Variant) (Long) 1
'--------------------------------------------------

Dim bSTR4715
bSTR4715 = ""
Dim bSTR4716
bSTR4716 = ""
Dim boolean2358
settingRepository1.GetAttrInfo "OMEGA_SQUARED_Nanometric", bSTR4715, bSTR4716, boolean2358
'--------------------------------------------------
' Parameter 1 : (String) "OMEGA_SQUARED_Nanometric"
' Parameter 2 : (String) "Default value"
' Parameter 3 : (String) "Unlocked"
' Parameter 4 : (Boolean) False
'--------------------------------------------------

long2359 = settingRepository1.GetAttr("PRESSURE_GRADIENT")
'--------------------------------------------------
' Parameter 1 : (String) "PRESSURE_GRADIENT"
' Returned value : (Variant) (Long) 1
'--------------------------------------------------

Dim bSTR4717
bSTR4717 = ""
Dim bSTR4718
bSTR4718 = ""
Dim boolean2359
settingRepository1.GetAttrInfo "PRESSURE_GRADIENT", bSTR4717, bSTR4718, boolean2359
'--------------------------------------------------
' Parameter 1 : (String) "PRESSURE_GRADIENT"
' Parameter 2 : (String) "Default value"
' Parameter 3 : (String) "Unlocked"
' Parameter 4 : (Boolean) False
'--------------------------------------------------

long2360 = settingRepository1.GetAttr("PRESSURE_GRADIENT_Large")
'--------------------------------------------------
' Parameter 1 : (String) "PRESSURE_GRADIENT_Large"
' Returned value : (Variant) (Long) 1
'--------------------------------------------------

Dim bSTR4719
bSTR4719 = ""
Dim bSTR4720
bSTR4720 = ""
Dim boolean2360
settingRepository1.GetAttrInfo "PRESSURE_GRADIENT_Large", bSTR4719, bSTR4720, boolean2360
'--------------------------------------------------
' Parameter 1 : (String) "PRESSURE_GRADIENT_Large"
' Parameter 2 : (String) "Default value"
' Parameter 3 : (String) "Unlocked"
' Parameter 4 : (Boolean) False
'--------------------------------------------------

long2361 = settingRepository1.GetAttr("PRESSURE_GRADIENT_ExtraLarge")
'--------------------------------------------------
' Parameter 1 : (String) "PRESSURE_GRADIENT_ExtraLarge"
' Returned value : (Variant) (Long) 1
'--------------------------------------------------

Dim bSTR4721
bSTR4721 = ""
Dim bSTR4722
bSTR4722 = ""
Dim boolean2361
settingRepository1.GetAttrInfo "PRESSURE_GRADIENT_ExtraLarge", bSTR4721, bSTR4722, boolean2361
'--------------------------------------------------
' Parameter 1 : (String) "PRESSURE_GRADIENT_ExtraLarge"
' Parameter 2 : (String) "Default value"
' Parameter 3 : (String) "Unlocked"
' Parameter 4 : (Boolean) False
'--------------------------------------------------

long2362 = settingRepository1.GetAttr("PRESSURE_GRADIENT_Small")
'--------------------------------------------------
' Parameter 1 : (String) "PRESSURE_GRADIENT_Small"
' Returned value : (Variant) (Long) 1
'--------------------------------------------------

Dim bSTR4723
bSTR4723 = ""
Dim bSTR4724
bSTR4724 = ""
Dim boolean2362
settingRepository1.GetAttrInfo "PRESSURE_GRADIENT_Small", bSTR4723, bSTR4724, boolean2362
'--------------------------------------------------
' Parameter 1 : (String) "PRESSURE_GRADIENT_Small"
' Parameter 2 : (String) "Default value"
' Parameter 3 : (String) "Unlocked"
' Parameter 4 : (Boolean) False
'--------------------------------------------------

long2363 = settingRepository1.GetAttr("PRESSURE_GRADIENT_ExtraSmall")
'--------------------------------------------------
' Parameter 1 : (String) "PRESSURE_GRADIENT_ExtraSmall"
' Returned value : (Variant) (Long) 1
'--------------------------------------------------

Dim bSTR4725
bSTR4725 = ""
Dim bSTR4726
bSTR4726 = ""
Dim boolean2363
settingRepository1.GetAttrInfo "PRESSURE_GRADIENT_ExtraSmall", bSTR4725, bSTR4726, boolean2363
'--------------------------------------------------
' Parameter 1 : (String) "PRESSURE_GRADIENT_ExtraSmall"
' Parameter 2 : (String) "Default value"
' Parameter 3 : (String) "Unlocked"
' Parameter 4 : (Boolean) False
'--------------------------------------------------

long2364 = settingRepository1.GetAttr("PRESSURE_GRADIENT_Nanometric")
'--------------------------------------------------
' Parameter 1 : (String) "PRESSURE_GRADIENT_Nanometric"
' Returned value : (Variant) (Long) 1
'--------------------------------------------------

Dim bSTR4727
bSTR4727 = ""
Dim bSTR4728
bSTR4728 = ""
Dim boolean2364
settingRepository1.GetAttrInfo "PRESSURE_GRADIENT_Nanometric", bSTR4727, bSTR4728, boolean2364
'--------------------------------------------------
' Parameter 1 : (String) "PRESSURE_GRADIENT_Nanometric"
' Parameter 2 : (String) "Default value"
' Parameter 3 : (String) "Unlocked"
' Parameter 4 : (Boolean) False
'--------------------------------------------------

long2365 = settingRepository1.GetAttr("TWIST")
'--------------------------------------------------
' Parameter 1 : (String) "TWIST"
' Returned value : (Variant) (Long) 1
'--------------------------------------------------

Dim bSTR4729
bSTR4729 = ""
Dim bSTR4730
bSTR4730 = ""
Dim boolean2365
settingRepository1.GetAttrInfo "TWIST", bSTR4729, bSTR4730, boolean2365
'--------------------------------------------------
' Parameter 1 : (String) "TWIST"
' Parameter 2 : (String) "Default value"
' Parameter 3 : (String) "Unlocked"
' Parameter 4 : (Boolean) False
'--------------------------------------------------

long2366 = settingRepository1.GetAttr("TWIST_Large")
'--------------------------------------------------
' Parameter 1 : (String) "TWIST_Large"
' Returned value : (Variant) (Long) 1
'--------------------------------------------------

Dim bSTR4731
bSTR4731 = ""
Dim bSTR4732
bSTR4732 = ""
Dim boolean2366
settingRepository1.GetAttrInfo "TWIST_Large", bSTR4731, bSTR4732, boolean2366
'--------------------------------------------------
' Parameter 1 : (String) "TWIST_Large"
' Parameter 2 : (String) "Default value"
' Parameter 3 : (String) "Unlocked"
' Parameter 4 : (Boolean) False
'--------------------------------------------------

long2367 = settingRepository1.GetAttr("TWIST_ExtraLarge")
'--------------------------------------------------
' Parameter 1 : (String) "TWIST_ExtraLarge"
' Returned value : (Variant) (Long) 1
'--------------------------------------------------

Dim bSTR4733
bSTR4733 = ""
Dim bSTR4734
bSTR4734 = ""
Dim boolean2367
settingRepository1.GetAttrInfo "TWIST_ExtraLarge", bSTR4733, bSTR4734, boolean2367
'--------------------------------------------------
' Parameter 1 : (String) "TWIST_ExtraLarge"
' Parameter 2 : (String) "Default value"
' Parameter 3 : (String) "Unlocked"
' Parameter 4 : (Boolean) False
'--------------------------------------------------

long2368 = settingRepository1.GetAttr("TWIST_Small")
'--------------------------------------------------
' Parameter 1 : (String) "TWIST_Small"
' Returned value : (Variant) (Long) 1
'--------------------------------------------------

Dim bSTR4735
bSTR4735 = ""
Dim bSTR4736
bSTR4736 = ""
Dim boolean2368
settingRepository1.GetAttrInfo "TWIST_Small", bSTR4735, bSTR4736, boolean2368
'--------------------------------------------------
' Parameter 1 : (String) "TWIST_Small"
' Parameter 2 : (String) "Default value"
' Parameter 3 : (String) "Unlocked"
' Parameter 4 : (Boolean) False
'--------------------------------------------------

long2369 = settingRepository1.GetAttr("TWIST_ExtraSmall")
'--------------------------------------------------
' Parameter 1 : (String) "TWIST_ExtraSmall"
' Returned value : (Variant) (Long) 1
'--------------------------------------------------

Dim bSTR4737
bSTR4737 = ""
Dim bSTR4738
bSTR4738 = ""
Dim boolean2369
settingRepository1.GetAttrInfo "TWIST_ExtraSmall", bSTR4737, bSTR4738, boolean2369
'--------------------------------------------------
' Parameter 1 : (String) "TWIST_ExtraSmall"
' Parameter 2 : (String) "Default value"
' Parameter 3 : (String) "Unlocked"
' Parameter 4 : (Boolean) False
'--------------------------------------------------

long2370 = settingRepository1.GetAttr("TWIST_Nanometric")
'--------------------------------------------------
' Parameter 1 : (String) "TWIST_Nanometric"
' Returned value : (Variant) (Long) 1
'--------------------------------------------------

Dim bSTR4739
bSTR4739 = ""
Dim bSTR4740
bSTR4740 = ""
Dim boolean2370
settingRepository1.GetAttrInfo "TWIST_Nanometric", bSTR4739, bSTR4740, boolean2370
'--------------------------------------------------
' Parameter 1 : (String) "TWIST_Nanometric"
' Parameter 2 : (String) "Default value"
' Parameter 3 : (String) "Unlocked"
' Parameter 4 : (Boolean) False
'--------------------------------------------------

long2371 = settingRepository1.GetAttr("TIME_INTEGRATED_ELECTRIC_CURRENT_PER_AREA")
'--------------------------------------------------
' Parameter 1 : (String) "TIME_INTEGRATED_ELECTRIC_CURRENT_PER_AREA"
' Returned value : (Variant) (Long) 1
'--------------------------------------------------

Dim bSTR4741
bSTR4741 = ""
Dim bSTR4742
bSTR4742 = ""
Dim boolean2371
settingRepository1.GetAttrInfo "TIME_INTEGRATED_ELECTRIC_CURRENT_PER_AREA", bSTR4741, bSTR4742, boolean2371
'--------------------------------------------------
' Parameter 1 : (String) "TIME_INTEGRATED_ELECTRIC_CURRENT_PER_AREA"
' Parameter 2 : (String) "Default value"
' Parameter 3 : (String) "Unlocked"
' Parameter 4 : (Boolean) False
'--------------------------------------------------

long2372 = settingRepository1.GetAttr("TIME_INTEGRATED_ELECTRIC_CURRENT_PER_AREA_Large")
'--------------------------------------------------
' Parameter 1 : (String) "TIME_INTEGRATED_ELECTRIC_CURRENT_PER_AREA_Large"
' Returned value : (Variant) (Long) 1
'--------------------------------------------------

Dim bSTR4743
bSTR4743 = ""
Dim bSTR4744
bSTR4744 = ""
Dim boolean2372
settingRepository1.GetAttrInfo "TIME_INTEGRATED_ELECTRIC_CURRENT_PER_AREA_Large", bSTR4743, bSTR4744, boolean2372
'--------------------------------------------------
' Parameter 1 : (String) "TIME_INTEGRATED_ELECTRIC_CURRENT_PER_AREA_Large"
' Parameter 2 : (String) "Default value"
' Parameter 3 : (String) "Unlocked"
' Parameter 4 : (Boolean) False
'--------------------------------------------------

long2373 = settingRepository1.GetAttr("TIME_INTEGRATED_ELECTRIC_CURRENT_PER_AREA_ExtraLarge")
'--------------------------------------------------
' Parameter 1 : (String) "TIME_INTEGRATED_ELECTRIC_CURRENT_PER_AREA_ExtraLarge"
' Returned value : (Variant) (Long) 1
'--------------------------------------------------

Dim bSTR4745
bSTR4745 = ""
Dim bSTR4746
bSTR4746 = ""
Dim boolean2373
settingRepository1.GetAttrInfo "TIME_INTEGRATED_ELECTRIC_CURRENT_PER_AREA_ExtraLarge", bSTR4745, bSTR4746, boolean2373
'--------------------------------------------------
' Parameter 1 : (String) "TIME_INTEGRATED_ELECTRIC_CURRENT_PER_AREA_ExtraLarge"
' Parameter 2 : (String) "Default value"
' Parameter 3 : (String) "Unlocked"
' Parameter 4 : (Boolean) False
'--------------------------------------------------

long2374 = settingRepository1.GetAttr("TIME_INTEGRATED_ELECTRIC_CURRENT_PER_AREA_Small")
'--------------------------------------------------
' Parameter 1 : (String) "TIME_INTEGRATED_ELECTRIC_CURRENT_PER_AREA_Small"
' Returned value : (Variant) (Long) 1
'--------------------------------------------------

Dim bSTR4747
bSTR4747 = ""
Dim bSTR4748
bSTR4748 = ""
Dim boolean2374
settingRepository1.GetAttrInfo "TIME_INTEGRATED_ELECTRIC_CURRENT_PER_AREA_Small", bSTR4747, bSTR4748, boolean2374
'--------------------------------------------------
' Parameter 1 : (String) "TIME_INTEGRATED_ELECTRIC_CURRENT_PER_AREA_Small"
' Parameter 2 : (String) "Default value"
' Parameter 3 : (String) "Unlocked"
' Parameter 4 : (Boolean) False
'--------------------------------------------------

long2375 = settingRepository1.GetAttr("TIME_INTEGRATED_ELECTRIC_CURRENT_PER_AREA_ExtraSmall")
'--------------------------------------------------
' Parameter 1 : (String) "TIME_INTEGRATED_ELECTRIC_CURRENT_PER_AREA_ExtraSmall"
' Returned value : (Variant) (Long) 1
'--------------------------------------------------

Dim bSTR4749
bSTR4749 = ""
Dim bSTR4750
bSTR4750 = ""
Dim boolean2375
settingRepository1.GetAttrInfo "TIME_INTEGRATED_ELECTRIC_CURRENT_PER_AREA_ExtraSmall", bSTR4749, bSTR4750, boolean2375
'--------------------------------------------------
' Parameter 1 : (String) "TIME_INTEGRATED_ELECTRIC_CURRENT_PER_AREA_ExtraSmall"
' Parameter 2 : (String) "Default value"
' Parameter 3 : (String) "Unlocked"
' Parameter 4 : (Boolean) False
'--------------------------------------------------

long2376 = settingRepository1.GetAttr("TIME_INTEGRATED_ELECTRIC_CURRENT_PER_AREA_Nanometric")
'--------------------------------------------------
' Parameter 1 : (String) "TIME_INTEGRATED_ELECTRIC_CURRENT_PER_AREA_Nanometric"
' Returned value : (Variant) (Long) 1
'--------------------------------------------------

Dim bSTR4751
bSTR4751 = ""
Dim bSTR4752
bSTR4752 = ""
Dim boolean2376
settingRepository1.GetAttrInfo "TIME_INTEGRATED_ELECTRIC_CURRENT_PER_AREA_Nanometric", bSTR4751, bSTR4752, boolean2376
'--------------------------------------------------
' Parameter 1 : (String) "TIME_INTEGRATED_ELECTRIC_CURRENT_PER_AREA_Nanometric"
' Parameter 2 : (String) "Default value"
' Parameter 3 : (String) "Unlocked"
' Parameter 4 : (Boolean) False
'--------------------------------------------------

long2377 = settingRepository1.GetAttr("HEAT_FLOW_PER_VOLUME")
'--------------------------------------------------
' Parameter 1 : (String) "HEAT_FLOW_PER_VOLUME"
' Returned value : (Variant) (Long) 1
'--------------------------------------------------

Dim bSTR4753
bSTR4753 = ""
Dim bSTR4754
bSTR4754 = ""
Dim boolean2377
settingRepository1.GetAttrInfo "HEAT_FLOW_PER_VOLUME", bSTR4753, bSTR4754, boolean2377
'--------------------------------------------------
' Parameter 1 : (String) "HEAT_FLOW_PER_VOLUME"
' Parameter 2 : (String) "Default value"
' Parameter 3 : (String) "Unlocked"
' Parameter 4 : (Boolean) False
'--------------------------------------------------

long2378 = settingRepository1.GetAttr("HEAT_FLOW_PER_VOLUME_Large")
'--------------------------------------------------
' Parameter 1 : (String) "HEAT_FLOW_PER_VOLUME_Large"
' Returned value : (Variant) (Long) 1
'--------------------------------------------------

Dim bSTR4755
bSTR4755 = ""
Dim bSTR4756
bSTR4756 = ""
Dim boolean2378
settingRepository1.GetAttrInfo "HEAT_FLOW_PER_VOLUME_Large", bSTR4755, bSTR4756, boolean2378
'--------------------------------------------------
' Parameter 1 : (String) "HEAT_FLOW_PER_VOLUME_Large"
' Parameter 2 : (String) "Default value"
' Parameter 3 : (String) "Unlocked"
' Parameter 4 : (Boolean) False
'--------------------------------------------------

long2379 = settingRepository1.GetAttr("HEAT_FLOW_PER_VOLUME_ExtraLarge")
'--------------------------------------------------
' Parameter 1 : (String) "HEAT_FLOW_PER_VOLUME_ExtraLarge"
' Returned value : (Variant) (Long) 1
'--------------------------------------------------

Dim bSTR4757
bSTR4757 = ""
Dim bSTR4758
bSTR4758 = ""
Dim boolean2379
settingRepository1.GetAttrInfo "HEAT_FLOW_PER_VOLUME_ExtraLarge", bSTR4757, bSTR4758, boolean2379
'--------------------------------------------------
' Parameter 1 : (String) "HEAT_FLOW_PER_VOLUME_ExtraLarge"
' Parameter 2 : (String) "Default value"
' Parameter 3 : (String) "Unlocked"
' Parameter 4 : (Boolean) False
'--------------------------------------------------

long2380 = settingRepository1.GetAttr("HEAT_FLOW_PER_VOLUME_Small")
'--------------------------------------------------
' Parameter 1 : (String) "HEAT_FLOW_PER_VOLUME_Small"
' Returned value : (Variant) (Long) 1
'--------------------------------------------------

Dim bSTR4759
bSTR4759 = ""
Dim bSTR4760
bSTR4760 = ""
Dim boolean2380
settingRepository1.GetAttrInfo "HEAT_FLOW_PER_VOLUME_Small", bSTR4759, bSTR4760, boolean2380
'--------------------------------------------------
' Parameter 1 : (String) "HEAT_FLOW_PER_VOLUME_Small"
' Parameter 2 : (String) "Default value"
' Parameter 3 : (String) "Unlocked"
' Parameter 4 : (Boolean) False
'--------------------------------------------------

long2381 = settingRepository1.GetAttr("HEAT_FLOW_PER_VOLUME_ExtraSmall")
'--------------------------------------------------
' Parameter 1 : (String) "HEAT_FLOW_PER_VOLUME_ExtraSmall"
' Returned value : (Variant) (Long) 1
'--------------------------------------------------

Dim bSTR4761
bSTR4761 = ""
Dim bSTR4762
bSTR4762 = ""
Dim boolean2381
settingRepository1.GetAttrInfo "HEAT_FLOW_PER_VOLUME_ExtraSmall", bSTR4761, bSTR4762, boolean2381
'--------------------------------------------------
' Parameter 1 : (String) "HEAT_FLOW_PER_VOLUME_ExtraSmall"
' Parameter 2 : (String) "Default value"
' Parameter 3 : (String) "Unlocked"
' Parameter 4 : (Boolean) False
'--------------------------------------------------

long2382 = settingRepository1.GetAttr("HEAT_FLOW_PER_VOLUME_Nanometric")
'--------------------------------------------------
' Parameter 1 : (String) "HEAT_FLOW_PER_VOLUME_Nanometric"
' Returned value : (Variant) (Long) 1
'--------------------------------------------------

Dim bSTR4763
bSTR4763 = ""
Dim bSTR4764
bSTR4764 = ""
Dim boolean2382
settingRepository1.GetAttrInfo "HEAT_FLOW_PER_VOLUME_Nanometric", bSTR4763, bSTR4764, boolean2382
'--------------------------------------------------
' Parameter 1 : (String) "HEAT_FLOW_PER_VOLUME_Nanometric"
' Parameter 2 : (String) "Default value"
' Parameter 3 : (String) "Unlocked"
' Parameter 4 : (Boolean) False
'--------------------------------------------------

long2383 = settingRepository1.GetAttr("SOUND_PRESSURE_LEVEL")
'--------------------------------------------------
' Parameter 1 : (String) "SOUND_PRESSURE_LEVEL"
' Returned value : (Variant) (Long) 1
'--------------------------------------------------

Dim bSTR4765
bSTR4765 = ""
Dim bSTR4766
bSTR4766 = ""
Dim boolean2383
settingRepository1.GetAttrInfo "SOUND_PRESSURE_LEVEL", bSTR4765, bSTR4766, boolean2383
'--------------------------------------------------
' Parameter 1 : (String) "SOUND_PRESSURE_LEVEL"
' Parameter 2 : (String) "Default value"
' Parameter 3 : (String) "Unlocked"
' Parameter 4 : (Boolean) False
'--------------------------------------------------

long2384 = settingRepository1.GetAttr("SOUND_PRESSURE_LEVEL_Large")
'--------------------------------------------------
' Parameter 1 : (String) "SOUND_PRESSURE_LEVEL_Large"
' Returned value : (Variant) (Long) 1
'--------------------------------------------------

Dim bSTR4767
bSTR4767 = ""
Dim bSTR4768
bSTR4768 = ""
Dim boolean2384
settingRepository1.GetAttrInfo "SOUND_PRESSURE_LEVEL_Large", bSTR4767, bSTR4768, boolean2384
'--------------------------------------------------
' Parameter 1 : (String) "SOUND_PRESSURE_LEVEL_Large"
' Parameter 2 : (String) "Default value"
' Parameter 3 : (String) "Unlocked"
' Parameter 4 : (Boolean) False
'--------------------------------------------------

long2385 = settingRepository1.GetAttr("SOUND_PRESSURE_LEVEL_ExtraLarge")
'--------------------------------------------------
' Parameter 1 : (String) "SOUND_PRESSURE_LEVEL_ExtraLarge"
' Returned value : (Variant) (Long) 1
'--------------------------------------------------

Dim bSTR4769
bSTR4769 = ""
Dim bSTR4770
bSTR4770 = ""
Dim boolean2385
settingRepository1.GetAttrInfo "SOUND_PRESSURE_LEVEL_ExtraLarge", bSTR4769, bSTR4770, boolean2385
'--------------------------------------------------
' Parameter 1 : (String) "SOUND_PRESSURE_LEVEL_ExtraLarge"
' Parameter 2 : (String) "Default value"
' Parameter 3 : (String) "Unlocked"
' Parameter 4 : (Boolean) False
'--------------------------------------------------

long2386 = settingRepository1.GetAttr("SOUND_PRESSURE_LEVEL_Small")
'--------------------------------------------------
' Parameter 1 : (String) "SOUND_PRESSURE_LEVEL_Small"
' Returned value : (Variant) (Long) 1
'--------------------------------------------------

Dim bSTR4771
bSTR4771 = ""
Dim bSTR4772
bSTR4772 = ""
Dim boolean2386
settingRepository1.GetAttrInfo "SOUND_PRESSURE_LEVEL_Small", bSTR4771, bSTR4772, boolean2386
'--------------------------------------------------
' Parameter 1 : (String) "SOUND_PRESSURE_LEVEL_Small"
' Parameter 2 : (String) "Default value"
' Parameter 3 : (String) "Unlocked"
' Parameter 4 : (Boolean) False
'--------------------------------------------------

long2387 = settingRepository1.GetAttr("SOUND_PRESSURE_LEVEL_ExtraSmall")
'--------------------------------------------------
' Parameter 1 : (String) "SOUND_PRESSURE_LEVEL_ExtraSmall"
' Returned value : (Variant) (Long) 1
'--------------------------------------------------

Dim bSTR4773
bSTR4773 = ""
Dim bSTR4774
bSTR4774 = ""
Dim boolean2387
settingRepository1.GetAttrInfo "SOUND_PRESSURE_LEVEL_ExtraSmall", bSTR4773, bSTR4774, boolean2387
'--------------------------------------------------
' Parameter 1 : (String) "SOUND_PRESSURE_LEVEL_ExtraSmall"
' Parameter 2 : (String) "Default value"
' Parameter 3 : (String) "Unlocked"
' Parameter 4 : (Boolean) False
'--------------------------------------------------

long2388 = settingRepository1.GetAttr("SOUND_PRESSURE_LEVEL_Nanometric")
'--------------------------------------------------
' Parameter 1 : (String) "SOUND_PRESSURE_LEVEL_Nanometric"
' Returned value : (Variant) (Long) 1
'--------------------------------------------------

Dim bSTR4775
bSTR4775 = ""
Dim bSTR4776
bSTR4776 = ""
Dim boolean2388
settingRepository1.GetAttrInfo "SOUND_PRESSURE_LEVEL_Nanometric", bSTR4775, bSTR4776, boolean2388
'--------------------------------------------------
' Parameter 1 : (String) "SOUND_PRESSURE_LEVEL_Nanometric"
' Parameter 2 : (String) "Default value"
' Parameter 3 : (String) "Unlocked"
' Parameter 4 : (Boolean) False
'--------------------------------------------------

long2389 = settingRepository1.GetAttr("SPECIFIC_E_ABSORPTION_RATE")
'--------------------------------------------------
' Parameter 1 : (String) "SPECIFIC_E_ABSORPTION_RATE"
' Returned value : (Variant) (Long) 1
'--------------------------------------------------

Dim bSTR4777
bSTR4777 = ""
Dim bSTR4778
bSTR4778 = ""
Dim boolean2389
settingRepository1.GetAttrInfo "SPECIFIC_E_ABSORPTION_RATE", bSTR4777, bSTR4778, boolean2389
'--------------------------------------------------
' Parameter 1 : (String) "SPECIFIC_E_ABSORPTION_RATE"
' Parameter 2 : (String) "Default value"
' Parameter 3 : (String) "Unlocked"
' Parameter 4 : (Boolean) False
'--------------------------------------------------

long2390 = settingRepository1.GetAttr("SPECIFIC_E_ABSORPTION_RATE_Large")
'--------------------------------------------------
' Parameter 1 : (String) "SPECIFIC_E_ABSORPTION_RATE_Large"
' Returned value : (Variant) (Long) 1
'--------------------------------------------------

Dim bSTR4779
bSTR4779 = ""
Dim bSTR4780
bSTR4780 = ""
Dim boolean2390
settingRepository1.GetAttrInfo "SPECIFIC_E_ABSORPTION_RATE_Large", bSTR4779, bSTR4780, boolean2390
'--------------------------------------------------
' Parameter 1 : (String) "SPECIFIC_E_ABSORPTION_RATE_Large"
' Parameter 2 : (String) "Default value"
' Parameter 3 : (String) "Unlocked"
' Parameter 4 : (Boolean) False
'--------------------------------------------------

long2391 = settingRepository1.GetAttr("SPECIFIC_E_ABSORPTION_RATE_ExtraLarge")
'--------------------------------------------------
' Parameter 1 : (String) "SPECIFIC_E_ABSORPTION_RATE_ExtraLarge"
' Returned value : (Variant) (Long) 1
'--------------------------------------------------

Dim bSTR4781
bSTR4781 = ""
Dim bSTR4782
bSTR4782 = ""
Dim boolean2391
settingRepository1.GetAttrInfo "SPECIFIC_E_ABSORPTION_RATE_ExtraLarge", bSTR4781, bSTR4782, boolean2391
'--------------------------------------------------
' Parameter 1 : (String) "SPECIFIC_E_ABSORPTION_RATE_ExtraLarge"
' Parameter 2 : (String) "Default value"
' Parameter 3 : (String) "Unlocked"
' Parameter 4 : (Boolean) False
'--------------------------------------------------

long2392 = settingRepository1.GetAttr("SPECIFIC_E_ABSORPTION_RATE_Small")
'--------------------------------------------------
' Parameter 1 : (String) "SPECIFIC_E_ABSORPTION_RATE_Small"
' Returned value : (Variant) (Long) 1
'--------------------------------------------------

Dim bSTR4783
bSTR4783 = ""
Dim bSTR4784
bSTR4784 = ""
Dim boolean2392
settingRepository1.GetAttrInfo "SPECIFIC_E_ABSORPTION_RATE_Small", bSTR4783, bSTR4784, boolean2392
'--------------------------------------------------
' Parameter 1 : (String) "SPECIFIC_E_ABSORPTION_RATE_Small"
' Parameter 2 : (String) "Default value"
' Parameter 3 : (String) "Unlocked"
' Parameter 4 : (Boolean) False
'--------------------------------------------------

long2393 = settingRepository1.GetAttr("SPECIFIC_E_ABSORPTION_RATE_ExtraSmall")
'--------------------------------------------------
' Parameter 1 : (String) "SPECIFIC_E_ABSORPTION_RATE_ExtraSmall"
' Returned value : (Variant) (Long) 1
'--------------------------------------------------

Dim bSTR4785
bSTR4785 = ""
Dim bSTR4786
bSTR4786 = ""
Dim boolean2393
settingRepository1.GetAttrInfo "SPECIFIC_E_ABSORPTION_RATE_ExtraSmall", bSTR4785, bSTR4786, boolean2393
'--------------------------------------------------
' Parameter 1 : (String) "SPECIFIC_E_ABSORPTION_RATE_ExtraSmall"
' Parameter 2 : (String) "Default value"
' Parameter 3 : (String) "Unlocked"
' Parameter 4 : (Boolean) False
'--------------------------------------------------

long2394 = settingRepository1.GetAttr("SPECIFIC_E_ABSORPTION_RATE_Nanometric")
'--------------------------------------------------
' Parameter 1 : (String) "SPECIFIC_E_ABSORPTION_RATE_Nanometric"
' Returned value : (Variant) (Long) 1
'--------------------------------------------------

Dim bSTR4787
bSTR4787 = ""
Dim bSTR4788
bSTR4788 = ""
Dim boolean2394
settingRepository1.GetAttrInfo "SPECIFIC_E_ABSORPTION_RATE_Nanometric", bSTR4787, bSTR4788, boolean2394
'--------------------------------------------------
' Parameter 1 : (String) "SPECIFIC_E_ABSORPTION_RATE_Nanometric"
' Parameter 2 : (String) "Default value"
' Parameter 3 : (String) "Unlocked"
' Parameter 4 : (Boolean) False
'--------------------------------------------------

long2395 = settingRepository1.GetAttr("ENERGY_PER_AREA")
'--------------------------------------------------
' Parameter 1 : (String) "ENERGY_PER_AREA"
' Returned value : (Variant) (Long) 1
'--------------------------------------------------

Dim bSTR4789
bSTR4789 = ""
Dim bSTR4790
bSTR4790 = ""
Dim boolean2395
settingRepository1.GetAttrInfo "ENERGY_PER_AREA", bSTR4789, bSTR4790, boolean2395
'--------------------------------------------------
' Parameter 1 : (String) "ENERGY_PER_AREA"
' Parameter 2 : (String) "Default value"
' Parameter 3 : (String) "Unlocked"
' Parameter 4 : (Boolean) False
'--------------------------------------------------

long2396 = settingRepository1.GetAttr("ENERGY_PER_AREA_Large")
'--------------------------------------------------
' Parameter 1 : (String) "ENERGY_PER_AREA_Large"
' Returned value : (Variant) (Long) 1
'--------------------------------------------------

Dim bSTR4791
bSTR4791 = ""
Dim bSTR4792
bSTR4792 = ""
Dim boolean2396
settingRepository1.GetAttrInfo "ENERGY_PER_AREA_Large", bSTR4791, bSTR4792, boolean2396
'--------------------------------------------------
' Parameter 1 : (String) "ENERGY_PER_AREA_Large"
' Parameter 2 : (String) "Default value"
' Parameter 3 : (String) "Unlocked"
' Parameter 4 : (Boolean) False
'--------------------------------------------------

long2397 = settingRepository1.GetAttr("ENERGY_PER_AREA_ExtraLarge")
'--------------------------------------------------
' Parameter 1 : (String) "ENERGY_PER_AREA_ExtraLarge"
' Returned value : (Variant) (Long) 1
'--------------------------------------------------

Dim bSTR4793
bSTR4793 = ""
Dim bSTR4794
bSTR4794 = ""
Dim boolean2397
settingRepository1.GetAttrInfo "ENERGY_PER_AREA_ExtraLarge", bSTR4793, bSTR4794, boolean2397
'--------------------------------------------------
' Parameter 1 : (String) "ENERGY_PER_AREA_ExtraLarge"
' Parameter 2 : (String) "Default value"
' Parameter 3 : (String) "Unlocked"
' Parameter 4 : (Boolean) False
'--------------------------------------------------

long2398 = settingRepository1.GetAttr("ENERGY_PER_AREA_Small")
'--------------------------------------------------
' Parameter 1 : (String) "ENERGY_PER_AREA_Small"
' Returned value : (Variant) (Long) 1
'--------------------------------------------------

Dim bSTR4795
bSTR4795 = ""
Dim bSTR4796
bSTR4796 = ""
Dim boolean2398
settingRepository1.GetAttrInfo "ENERGY_PER_AREA_Small", bSTR4795, bSTR4796, boolean2398
'--------------------------------------------------
' Parameter 1 : (String) "ENERGY_PER_AREA_Small"
' Parameter 2 : (String) "Default value"
' Parameter 3 : (String) "Unlocked"
' Parameter 4 : (Boolean) False
'--------------------------------------------------

long2399 = settingRepository1.GetAttr("ENERGY_PER_AREA_ExtraSmall")
'--------------------------------------------------
' Parameter 1 : (String) "ENERGY_PER_AREA_ExtraSmall"
' Returned value : (Variant) (Long) 1
'--------------------------------------------------

Dim bSTR4797
bSTR4797 = ""
Dim bSTR4798
bSTR4798 = ""
Dim boolean2399
settingRepository1.GetAttrInfo "ENERGY_PER_AREA_ExtraSmall", bSTR4797, bSTR4798, boolean2399
'--------------------------------------------------
' Parameter 1 : (String) "ENERGY_PER_AREA_ExtraSmall"
' Parameter 2 : (String) "Default value"
' Parameter 3 : (String) "Unlocked"
' Parameter 4 : (Boolean) False
'--------------------------------------------------

long2400 = settingRepository1.GetAttr("ENERGY_PER_AREA_Nanometric")
'--------------------------------------------------
' Parameter 1 : (String) "ENERGY_PER_AREA_Nanometric"
' Returned value : (Variant) (Long) 1
'--------------------------------------------------

Dim bSTR4799
bSTR4799 = ""
Dim bSTR4800
bSTR4800 = ""
Dim boolean2400
settingRepository1.GetAttrInfo "ENERGY_PER_AREA_Nanometric", bSTR4799, bSTR4800, boolean2400
'--------------------------------------------------
' Parameter 1 : (String) "ENERGY_PER_AREA_Nanometric"
' Parameter 2 : (String) "Default value"
' Parameter 3 : (String) "Unlocked"
' Parameter 4 : (Boolean) False
'--------------------------------------------------

long2401 = settingRepository1.GetAttr("HYDRODYNAMIC_RESISTANCE_COEFFICIENT")
'--------------------------------------------------
' Parameter 1 : (String) "HYDRODYNAMIC_RESISTANCE_COEFFICIENT"
' Returned value : (Variant) (Long) 1
'--------------------------------------------------

Dim bSTR4801
bSTR4801 = ""
Dim bSTR4802
bSTR4802 = ""
Dim boolean2401
settingRepository1.GetAttrInfo "HYDRODYNAMIC_RESISTANCE_COEFFICIENT", bSTR4801, bSTR4802, boolean2401
'--------------------------------------------------
' Parameter 1 : (String) "HYDRODYNAMIC_RESISTANCE_COEFFICIENT"
' Parameter 2 : (String) "Default value"
' Parameter 3 : (String) "Unlocked"
' Parameter 4 : (Boolean) False
'--------------------------------------------------

long2402 = settingRepository1.GetAttr("HYDRODYNAMIC_RESISTANCE_COEFFICIENT_Large")
'--------------------------------------------------
' Parameter 1 : (String) "HYDRODYNAMIC_RESISTANCE_COEFFICIENT_Large"
' Returned value : (Variant) (Long) 1
'--------------------------------------------------

Dim bSTR4803
bSTR4803 = ""
Dim bSTR4804
bSTR4804 = ""
Dim boolean2402
settingRepository1.GetAttrInfo "HYDRODYNAMIC_RESISTANCE_COEFFICIENT_Large", bSTR4803, bSTR4804, boolean2402
'--------------------------------------------------
' Parameter 1 : (String) "HYDRODYNAMIC_RESISTANCE_COEFFICIENT_Large"
' Parameter 2 : (String) "Default value"
' Parameter 3 : (String) "Unlocked"
' Parameter 4 : (Boolean) False
'--------------------------------------------------

long2403 = settingRepository1.GetAttr("HYDRODYNAMIC_RESISTANCE_COEFFICIENT_ExtraLarge")
'--------------------------------------------------
' Parameter 1 : (String) "HYDRODYNAMIC_RESISTANCE_COEFFICIENT_ExtraLarge"
' Returned value : (Variant) (Long) 1
'--------------------------------------------------

Dim bSTR4805
bSTR4805 = ""
Dim bSTR4806
bSTR4806 = ""
Dim boolean2403
settingRepository1.GetAttrInfo "HYDRODYNAMIC_RESISTANCE_COEFFICIENT_ExtraLarge", bSTR4805, bSTR4806, boolean2403
'--------------------------------------------------
' Parameter 1 : (String) "HYDRODYNAMIC_RESISTANCE_COEFFICIENT_ExtraLarge"
' Parameter 2 : (String) "Default value"
' Parameter 3 : (String) "Unlocked"
' Parameter 4 : (Boolean) False
'--------------------------------------------------

long2404 = settingRepository1.GetAttr("HYDRODYNAMIC_RESISTANCE_COEFFICIENT_Small")
'--------------------------------------------------
' Parameter 1 : (String) "HYDRODYNAMIC_RESISTANCE_COEFFICIENT_Small"
' Returned value : (Variant) (Long) 1
'--------------------------------------------------

Dim bSTR4807
bSTR4807 = ""
Dim bSTR4808
bSTR4808 = ""
Dim boolean2404
settingRepository1.GetAttrInfo "HYDRODYNAMIC_RESISTANCE_COEFFICIENT_Small", bSTR4807, bSTR4808, boolean2404
'--------------------------------------------------
' Parameter 1 : (String) "HYDRODYNAMIC_RESISTANCE_COEFFICIENT_Small"
' Parameter 2 : (String) "Default value"
' Parameter 3 : (String) "Unlocked"
' Parameter 4 : (Boolean) False
'--------------------------------------------------

long2405 = settingRepository1.GetAttr("HYDRODYNAMIC_RESISTANCE_COEFFICIENT_ExtraSmall")
'--------------------------------------------------
' Parameter 1 : (String) "HYDRODYNAMIC_RESISTANCE_COEFFICIENT_ExtraSmall"
' Returned value : (Variant) (Long) 1
'--------------------------------------------------

Dim bSTR4809
bSTR4809 = ""
Dim bSTR4810
bSTR4810 = ""
Dim boolean2405
settingRepository1.GetAttrInfo "HYDRODYNAMIC_RESISTANCE_COEFFICIENT_ExtraSmall", bSTR4809, bSTR4810, boolean2405
'--------------------------------------------------
' Parameter 1 : (String) "HYDRODYNAMIC_RESISTANCE_COEFFICIENT_ExtraSmall"
' Parameter 2 : (String) "Default value"
' Parameter 3 : (String) "Unlocked"
' Parameter 4 : (Boolean) False
'--------------------------------------------------

long2406 = settingRepository1.GetAttr("HYDRODYNAMIC_RESISTANCE_COEFFICIENT_Nanometric")
'--------------------------------------------------
' Parameter 1 : (String) "HYDRODYNAMIC_RESISTANCE_COEFFICIENT_Nanometric"
' Returned value : (Variant) (Long) 1
'--------------------------------------------------

Dim bSTR4811
bSTR4811 = ""
Dim bSTR4812
bSTR4812 = ""
Dim boolean2406
settingRepository1.GetAttrInfo "HYDRODYNAMIC_RESISTANCE_COEFFICIENT_Nanometric", bSTR4811, bSTR4812, boolean2406
'--------------------------------------------------
' Parameter 1 : (String) "HYDRODYNAMIC_RESISTANCE_COEFFICIENT_Nanometric"
' Parameter 2 : (String) "Default value"
' Parameter 3 : (String) "Unlocked"
' Parameter 4 : (Boolean) False
'--------------------------------------------------

long2407 = settingRepository1.GetAttr("MOMENT_PER_LENGTH")
'--------------------------------------------------
' Parameter 1 : (String) "MOMENT_PER_LENGTH"
' Returned value : (Variant) (Long) 1
'--------------------------------------------------

Dim bSTR4813
bSTR4813 = ""
Dim bSTR4814
bSTR4814 = ""
Dim boolean2407
settingRepository1.GetAttrInfo "MOMENT_PER_LENGTH", bSTR4813, bSTR4814, boolean2407
'--------------------------------------------------
' Parameter 1 : (String) "MOMENT_PER_LENGTH"
' Parameter 2 : (String) "Default value"
' Parameter 3 : (String) "Unlocked"
' Parameter 4 : (Boolean) False
'--------------------------------------------------

long2408 = settingRepository1.GetAttr("MOMENT_PER_LENGTH_Large")
'--------------------------------------------------
' Parameter 1 : (String) "MOMENT_PER_LENGTH_Large"
' Returned value : (Variant) (Long) 1
'--------------------------------------------------

Dim bSTR4815
bSTR4815 = ""
Dim bSTR4816
bSTR4816 = ""
Dim boolean2408
settingRepository1.GetAttrInfo "MOMENT_PER_LENGTH_Large", bSTR4815, bSTR4816, boolean2408
'--------------------------------------------------
' Parameter 1 : (String) "MOMENT_PER_LENGTH_Large"
' Parameter 2 : (String) "Default value"
' Parameter 3 : (String) "Unlocked"
' Parameter 4 : (Boolean) False
'--------------------------------------------------

long2409 = settingRepository1.GetAttr("MOMENT_PER_LENGTH_ExtraLarge")
'--------------------------------------------------
' Parameter 1 : (String) "MOMENT_PER_LENGTH_ExtraLarge"
' Returned value : (Variant) (Long) 1
'--------------------------------------------------

Dim bSTR4817
bSTR4817 = ""
Dim bSTR4818
bSTR4818 = ""
Dim boolean2409
settingRepository1.GetAttrInfo "MOMENT_PER_LENGTH_ExtraLarge", bSTR4817, bSTR4818, boolean2409
'--------------------------------------------------
' Parameter 1 : (String) "MOMENT_PER_LENGTH_ExtraLarge"
' Parameter 2 : (String) "Default value"
' Parameter 3 : (String) "Unlocked"
' Parameter 4 : (Boolean) False
'--------------------------------------------------

long2410 = settingRepository1.GetAttr("MOMENT_PER_LENGTH_Small")
'--------------------------------------------------
' Parameter 1 : (String) "MOMENT_PER_LENGTH_Small"
' Returned value : (Variant) (Long) 1
'--------------------------------------------------

Dim bSTR4819
bSTR4819 = ""
Dim bSTR4820
bSTR4820 = ""
Dim boolean2410
settingRepository1.GetAttrInfo "MOMENT_PER_LENGTH_Small", bSTR4819, bSTR4820, boolean2410
'--------------------------------------------------
' Parameter 1 : (String) "MOMENT_PER_LENGTH_Small"
' Parameter 2 : (String) "Default value"
' Parameter 3 : (String) "Unlocked"
' Parameter 4 : (Boolean) False
'--------------------------------------------------

long2411 = settingRepository1.GetAttr("MOMENT_PER_LENGTH_ExtraSmall")
'--------------------------------------------------
' Parameter 1 : (String) "MOMENT_PER_LENGTH_ExtraSmall"
' Returned value : (Variant) (Long) 1
'--------------------------------------------------

Dim bSTR4821
bSTR4821 = ""
Dim bSTR4822
bSTR4822 = ""
Dim boolean2411
settingRepository1.GetAttrInfo "MOMENT_PER_LENGTH_ExtraSmall", bSTR4821, bSTR4822, boolean2411
'--------------------------------------------------
' Parameter 1 : (String) "MOMENT_PER_LENGTH_ExtraSmall"
' Parameter 2 : (String) "Default value"
' Parameter 3 : (String) "Unlocked"
' Parameter 4 : (Boolean) False
'--------------------------------------------------

long2412 = settingRepository1.GetAttr("MOMENT_PER_LENGTH_Nanometric")
'--------------------------------------------------
' Parameter 1 : (String) "MOMENT_PER_LENGTH_Nanometric"
' Returned value : (Variant) (Long) 1
'--------------------------------------------------

Dim bSTR4823
bSTR4823 = ""
Dim bSTR4824
bSTR4824 = ""
Dim boolean2412
settingRepository1.GetAttrInfo "MOMENT_PER_LENGTH_Nanometric", bSTR4823, bSTR4824, boolean2412
'--------------------------------------------------
' Parameter 1 : (String) "MOMENT_PER_LENGTH_Nanometric"
' Parameter 2 : (String) "Default value"
' Parameter 3 : (String) "Unlocked"
' Parameter 4 : (Boolean) False
'--------------------------------------------------

long2413 = settingRepository1.GetAttr("QUIETNESS_INDEX")
'--------------------------------------------------
' Parameter 1 : (String) "QUIETNESS_INDEX"
' Returned value : (Variant) (Long) 1
'--------------------------------------------------

Dim bSTR4825
bSTR4825 = ""
Dim bSTR4826
bSTR4826 = ""
Dim boolean2413
settingRepository1.GetAttrInfo "QUIETNESS_INDEX", bSTR4825, bSTR4826, boolean2413
'--------------------------------------------------
' Parameter 1 : (String) "QUIETNESS_INDEX"
' Parameter 2 : (String) "Default value"
' Parameter 3 : (String) "Unlocked"
' Parameter 4 : (Boolean) False
'--------------------------------------------------

long2414 = settingRepository1.GetAttr("QUIETNESS_INDEX_Large")
'--------------------------------------------------
' Parameter 1 : (String) "QUIETNESS_INDEX_Large"
' Returned value : (Variant) (Long) 1
'--------------------------------------------------

Dim bSTR4827
bSTR4827 = ""
Dim bSTR4828
bSTR4828 = ""
Dim boolean2414
settingRepository1.GetAttrInfo "QUIETNESS_INDEX_Large", bSTR4827, bSTR4828, boolean2414
'--------------------------------------------------
' Parameter 1 : (String) "QUIETNESS_INDEX_Large"
' Parameter 2 : (String) "Default value"
' Parameter 3 : (String) "Unlocked"
' Parameter 4 : (Boolean) False
'--------------------------------------------------

long2415 = settingRepository1.GetAttr("QUIETNESS_INDEX_ExtraLarge")
'--------------------------------------------------
' Parameter 1 : (String) "QUIETNESS_INDEX_ExtraLarge"
' Returned value : (Variant) (Long) 1
'--------------------------------------------------

Dim bSTR4829
bSTR4829 = ""
Dim bSTR4830
bSTR4830 = ""
Dim boolean2415
settingRepository1.GetAttrInfo "QUIETNESS_INDEX_ExtraLarge", bSTR4829, bSTR4830, boolean2415
'--------------------------------------------------
' Parameter 1 : (String) "QUIETNESS_INDEX_ExtraLarge"
' Parameter 2 : (String) "Default value"
' Parameter 3 : (String) "Unlocked"
' Parameter 4 : (Boolean) False
'--------------------------------------------------

long2416 = settingRepository1.GetAttr("QUIETNESS_INDEX_Small")
'--------------------------------------------------
' Parameter 1 : (String) "QUIETNESS_INDEX_Small"
' Returned value : (Variant) (Long) 1
'--------------------------------------------------

Dim bSTR4831
bSTR4831 = ""
Dim bSTR4832
bSTR4832 = ""
Dim boolean2416
settingRepository1.GetAttrInfo "QUIETNESS_INDEX_Small", bSTR4831, bSTR4832, boolean2416
'--------------------------------------------------
' Parameter 1 : (String) "QUIETNESS_INDEX_Small"
' Parameter 2 : (String) "Default value"
' Parameter 3 : (String) "Unlocked"
' Parameter 4 : (Boolean) False
'--------------------------------------------------

long2417 = settingRepository1.GetAttr("QUIETNESS_INDEX_ExtraSmall")
'--------------------------------------------------
' Parameter 1 : (String) "QUIETNESS_INDEX_ExtraSmall"
' Returned value : (Variant) (Long) 1
'--------------------------------------------------

Dim bSTR4833
bSTR4833 = ""
Dim bSTR4834
bSTR4834 = ""
Dim boolean2417
settingRepository1.GetAttrInfo "QUIETNESS_INDEX_ExtraSmall", bSTR4833, bSTR4834, boolean2417
'--------------------------------------------------
' Parameter 1 : (String) "QUIETNESS_INDEX_ExtraSmall"
' Parameter 2 : (String) "Default value"
' Parameter 3 : (String) "Unlocked"
' Parameter 4 : (Boolean) False
'--------------------------------------------------

long2418 = settingRepository1.GetAttr("QUIETNESS_INDEX_Nanometric")
'--------------------------------------------------
' Parameter 1 : (String) "QUIETNESS_INDEX_Nanometric"
' Returned value : (Variant) (Long) 1
'--------------------------------------------------

Dim bSTR4835
bSTR4835 = ""
Dim bSTR4836
bSTR4836 = ""
Dim boolean2418
settingRepository1.GetAttrInfo "QUIETNESS_INDEX_Nanometric", bSTR4835, bSTR4836, boolean2418
'--------------------------------------------------
' Parameter 1 : (String) "QUIETNESS_INDEX_Nanometric"
' Parameter 2 : (String) "Default value"
' Parameter 3 : (String) "Unlocked"
' Parameter 4 : (Boolean) False
'--------------------------------------------------

long2419 = settingRepository1.GetAttr("SURFACIC_DAMPING_CONSTANT")
'--------------------------------------------------
' Parameter 1 : (String) "SURFACIC_DAMPING_CONSTANT"
' Returned value : (Variant) (Long) 1
'--------------------------------------------------

Dim bSTR4837
bSTR4837 = ""
Dim bSTR4838
bSTR4838 = ""
Dim boolean2419
settingRepository1.GetAttrInfo "SURFACIC_DAMPING_CONSTANT", bSTR4837, bSTR4838, boolean2419
'--------------------------------------------------
' Parameter 1 : (String) "SURFACIC_DAMPING_CONSTANT"
' Parameter 2 : (String) "Default value"
' Parameter 3 : (String) "Unlocked"
' Parameter 4 : (Boolean) False
'--------------------------------------------------

long2420 = settingRepository1.GetAttr("SURFACIC_DAMPING_CONSTANT_Large")
'--------------------------------------------------
' Parameter 1 : (String) "SURFACIC_DAMPING_CONSTANT_Large"
' Returned value : (Variant) (Long) 1
'--------------------------------------------------

Dim bSTR4839
bSTR4839 = ""
Dim bSTR4840
bSTR4840 = ""
Dim boolean2420
settingRepository1.GetAttrInfo "SURFACIC_DAMPING_CONSTANT_Large", bSTR4839, bSTR4840, boolean2420
'--------------------------------------------------
' Parameter 1 : (String) "SURFACIC_DAMPING_CONSTANT_Large"
' Parameter 2 : (String) "Default value"
' Parameter 3 : (String) "Unlocked"
' Parameter 4 : (Boolean) False
'--------------------------------------------------

long2421 = settingRepository1.GetAttr("SURFACIC_DAMPING_CONSTANT_ExtraLarge")
'--------------------------------------------------
' Parameter 1 : (String) "SURFACIC_DAMPING_CONSTANT_ExtraLarge"
' Returned value : (Variant) (Long) 1
'--------------------------------------------------

Dim bSTR4841
bSTR4841 = ""
Dim bSTR4842
bSTR4842 = ""
Dim boolean2421
settingRepository1.GetAttrInfo "SURFACIC_DAMPING_CONSTANT_ExtraLarge", bSTR4841, bSTR4842, boolean2421
'--------------------------------------------------
' Parameter 1 : (String) "SURFACIC_DAMPING_CONSTANT_ExtraLarge"
' Parameter 2 : (String) "Default value"
' Parameter 3 : (String) "Unlocked"
' Parameter 4 : (Boolean) False
'--------------------------------------------------

long2422 = settingRepository1.GetAttr("SURFACIC_DAMPING_CONSTANT_Small")
'--------------------------------------------------
' Parameter 1 : (String) "SURFACIC_DAMPING_CONSTANT_Small"
' Returned value : (Variant) (Long) 1
'--------------------------------------------------

Dim bSTR4843
bSTR4843 = ""
Dim bSTR4844
bSTR4844 = ""
Dim boolean2422
settingRepository1.GetAttrInfo "SURFACIC_DAMPING_CONSTANT_Small", bSTR4843, bSTR4844, boolean2422
'--------------------------------------------------
' Parameter 1 : (String) "SURFACIC_DAMPING_CONSTANT_Small"
' Parameter 2 : (String) "Default value"
' Parameter 3 : (String) "Unlocked"
' Parameter 4 : (Boolean) False
'--------------------------------------------------

long2423 = settingRepository1.GetAttr("SURFACIC_DAMPING_CONSTANT_ExtraSmall")
'--------------------------------------------------
' Parameter 1 : (String) "SURFACIC_DAMPING_CONSTANT_ExtraSmall"
' Returned value : (Variant) (Long) 1
'--------------------------------------------------

Dim bSTR4845
bSTR4845 = ""
Dim bSTR4846
bSTR4846 = ""
Dim boolean2423
settingRepository1.GetAttrInfo "SURFACIC_DAMPING_CONSTANT_ExtraSmall", bSTR4845, bSTR4846, boolean2423
'--------------------------------------------------
' Parameter 1 : (String) "SURFACIC_DAMPING_CONSTANT_ExtraSmall"
' Parameter 2 : (String) "Default value"
' Parameter 3 : (String) "Unlocked"
' Parameter 4 : (Boolean) False
'--------------------------------------------------

long2424 = settingRepository1.GetAttr("SURFACIC_DAMPING_CONSTANT_Nanometric")
'--------------------------------------------------
' Parameter 1 : (String) "SURFACIC_DAMPING_CONSTANT_Nanometric"
' Returned value : (Variant) (Long) 1
'--------------------------------------------------

Dim bSTR4847
bSTR4847 = ""
Dim bSTR4848
bSTR4848 = ""
Dim boolean2424
settingRepository1.GetAttrInfo "SURFACIC_DAMPING_CONSTANT_Nanometric", bSTR4847, bSTR4848, boolean2424
'--------------------------------------------------
' Parameter 1 : (String) "SURFACIC_DAMPING_CONSTANT_Nanometric"
' Parameter 2 : (String) "Default value"
' Parameter 3 : (String) "Unlocked"
' Parameter 4 : (Boolean) False
'--------------------------------------------------

long2425 = settingRepository1.GetAttr("MASS_FRACTION")
'--------------------------------------------------
' Parameter 1 : (String) "MASS_FRACTION"
' Returned value : (Variant) (Long) 1
'--------------------------------------------------

Dim bSTR4849
bSTR4849 = ""
Dim bSTR4850
bSTR4850 = ""
Dim boolean2425
settingRepository1.GetAttrInfo "MASS_FRACTION", bSTR4849, bSTR4850, boolean2425
'--------------------------------------------------
' Parameter 1 : (String) "MASS_FRACTION"
' Parameter 2 : (String) "Default value"
' Parameter 3 : (String) "Unlocked"
' Parameter 4 : (Boolean) False
'--------------------------------------------------

long2426 = settingRepository1.GetAttr("MASS_FRACTION_Large")
'--------------------------------------------------
' Parameter 1 : (String) "MASS_FRACTION_Large"
' Returned value : (Variant) (Long) 1
'--------------------------------------------------

Dim bSTR4851
bSTR4851 = ""
Dim bSTR4852
bSTR4852 = ""
Dim boolean2426
settingRepository1.GetAttrInfo "MASS_FRACTION_Large", bSTR4851, bSTR4852, boolean2426
'--------------------------------------------------
' Parameter 1 : (String) "MASS_FRACTION_Large"
' Parameter 2 : (String) "Default value"
' Parameter 3 : (String) "Unlocked"
' Parameter 4 : (Boolean) False
'--------------------------------------------------

long2427 = settingRepository1.GetAttr("MASS_FRACTION_ExtraLarge")
'--------------------------------------------------
' Parameter 1 : (String) "MASS_FRACTION_ExtraLarge"
' Returned value : (Variant) (Long) 1
'--------------------------------------------------

Dim bSTR4853
bSTR4853 = ""
Dim bSTR4854
bSTR4854 = ""
Dim boolean2427
settingRepository1.GetAttrInfo "MASS_FRACTION_ExtraLarge", bSTR4853, bSTR4854, boolean2427
'--------------------------------------------------
' Parameter 1 : (String) "MASS_FRACTION_ExtraLarge"
' Parameter 2 : (String) "Default value"
' Parameter 3 : (String) "Unlocked"
' Parameter 4 : (Boolean) False
'--------------------------------------------------

long2428 = settingRepository1.GetAttr("MASS_FRACTION_Small")
'--------------------------------------------------
' Parameter 1 : (String) "MASS_FRACTION_Small"
' Returned value : (Variant) (Long) 1
'--------------------------------------------------

Dim bSTR4855
bSTR4855 = ""
Dim bSTR4856
bSTR4856 = ""
Dim boolean2428
settingRepository1.GetAttrInfo "MASS_FRACTION_Small", bSTR4855, bSTR4856, boolean2428
'--------------------------------------------------
' Parameter 1 : (String) "MASS_FRACTION_Small"
' Parameter 2 : (String) "Default value"
' Parameter 3 : (String) "Unlocked"
' Parameter 4 : (Boolean) False
'--------------------------------------------------

long2429 = settingRepository1.GetAttr("MASS_FRACTION_ExtraSmall")
'--------------------------------------------------
' Parameter 1 : (String) "MASS_FRACTION_ExtraSmall"
' Returned value : (Variant) (Long) 1
'--------------------------------------------------

Dim bSTR4857
bSTR4857 = ""
Dim bSTR4858
bSTR4858 = ""
Dim boolean2429
settingRepository1.GetAttrInfo "MASS_FRACTION_ExtraSmall", bSTR4857, bSTR4858, boolean2429
'--------------------------------------------------
' Parameter 1 : (String) "MASS_FRACTION_ExtraSmall"
' Parameter 2 : (String) "Default value"
' Parameter 3 : (String) "Unlocked"
' Parameter 4 : (Boolean) False
'--------------------------------------------------

long2430 = settingRepository1.GetAttr("MASS_FRACTION_Nanometric")
'--------------------------------------------------
' Parameter 1 : (String) "MASS_FRACTION_Nanometric"
' Returned value : (Variant) (Long) 1
'--------------------------------------------------

Dim bSTR4859
bSTR4859 = ""
Dim bSTR4860
bSTR4860 = ""
Dim boolean2430
settingRepository1.GetAttrInfo "MASS_FRACTION_Nanometric", bSTR4859, bSTR4860, boolean2430
'--------------------------------------------------
' Parameter 1 : (String) "MASS_FRACTION_Nanometric"
' Parameter 2 : (String) "Default value"
' Parameter 3 : (String) "Unlocked"
' Parameter 4 : (Boolean) False
'--------------------------------------------------

long2431 = settingRepository1.GetAttr("SPECIFIC_SURFACE_AREA")
'--------------------------------------------------
' Parameter 1 : (String) "SPECIFIC_SURFACE_AREA"
' Returned value : (Variant) (Long) 1
'--------------------------------------------------

Dim bSTR4861
bSTR4861 = ""
Dim bSTR4862
bSTR4862 = ""
Dim boolean2431
settingRepository1.GetAttrInfo "SPECIFIC_SURFACE_AREA", bSTR4861, bSTR4862, boolean2431
'--------------------------------------------------
' Parameter 1 : (String) "SPECIFIC_SURFACE_AREA"
' Parameter 2 : (String) "Default value"
' Parameter 3 : (String) "Unlocked"
' Parameter 4 : (Boolean) False
'--------------------------------------------------

long2432 = settingRepository1.GetAttr("SPECIFIC_SURFACE_AREA_Large")
'--------------------------------------------------
' Parameter 1 : (String) "SPECIFIC_SURFACE_AREA_Large"
' Returned value : (Variant) (Long) 1
'--------------------------------------------------

Dim bSTR4863
bSTR4863 = ""
Dim bSTR4864
bSTR4864 = ""
Dim boolean2432
settingRepository1.GetAttrInfo "SPECIFIC_SURFACE_AREA_Large", bSTR4863, bSTR4864, boolean2432
'--------------------------------------------------
' Parameter 1 : (String) "SPECIFIC_SURFACE_AREA_Large"
' Parameter 2 : (String) "Default value"
' Parameter 3 : (String) "Unlocked"
' Parameter 4 : (Boolean) False
'--------------------------------------------------

long2433 = settingRepository1.GetAttr("SPECIFIC_SURFACE_AREA_ExtraLarge")
'--------------------------------------------------
' Parameter 1 : (String) "SPECIFIC_SURFACE_AREA_ExtraLarge"
' Returned value : (Variant) (Long) 1
'--------------------------------------------------

Dim bSTR4865
bSTR4865 = ""
Dim bSTR4866
bSTR4866 = ""
Dim boolean2433
settingRepository1.GetAttrInfo "SPECIFIC_SURFACE_AREA_ExtraLarge", bSTR4865, bSTR4866, boolean2433
'--------------------------------------------------
' Parameter 1 : (String) "SPECIFIC_SURFACE_AREA_ExtraLarge"
' Parameter 2 : (String) "Default value"
' Parameter 3 : (String) "Unlocked"
' Parameter 4 : (Boolean) False
'--------------------------------------------------

long2434 = settingRepository1.GetAttr("SPECIFIC_SURFACE_AREA_Small")
'--------------------------------------------------
' Parameter 1 : (String) "SPECIFIC_SURFACE_AREA_Small"
' Returned value : (Variant) (Long) 1
'--------------------------------------------------

Dim bSTR4867
bSTR4867 = ""
Dim bSTR4868
bSTR4868 = ""
Dim boolean2434
settingRepository1.GetAttrInfo "SPECIFIC_SURFACE_AREA_Small", bSTR4867, bSTR4868, boolean2434
'--------------------------------------------------
' Parameter 1 : (String) "SPECIFIC_SURFACE_AREA_Small"
' Parameter 2 : (String) "Default value"
' Parameter 3 : (String) "Unlocked"
' Parameter 4 : (Boolean) False
'--------------------------------------------------

long2435 = settingRepository1.GetAttr("SPECIFIC_SURFACE_AREA_ExtraSmall")
'--------------------------------------------------
' Parameter 1 : (String) "SPECIFIC_SURFACE_AREA_ExtraSmall"
' Returned value : (Variant) (Long) 1
'--------------------------------------------------

Dim bSTR4869
bSTR4869 = ""
Dim bSTR4870
bSTR4870 = ""
Dim boolean2435
settingRepository1.GetAttrInfo "SPECIFIC_SURFACE_AREA_ExtraSmall", bSTR4869, bSTR4870, boolean2435
'--------------------------------------------------
' Parameter 1 : (String) "SPECIFIC_SURFACE_AREA_ExtraSmall"
' Parameter 2 : (String) "Default value"
' Parameter 3 : (String) "Unlocked"
' Parameter 4 : (Boolean) False
'--------------------------------------------------

long2436 = settingRepository1.GetAttr("SPECIFIC_SURFACE_AREA_Nanometric")
'--------------------------------------------------
' Parameter 1 : (String) "SPECIFIC_SURFACE_AREA_Nanometric"
' Returned value : (Variant) (Long) 1
'--------------------------------------------------

Dim bSTR4871
bSTR4871 = ""
Dim bSTR4872
bSTR4872 = ""
Dim boolean2436
settingRepository1.GetAttrInfo "SPECIFIC_SURFACE_AREA_Nanometric", bSTR4871, bSTR4872, boolean2436
'--------------------------------------------------
' Parameter 1 : (String) "SPECIFIC_SURFACE_AREA_Nanometric"
' Parameter 2 : (String) "Default value"
' Parameter 3 : (String) "Unlocked"
' Parameter 4 : (Boolean) False
'--------------------------------------------------

long2437 = settingRepository1.GetAttr("LINEAR_MASS_DENSITY_OF_FIBERS")
'--------------------------------------------------
' Parameter 1 : (String) "LINEAR_MASS_DENSITY_OF_FIBERS"
' Returned value : (Variant) (Long) 1
'--------------------------------------------------

Dim bSTR4873
bSTR4873 = ""
Dim bSTR4874
bSTR4874 = ""
Dim boolean2437
settingRepository1.GetAttrInfo "LINEAR_MASS_DENSITY_OF_FIBERS", bSTR4873, bSTR4874, boolean2437
'--------------------------------------------------
' Parameter 1 : (String) "LINEAR_MASS_DENSITY_OF_FIBERS"
' Parameter 2 : (String) "Default value"
' Parameter 3 : (String) "Unlocked"
' Parameter 4 : (Boolean) False
'--------------------------------------------------

long2438 = settingRepository1.GetAttr("LINEAR_MASS_DENSITY_OF_FIBERS_Large")
'--------------------------------------------------
' Parameter 1 : (String) "LINEAR_MASS_DENSITY_OF_FIBERS_Large"
' Returned value : (Variant) (Long) 1
'--------------------------------------------------

Dim bSTR4875
bSTR4875 = ""
Dim bSTR4876
bSTR4876 = ""
Dim boolean2438
settingRepository1.GetAttrInfo "LINEAR_MASS_DENSITY_OF_FIBERS_Large", bSTR4875, bSTR4876, boolean2438
'--------------------------------------------------
' Parameter 1 : (String) "LINEAR_MASS_DENSITY_OF_FIBERS_Large"
' Parameter 2 : (String) "Default value"
' Parameter 3 : (String) "Unlocked"
' Parameter 4 : (Boolean) False
'--------------------------------------------------

long2439 = settingRepository1.GetAttr("LINEAR_MASS_DENSITY_OF_FIBERS_ExtraLarge")
'--------------------------------------------------
' Parameter 1 : (String) "LINEAR_MASS_DENSITY_OF_FIBERS_ExtraLarge"
' Returned value : (Variant) (Long) 1
'--------------------------------------------------

Dim bSTR4877
bSTR4877 = ""
Dim bSTR4878
bSTR4878 = ""
Dim boolean2439
settingRepository1.GetAttrInfo "LINEAR_MASS_DENSITY_OF_FIBERS_ExtraLarge", bSTR4877, bSTR4878, boolean2439
'--------------------------------------------------
' Parameter 1 : (String) "LINEAR_MASS_DENSITY_OF_FIBERS_ExtraLarge"
' Parameter 2 : (String) "Default value"
' Parameter 3 : (String) "Unlocked"
' Parameter 4 : (Boolean) False
'--------------------------------------------------

long2440 = settingRepository1.GetAttr("LINEAR_MASS_DENSITY_OF_FIBERS_Small")
'--------------------------------------------------
' Parameter 1 : (String) "LINEAR_MASS_DENSITY_OF_FIBERS_Small"
' Returned value : (Variant) (Long) 1
'--------------------------------------------------

Dim bSTR4879
bSTR4879 = ""
Dim bSTR4880
bSTR4880 = ""
Dim boolean2440
settingRepository1.GetAttrInfo "LINEAR_MASS_DENSITY_OF_FIBERS_Small", bSTR4879, bSTR4880, boolean2440
'--------------------------------------------------
' Parameter 1 : (String) "LINEAR_MASS_DENSITY_OF_FIBERS_Small"
' Parameter 2 : (String) "Default value"
' Parameter 3 : (String) "Unlocked"
' Parameter 4 : (Boolean) False
'--------------------------------------------------

long2441 = settingRepository1.GetAttr("LINEAR_MASS_DENSITY_OF_FIBERS_ExtraSmall")
'--------------------------------------------------
' Parameter 1 : (String) "LINEAR_MASS_DENSITY_OF_FIBERS_ExtraSmall"
' Returned value : (Variant) (Long) 1
'--------------------------------------------------

Dim bSTR4881
bSTR4881 = ""
Dim bSTR4882
bSTR4882 = ""
Dim boolean2441
settingRepository1.GetAttrInfo "LINEAR_MASS_DENSITY_OF_FIBERS_ExtraSmall", bSTR4881, bSTR4882, boolean2441
'--------------------------------------------------
' Parameter 1 : (String) "LINEAR_MASS_DENSITY_OF_FIBERS_ExtraSmall"
' Parameter 2 : (String) "Default value"
' Parameter 3 : (String) "Unlocked"
' Parameter 4 : (Boolean) False
'--------------------------------------------------

long2442 = settingRepository1.GetAttr("LINEAR_MASS_DENSITY_OF_FIBERS_Nanometric")
'--------------------------------------------------
' Parameter 1 : (String) "LINEAR_MASS_DENSITY_OF_FIBERS_Nanometric"
' Returned value : (Variant) (Long) 1
'--------------------------------------------------

Dim bSTR4883
bSTR4883 = ""
Dim bSTR4884
bSTR4884 = ""
Dim boolean2442
settingRepository1.GetAttrInfo "LINEAR_MASS_DENSITY_OF_FIBERS_Nanometric", bSTR4883, bSTR4884, boolean2442
'--------------------------------------------------
' Parameter 1 : (String) "LINEAR_MASS_DENSITY_OF_FIBERS_Nanometric"
' Parameter 2 : (String) "Default value"
' Parameter 3 : (String) "Unlocked"
' Parameter 4 : (Boolean) False
'--------------------------------------------------

long2443 = settingRepository1.GetAttr("HARDNESS")
'--------------------------------------------------
' Parameter 1 : (String) "HARDNESS"
' Returned value : (Variant) (Long) 1
'--------------------------------------------------

Dim bSTR4885
bSTR4885 = ""
Dim bSTR4886
bSTR4886 = ""
Dim boolean2443
settingRepository1.GetAttrInfo "HARDNESS", bSTR4885, bSTR4886, boolean2443
'--------------------------------------------------
' Parameter 1 : (String) "HARDNESS"
' Parameter 2 : (String) "Default value"
' Parameter 3 : (String) "Unlocked"
' Parameter 4 : (Boolean) False
'--------------------------------------------------

long2444 = settingRepository1.GetAttr("HARDNESS_Large")
'--------------------------------------------------
' Parameter 1 : (String) "HARDNESS_Large"
' Returned value : (Variant) (Long) 1
'--------------------------------------------------

Dim bSTR4887
bSTR4887 = ""
Dim bSTR4888
bSTR4888 = ""
Dim boolean2444
settingRepository1.GetAttrInfo "HARDNESS_Large", bSTR4887, bSTR4888, boolean2444
'--------------------------------------------------
' Parameter 1 : (String) "HARDNESS_Large"
' Parameter 2 : (String) "Default value"
' Parameter 3 : (String) "Unlocked"
' Parameter 4 : (Boolean) False
'--------------------------------------------------

long2445 = settingRepository1.GetAttr("HARDNESS_ExtraLarge")
'--------------------------------------------------
' Parameter 1 : (String) "HARDNESS_ExtraLarge"
' Returned value : (Variant) (Long) 1
'--------------------------------------------------

Dim bSTR4889
bSTR4889 = ""
Dim bSTR4890
bSTR4890 = ""
Dim boolean2445
settingRepository1.GetAttrInfo "HARDNESS_ExtraLarge", bSTR4889, bSTR4890, boolean2445
'--------------------------------------------------
' Parameter 1 : (String) "HARDNESS_ExtraLarge"
' Parameter 2 : (String) "Default value"
' Parameter 3 : (String) "Unlocked"
' Parameter 4 : (Boolean) False
'--------------------------------------------------

long2446 = settingRepository1.GetAttr("HARDNESS_Small")
'--------------------------------------------------
' Parameter 1 : (String) "HARDNESS_Small"
' Returned value : (Variant) (Long) 1
'--------------------------------------------------

Dim bSTR4891
bSTR4891 = ""
Dim bSTR4892
bSTR4892 = ""
Dim boolean2446
settingRepository1.GetAttrInfo "HARDNESS_Small", bSTR4891, bSTR4892, boolean2446
'--------------------------------------------------
' Parameter 1 : (String) "HARDNESS_Small"
' Parameter 2 : (String) "Default value"
' Parameter 3 : (String) "Unlocked"
' Parameter 4 : (Boolean) False
'--------------------------------------------------

long2447 = settingRepository1.GetAttr("HARDNESS_ExtraSmall")
'--------------------------------------------------
' Parameter 1 : (String) "HARDNESS_ExtraSmall"
' Returned value : (Variant) (Long) 1
'--------------------------------------------------

Dim bSTR4893
bSTR4893 = ""
Dim bSTR4894
bSTR4894 = ""
Dim boolean2447
settingRepository1.GetAttrInfo "HARDNESS_ExtraSmall", bSTR4893, bSTR4894, boolean2447
'--------------------------------------------------
' Parameter 1 : (String) "HARDNESS_ExtraSmall"
' Parameter 2 : (String) "Default value"
' Parameter 3 : (String) "Unlocked"
' Parameter 4 : (Boolean) False
'--------------------------------------------------

long2448 = settingRepository1.GetAttr("HARDNESS_Nanometric")
'--------------------------------------------------
' Parameter 1 : (String) "HARDNESS_Nanometric"
' Returned value : (Variant) (Long) 1
'--------------------------------------------------

Dim bSTR4895
bSTR4895 = ""
Dim bSTR4896
bSTR4896 = ""
Dim boolean2448
settingRepository1.GetAttrInfo "HARDNESS_Nanometric", bSTR4895, bSTR4896, boolean2448
'--------------------------------------------------
' Parameter 1 : (String) "HARDNESS_Nanometric"
' Parameter 2 : (String) "Default value"
' Parameter 3 : (String) "Unlocked"
' Parameter 4 : (Boolean) False
'--------------------------------------------------

long2449 = settingRepository1.GetAttr("TRANSMISSION")
'--------------------------------------------------
' Parameter 1 : (String) "TRANSMISSION"
' Returned value : (Variant) (Long) 1
'--------------------------------------------------

Dim bSTR4897
bSTR4897 = ""
Dim bSTR4898
bSTR4898 = ""
Dim boolean2449
settingRepository1.GetAttrInfo "TRANSMISSION", bSTR4897, bSTR4898, boolean2449
'--------------------------------------------------
' Parameter 1 : (String) "TRANSMISSION"
' Parameter 2 : (String) "Default value"
' Parameter 3 : (String) "Unlocked"
' Parameter 4 : (Boolean) False
'--------------------------------------------------

long2450 = settingRepository1.GetAttr("TRANSMISSION_Large")
'--------------------------------------------------
' Parameter 1 : (String) "TRANSMISSION_Large"
' Returned value : (Variant) (Long) 1
'--------------------------------------------------

Dim bSTR4899
bSTR4899 = ""
Dim bSTR4900
bSTR4900 = ""
Dim boolean2450
settingRepository1.GetAttrInfo "TRANSMISSION_Large", bSTR4899, bSTR4900, boolean2450
'--------------------------------------------------
' Parameter 1 : (String) "TRANSMISSION_Large"
' Parameter 2 : (String) "Default value"
' Parameter 3 : (String) "Unlocked"
' Parameter 4 : (Boolean) False
'--------------------------------------------------

long2451 = settingRepository1.GetAttr("TRANSMISSION_ExtraLarge")
'--------------------------------------------------
' Parameter 1 : (String) "TRANSMISSION_ExtraLarge"
' Returned value : (Variant) (Long) 1
'--------------------------------------------------

Dim bSTR4901
bSTR4901 = ""
Dim bSTR4902
bSTR4902 = ""
Dim boolean2451
settingRepository1.GetAttrInfo "TRANSMISSION_ExtraLarge", bSTR4901, bSTR4902, boolean2451
'--------------------------------------------------
' Parameter 1 : (String) "TRANSMISSION_ExtraLarge"
' Parameter 2 : (String) "Default value"
' Parameter 3 : (String) "Unlocked"
' Parameter 4 : (Boolean) False
'--------------------------------------------------

long2452 = settingRepository1.GetAttr("TRANSMISSION_Small")
'--------------------------------------------------
' Parameter 1 : (String) "TRANSMISSION_Small"
' Returned value : (Variant) (Long) 1
'--------------------------------------------------

Dim bSTR4903
bSTR4903 = ""
Dim bSTR4904
bSTR4904 = ""
Dim boolean2452
settingRepository1.GetAttrInfo "TRANSMISSION_Small", bSTR4903, bSTR4904, boolean2452
'--------------------------------------------------
' Parameter 1 : (String) "TRANSMISSION_Small"
' Parameter 2 : (String) "Default value"
' Parameter 3 : (String) "Unlocked"
' Parameter 4 : (Boolean) False
'--------------------------------------------------

long2453 = settingRepository1.GetAttr("TRANSMISSION_ExtraSmall")
'--------------------------------------------------
' Parameter 1 : (String) "TRANSMISSION_ExtraSmall"
' Returned value : (Variant) (Long) 1
'--------------------------------------------------

Dim bSTR4905
bSTR4905 = ""
Dim bSTR4906
bSTR4906 = ""
Dim boolean2453
settingRepository1.GetAttrInfo "TRANSMISSION_ExtraSmall", bSTR4905, bSTR4906, boolean2453
'--------------------------------------------------
' Parameter 1 : (String) "TRANSMISSION_ExtraSmall"
' Parameter 2 : (String) "Default value"
' Parameter 3 : (String) "Unlocked"
' Parameter 4 : (Boolean) False
'--------------------------------------------------

long2454 = settingRepository1.GetAttr("TRANSMISSION_Nanometric")
'--------------------------------------------------
' Parameter 1 : (String) "TRANSMISSION_Nanometric"
' Returned value : (Variant) (Long) 1
'--------------------------------------------------

Dim bSTR4907
bSTR4907 = ""
Dim bSTR4908
bSTR4908 = ""
Dim boolean2454
settingRepository1.GetAttrInfo "TRANSMISSION_Nanometric", bSTR4907, bSTR4908, boolean2454
'--------------------------------------------------
' Parameter 1 : (String) "TRANSMISSION_Nanometric"
' Parameter 2 : (String) "Default value"
' Parameter 3 : (String) "Unlocked"
' Parameter 4 : (Boolean) False
'--------------------------------------------------

long2455 = settingRepository1.GetAttr("WAVE_FRONT_ERROR")
'--------------------------------------------------
' Parameter 1 : (String) "WAVE_FRONT_ERROR"
' Returned value : (Variant) (Long) 1
'--------------------------------------------------

Dim bSTR4909
bSTR4909 = ""
Dim bSTR4910
bSTR4910 = ""
Dim boolean2455
settingRepository1.GetAttrInfo "WAVE_FRONT_ERROR", bSTR4909, bSTR4910, boolean2455
'--------------------------------------------------
' Parameter 1 : (String) "WAVE_FRONT_ERROR"
' Parameter 2 : (String) "Default value"
' Parameter 3 : (String) "Unlocked"
' Parameter 4 : (Boolean) False
'--------------------------------------------------

long2456 = settingRepository1.GetAttr("WAVE_FRONT_ERROR_Large")
'--------------------------------------------------
' Parameter 1 : (String) "WAVE_FRONT_ERROR_Large"
' Returned value : (Variant) (Long) 1
'--------------------------------------------------

Dim bSTR4911
bSTR4911 = ""
Dim bSTR4912
bSTR4912 = ""
Dim boolean2456
settingRepository1.GetAttrInfo "WAVE_FRONT_ERROR_Large", bSTR4911, bSTR4912, boolean2456
'--------------------------------------------------
' Parameter 1 : (String) "WAVE_FRONT_ERROR_Large"
' Parameter 2 : (String) "Default value"
' Parameter 3 : (String) "Unlocked"
' Parameter 4 : (Boolean) False
'--------------------------------------------------

long2457 = settingRepository1.GetAttr("WAVE_FRONT_ERROR_ExtraLarge")
'--------------------------------------------------
' Parameter 1 : (String) "WAVE_FRONT_ERROR_ExtraLarge"
' Returned value : (Variant) (Long) 1
'--------------------------------------------------

Dim bSTR4913
bSTR4913 = ""
Dim bSTR4914
bSTR4914 = ""
Dim boolean2457
settingRepository1.GetAttrInfo "WAVE_FRONT_ERROR_ExtraLarge", bSTR4913, bSTR4914, boolean2457
'--------------------------------------------------
' Parameter 1 : (String) "WAVE_FRONT_ERROR_ExtraLarge"
' Parameter 2 : (String) "Default value"
' Parameter 3 : (String) "Unlocked"
' Parameter 4 : (Boolean) False
'--------------------------------------------------

long2458 = settingRepository1.GetAttr("WAVE_FRONT_ERROR_Small")
'--------------------------------------------------
' Parameter 1 : (String) "WAVE_FRONT_ERROR_Small"
' Returned value : (Variant) (Long) 1
'--------------------------------------------------

Dim bSTR4915
bSTR4915 = ""
Dim bSTR4916
bSTR4916 = ""
Dim boolean2458
settingRepository1.GetAttrInfo "WAVE_FRONT_ERROR_Small", bSTR4915, bSTR4916, boolean2458
'--------------------------------------------------
' Parameter 1 : (String) "WAVE_FRONT_ERROR_Small"
' Parameter 2 : (String) "Default value"
' Parameter 3 : (String) "Unlocked"
' Parameter 4 : (Boolean) False
'--------------------------------------------------

long2459 = settingRepository1.GetAttr("WAVE_FRONT_ERROR_ExtraSmall")
'--------------------------------------------------
' Parameter 1 : (String) "WAVE_FRONT_ERROR_ExtraSmall"
' Returned value : (Variant) (Long) 1
'--------------------------------------------------

Dim bSTR4917
bSTR4917 = ""
Dim bSTR4918
bSTR4918 = ""
Dim boolean2459
settingRepository1.GetAttrInfo "WAVE_FRONT_ERROR_ExtraSmall", bSTR4917, bSTR4918, boolean2459
'--------------------------------------------------
' Parameter 1 : (String) "WAVE_FRONT_ERROR_ExtraSmall"
' Parameter 2 : (String) "Default value"
' Parameter 3 : (String) "Unlocked"
' Parameter 4 : (Boolean) False
'--------------------------------------------------

long2460 = settingRepository1.GetAttr("WAVE_FRONT_ERROR_Nanometric")
'--------------------------------------------------
' Parameter 1 : (String) "WAVE_FRONT_ERROR_Nanometric"
' Returned value : (Variant) (Long) 1
'--------------------------------------------------

Dim bSTR4919
bSTR4919 = ""
Dim bSTR4920
bSTR4920 = ""
Dim boolean2460
settingRepository1.GetAttrInfo "WAVE_FRONT_ERROR_Nanometric", bSTR4919, bSTR4920, boolean2460
'--------------------------------------------------
' Parameter 1 : (String) "WAVE_FRONT_ERROR_Nanometric"
' Parameter 2 : (String) "Default value"
' Parameter 3 : (String) "Unlocked"
' Parameter 4 : (Boolean) False
'--------------------------------------------------

long2461 = settingRepository1.GetAttr("ROUGHNESS")
'--------------------------------------------------
' Parameter 1 : (String) "ROUGHNESS"
' Returned value : (Variant) (Long) 1
'--------------------------------------------------

Dim bSTR4921
bSTR4921 = ""
Dim bSTR4922
bSTR4922 = ""
Dim boolean2461
settingRepository1.GetAttrInfo "ROUGHNESS", bSTR4921, bSTR4922, boolean2461
'--------------------------------------------------
' Parameter 1 : (String) "ROUGHNESS"
' Parameter 2 : (String) "Default value"
' Parameter 3 : (String) "Unlocked"
' Parameter 4 : (Boolean) False
'--------------------------------------------------

long2462 = settingRepository1.GetAttr("ROUGHNESS_Large")
'--------------------------------------------------
' Parameter 1 : (String) "ROUGHNESS_Large"
' Returned value : (Variant) (Long) 1
'--------------------------------------------------

Dim bSTR4923
bSTR4923 = ""
Dim bSTR4924
bSTR4924 = ""
Dim boolean2462
settingRepository1.GetAttrInfo "ROUGHNESS_Large", bSTR4923, bSTR4924, boolean2462
'--------------------------------------------------
' Parameter 1 : (String) "ROUGHNESS_Large"
' Parameter 2 : (String) "Default value"
' Parameter 3 : (String) "Unlocked"
' Parameter 4 : (Boolean) False
'--------------------------------------------------

long2463 = settingRepository1.GetAttr("ROUGHNESS_ExtraLarge")
'--------------------------------------------------
' Parameter 1 : (String) "ROUGHNESS_ExtraLarge"
' Returned value : (Variant) (Long) 1
'--------------------------------------------------

Dim bSTR4925
bSTR4925 = ""
Dim bSTR4926
bSTR4926 = ""
Dim boolean2463
settingRepository1.GetAttrInfo "ROUGHNESS_ExtraLarge", bSTR4925, bSTR4926, boolean2463
'--------------------------------------------------
' Parameter 1 : (String) "ROUGHNESS_ExtraLarge"
' Parameter 2 : (String) "Default value"
' Parameter 3 : (String) "Unlocked"
' Parameter 4 : (Boolean) False
'--------------------------------------------------

long2464 = settingRepository1.GetAttr("ROUGHNESS_Small")
'--------------------------------------------------
' Parameter 1 : (String) "ROUGHNESS_Small"
' Returned value : (Variant) (Long) 1
'--------------------------------------------------

Dim bSTR4927
bSTR4927 = ""
Dim bSTR4928
bSTR4928 = ""
Dim boolean2464
settingRepository1.GetAttrInfo "ROUGHNESS_Small", bSTR4927, bSTR4928, boolean2464
'--------------------------------------------------
' Parameter 1 : (String) "ROUGHNESS_Small"
' Parameter 2 : (String) "Default value"
' Parameter 3 : (String) "Unlocked"
' Parameter 4 : (Boolean) False
'--------------------------------------------------

long2465 = settingRepository1.GetAttr("ROUGHNESS_ExtraSmall")
'--------------------------------------------------
' Parameter 1 : (String) "ROUGHNESS_ExtraSmall"
' Returned value : (Variant) (Long) 1
'--------------------------------------------------

Dim bSTR4929
bSTR4929 = ""
Dim bSTR4930
bSTR4930 = ""
Dim boolean2465
settingRepository1.GetAttrInfo "ROUGHNESS_ExtraSmall", bSTR4929, bSTR4930, boolean2465
'--------------------------------------------------
' Parameter 1 : (String) "ROUGHNESS_ExtraSmall"
' Parameter 2 : (String) "Default value"
' Parameter 3 : (String) "Unlocked"
' Parameter 4 : (Boolean) False
'--------------------------------------------------

long2466 = settingRepository1.GetAttr("ROUGHNESS_Nanometric")
'--------------------------------------------------
' Parameter 1 : (String) "ROUGHNESS_Nanometric"
' Returned value : (Variant) (Long) 1
'--------------------------------------------------

Dim bSTR4931
bSTR4931 = ""
Dim bSTR4932
bSTR4932 = ""
Dim boolean2466
settingRepository1.GetAttrInfo "ROUGHNESS_Nanometric", bSTR4931, bSTR4932, boolean2466
'--------------------------------------------------
' Parameter 1 : (String) "ROUGHNESS_Nanometric"
' Parameter 2 : (String) "Default value"
' Parameter 3 : (String) "Unlocked"
' Parameter 4 : (Boolean) False
'--------------------------------------------------

long2467 = settingRepository1.GetAttr("FLATNESS")
'--------------------------------------------------
' Parameter 1 : (String) "FLATNESS"
' Returned value : (Variant) (Long) 1
'--------------------------------------------------

Dim bSTR4933
bSTR4933 = ""
Dim bSTR4934
bSTR4934 = ""
Dim boolean2467
settingRepository1.GetAttrInfo "FLATNESS", bSTR4933, bSTR4934, boolean2467
'--------------------------------------------------
' Parameter 1 : (String) "FLATNESS"
' Parameter 2 : (String) "Default value"
' Parameter 3 : (String) "Unlocked"
' Parameter 4 : (Boolean) False
'--------------------------------------------------

long2468 = settingRepository1.GetAttr("FLATNESS_Large")
'--------------------------------------------------
' Parameter 1 : (String) "FLATNESS_Large"
' Returned value : (Variant) (Long) 1
'--------------------------------------------------

Dim bSTR4935
bSTR4935 = ""
Dim bSTR4936
bSTR4936 = ""
Dim boolean2468
settingRepository1.GetAttrInfo "FLATNESS_Large", bSTR4935, bSTR4936, boolean2468
'--------------------------------------------------
' Parameter 1 : (String) "FLATNESS_Large"
' Parameter 2 : (String) "Default value"
' Parameter 3 : (String) "Unlocked"
' Parameter 4 : (Boolean) False
'--------------------------------------------------

long2469 = settingRepository1.GetAttr("FLATNESS_ExtraLarge")
'--------------------------------------------------
' Parameter 1 : (String) "FLATNESS_ExtraLarge"
' Returned value : (Variant) (Long) 1
'--------------------------------------------------

Dim bSTR4937
bSTR4937 = ""
Dim bSTR4938
bSTR4938 = ""
Dim boolean2469
settingRepository1.GetAttrInfo "FLATNESS_ExtraLarge", bSTR4937, bSTR4938, boolean2469
'--------------------------------------------------
' Parameter 1 : (String) "FLATNESS_ExtraLarge"
' Parameter 2 : (String) "Default value"
' Parameter 3 : (String) "Unlocked"
' Parameter 4 : (Boolean) False
'--------------------------------------------------

long2470 = settingRepository1.GetAttr("FLATNESS_Small")
'--------------------------------------------------
' Parameter 1 : (String) "FLATNESS_Small"
' Returned value : (Variant) (Long) 1
'--------------------------------------------------

Dim bSTR4939
bSTR4939 = ""
Dim bSTR4940
bSTR4940 = ""
Dim boolean2470
settingRepository1.GetAttrInfo "FLATNESS_Small", bSTR4939, bSTR4940, boolean2470
'--------------------------------------------------
' Parameter 1 : (String) "FLATNESS_Small"
' Parameter 2 : (String) "Default value"
' Parameter 3 : (String) "Unlocked"
' Parameter 4 : (Boolean) False
'--------------------------------------------------

long2471 = settingRepository1.GetAttr("FLATNESS_ExtraSmall")
'--------------------------------------------------
' Parameter 1 : (String) "FLATNESS_ExtraSmall"
' Returned value : (Variant) (Long) 1
'--------------------------------------------------

Dim bSTR4941
bSTR4941 = ""
Dim bSTR4942
bSTR4942 = ""
Dim boolean2471
settingRepository1.GetAttrInfo "FLATNESS_ExtraSmall", bSTR4941, bSTR4942, boolean2471
'--------------------------------------------------
' Parameter 1 : (String) "FLATNESS_ExtraSmall"
' Parameter 2 : (String) "Default value"
' Parameter 3 : (String) "Unlocked"
' Parameter 4 : (Boolean) False
'--------------------------------------------------

long2472 = settingRepository1.GetAttr("FLATNESS_Nanometric")
'--------------------------------------------------
' Parameter 1 : (String) "FLATNESS_Nanometric"
' Returned value : (Variant) (Long) 1
'--------------------------------------------------

Dim bSTR4943
bSTR4943 = ""
Dim bSTR4944
bSTR4944 = ""
Dim boolean2472
settingRepository1.GetAttrInfo "FLATNESS_Nanometric", bSTR4943, bSTR4944, boolean2472
'--------------------------------------------------
' Parameter 1 : (String) "FLATNESS_Nanometric"
' Parameter 2 : (String) "Default value"
' Parameter 3 : (String) "Unlocked"
' Parameter 4 : (Boolean) False
'--------------------------------------------------

long2473 = settingRepository1.GetAttr("HYGROMETRY")
'--------------------------------------------------
' Parameter 1 : (String) "HYGROMETRY"
' Returned value : (Variant) (Long) 1
'--------------------------------------------------

Dim bSTR4945
bSTR4945 = ""
Dim bSTR4946
bSTR4946 = ""
Dim boolean2473
settingRepository1.GetAttrInfo "HYGROMETRY", bSTR4945, bSTR4946, boolean2473
'--------------------------------------------------
' Parameter 1 : (String) "HYGROMETRY"
' Parameter 2 : (String) "Default value"
' Parameter 3 : (String) "Unlocked"
' Parameter 4 : (Boolean) False
'--------------------------------------------------

long2474 = settingRepository1.GetAttr("HYGROMETRY_Large")
'--------------------------------------------------
' Parameter 1 : (String) "HYGROMETRY_Large"
' Returned value : (Variant) (Long) 1
'--------------------------------------------------

Dim bSTR4947
bSTR4947 = ""
Dim bSTR4948
bSTR4948 = ""
Dim boolean2474
settingRepository1.GetAttrInfo "HYGROMETRY_Large", bSTR4947, bSTR4948, boolean2474
'--------------------------------------------------
' Parameter 1 : (String) "HYGROMETRY_Large"
' Parameter 2 : (String) "Default value"
' Parameter 3 : (String) "Unlocked"
' Parameter 4 : (Boolean) False
'--------------------------------------------------

long2475 = settingRepository1.GetAttr("HYGROMETRY_ExtraLarge")
'--------------------------------------------------
' Parameter 1 : (String) "HYGROMETRY_ExtraLarge"
' Returned value : (Variant) (Long) 1
'--------------------------------------------------

Dim bSTR4949
bSTR4949 = ""
Dim bSTR4950
bSTR4950 = ""
Dim boolean2475
settingRepository1.GetAttrInfo "HYGROMETRY_ExtraLarge", bSTR4949, bSTR4950, boolean2475
'--------------------------------------------------
' Parameter 1 : (String) "HYGROMETRY_ExtraLarge"
' Parameter 2 : (String) "Default value"
' Parameter 3 : (String) "Unlocked"
' Parameter 4 : (Boolean) False
'--------------------------------------------------

long2476 = settingRepository1.GetAttr("HYGROMETRY_Small")
'--------------------------------------------------
' Parameter 1 : (String) "HYGROMETRY_Small"
' Returned value : (Variant) (Long) 1
'--------------------------------------------------

Dim bSTR4951
bSTR4951 = ""
Dim bSTR4952
bSTR4952 = ""
Dim boolean2476
settingRepository1.GetAttrInfo "HYGROMETRY_Small", bSTR4951, bSTR4952, boolean2476
'--------------------------------------------------
' Parameter 1 : (String) "HYGROMETRY_Small"
' Parameter 2 : (String) "Default value"
' Parameter 3 : (String) "Unlocked"
' Parameter 4 : (Boolean) False
'--------------------------------------------------

long2477 = settingRepository1.GetAttr("HYGROMETRY_ExtraSmall")
'--------------------------------------------------
' Parameter 1 : (String) "HYGROMETRY_ExtraSmall"
' Returned value : (Variant) (Long) 1
'--------------------------------------------------

Dim bSTR4953
bSTR4953 = ""
Dim bSTR4954
bSTR4954 = ""
Dim boolean2477
settingRepository1.GetAttrInfo "HYGROMETRY_ExtraSmall", bSTR4953, bSTR4954, boolean2477
'--------------------------------------------------
' Parameter 1 : (String) "HYGROMETRY_ExtraSmall"
' Parameter 2 : (String) "Default value"
' Parameter 3 : (String) "Unlocked"
' Parameter 4 : (Boolean) False
'--------------------------------------------------

long2478 = settingRepository1.GetAttr("HYGROMETRY_Nanometric")
'--------------------------------------------------
' Parameter 1 : (String) "HYGROMETRY_Nanometric"
' Returned value : (Variant) (Long) 1
'--------------------------------------------------

Dim bSTR4955
bSTR4955 = ""
Dim bSTR4956
bSTR4956 = ""
Dim boolean2478
settingRepository1.GetAttrInfo "HYGROMETRY_Nanometric", bSTR4955, bSTR4956, boolean2478
'--------------------------------------------------
' Parameter 1 : (String) "HYGROMETRY_Nanometric"
' Parameter 2 : (String) "Default value"
' Parameter 3 : (String) "Unlocked"
' Parameter 4 : (Boolean) False
'--------------------------------------------------

long2479 = settingRepository1.GetAttr("FREQUENCY_NOISE")
'--------------------------------------------------
' Parameter 1 : (String) "FREQUENCY_NOISE"
' Returned value : (Variant) (Long) 1
'--------------------------------------------------

Dim bSTR4957
bSTR4957 = ""
Dim bSTR4958
bSTR4958 = ""
Dim boolean2479
settingRepository1.GetAttrInfo "FREQUENCY_NOISE", bSTR4957, bSTR4958, boolean2479
'--------------------------------------------------
' Parameter 1 : (String) "FREQUENCY_NOISE"
' Parameter 2 : (String) "Default value"
' Parameter 3 : (String) "Unlocked"
' Parameter 4 : (Boolean) False
'--------------------------------------------------

long2480 = settingRepository1.GetAttr("FREQUENCY_NOISE_Large")
'--------------------------------------------------
' Parameter 1 : (String) "FREQUENCY_NOISE_Large"
' Returned value : (Variant) (Long) 1
'--------------------------------------------------

Dim bSTR4959
bSTR4959 = ""
Dim bSTR4960
bSTR4960 = ""
Dim boolean2480
settingRepository1.GetAttrInfo "FREQUENCY_NOISE_Large", bSTR4959, bSTR4960, boolean2480
'--------------------------------------------------
' Parameter 1 : (String) "FREQUENCY_NOISE_Large"
' Parameter 2 : (String) "Default value"
' Parameter 3 : (String) "Unlocked"
' Parameter 4 : (Boolean) False
'--------------------------------------------------

long2481 = settingRepository1.GetAttr("FREQUENCY_NOISE_ExtraLarge")
'--------------------------------------------------
' Parameter 1 : (String) "FREQUENCY_NOISE_ExtraLarge"
' Returned value : (Variant) (Long) 1
'--------------------------------------------------

Dim bSTR4961
bSTR4961 = ""
Dim bSTR4962
bSTR4962 = ""
Dim boolean2481
settingRepository1.GetAttrInfo "FREQUENCY_NOISE_ExtraLarge", bSTR4961, bSTR4962, boolean2481
'--------------------------------------------------
' Parameter 1 : (String) "FREQUENCY_NOISE_ExtraLarge"
' Parameter 2 : (String) "Default value"
' Parameter 3 : (String) "Unlocked"
' Parameter 4 : (Boolean) False
'--------------------------------------------------

long2482 = settingRepository1.GetAttr("FREQUENCY_NOISE_Small")
'--------------------------------------------------
' Parameter 1 : (String) "FREQUENCY_NOISE_Small"
' Returned value : (Variant) (Long) 1
'--------------------------------------------------

Dim bSTR4963
bSTR4963 = ""
Dim bSTR4964
bSTR4964 = ""
Dim boolean2482
settingRepository1.GetAttrInfo "FREQUENCY_NOISE_Small", bSTR4963, bSTR4964, boolean2482
'--------------------------------------------------
' Parameter 1 : (String) "FREQUENCY_NOISE_Small"
' Parameter 2 : (String) "Default value"
' Parameter 3 : (String) "Unlocked"
' Parameter 4 : (Boolean) False
'--------------------------------------------------

long2483 = settingRepository1.GetAttr("FREQUENCY_NOISE_ExtraSmall")
'--------------------------------------------------
' Parameter 1 : (String) "FREQUENCY_NOISE_ExtraSmall"
' Returned value : (Variant) (Long) 1
'--------------------------------------------------

Dim bSTR4965
bSTR4965 = ""
Dim bSTR4966
bSTR4966 = ""
Dim boolean2483
settingRepository1.GetAttrInfo "FREQUENCY_NOISE_ExtraSmall", bSTR4965, bSTR4966, boolean2483
'--------------------------------------------------
' Parameter 1 : (String) "FREQUENCY_NOISE_ExtraSmall"
' Parameter 2 : (String) "Default value"
' Parameter 3 : (String) "Unlocked"
' Parameter 4 : (Boolean) False
'--------------------------------------------------

long2484 = settingRepository1.GetAttr("FREQUENCY_NOISE_Nanometric")
'--------------------------------------------------
' Parameter 1 : (String) "FREQUENCY_NOISE_Nanometric"
' Returned value : (Variant) (Long) 1
'--------------------------------------------------

Dim bSTR4967
bSTR4967 = ""
Dim bSTR4968
bSTR4968 = ""
Dim boolean2484
settingRepository1.GetAttrInfo "FREQUENCY_NOISE_Nanometric", bSTR4967, bSTR4968, boolean2484
'--------------------------------------------------
' Parameter 1 : (String) "FREQUENCY_NOISE_Nanometric"
' Parameter 2 : (String) "Default value"
' Parameter 3 : (String) "Unlocked"
' Parameter 4 : (Boolean) False
'--------------------------------------------------

long2485 = settingRepository1.GetAttr("STRESS_OVER_SQUARE_TEMPERATURE")
'--------------------------------------------------
' Parameter 1 : (String) "STRESS_OVER_SQUARE_TEMPERATURE"
' Returned value : (Variant) (Long) 1
'--------------------------------------------------

Dim bSTR4969
bSTR4969 = ""
Dim bSTR4970
bSTR4970 = ""
Dim boolean2485
settingRepository1.GetAttrInfo "STRESS_OVER_SQUARE_TEMPERATURE", bSTR4969, bSTR4970, boolean2485
'--------------------------------------------------
' Parameter 1 : (String) "STRESS_OVER_SQUARE_TEMPERATURE"
' Parameter 2 : (String) "Default value"
' Parameter 3 : (String) "Unlocked"
' Parameter 4 : (Boolean) False
'--------------------------------------------------

long2486 = settingRepository1.GetAttr("STRESS_OVER_SQUARE_TEMPERATURE_Large")
'--------------------------------------------------
' Parameter 1 : (String) "STRESS_OVER_SQUARE_TEMPERATURE_Large"
' Returned value : (Variant) (Long) 1
'--------------------------------------------------

Dim bSTR4971
bSTR4971 = ""
Dim bSTR4972
bSTR4972 = ""
Dim boolean2486
settingRepository1.GetAttrInfo "STRESS_OVER_SQUARE_TEMPERATURE_Large", bSTR4971, bSTR4972, boolean2486
'--------------------------------------------------
' Parameter 1 : (String) "STRESS_OVER_SQUARE_TEMPERATURE_Large"
' Parameter 2 : (String) "Default value"
' Parameter 3 : (String) "Unlocked"
' Parameter 4 : (Boolean) False
'--------------------------------------------------

long2487 = settingRepository1.GetAttr("STRESS_OVER_SQUARE_TEMPERATURE_ExtraLarge")
'--------------------------------------------------
' Parameter 1 : (String) "STRESS_OVER_SQUARE_TEMPERATURE_ExtraLarge"
' Returned value : (Variant) (Long) 1
'--------------------------------------------------

Dim bSTR4973
bSTR4973 = ""
Dim bSTR4974
bSTR4974 = ""
Dim boolean2487
settingRepository1.GetAttrInfo "STRESS_OVER_SQUARE_TEMPERATURE_ExtraLarge", bSTR4973, bSTR4974, boolean2487
'--------------------------------------------------
' Parameter 1 : (String) "STRESS_OVER_SQUARE_TEMPERATURE_ExtraLarge"
' Parameter 2 : (String) "Default value"
' Parameter 3 : (String) "Unlocked"
' Parameter 4 : (Boolean) False
'--------------------------------------------------

long2488 = settingRepository1.GetAttr("STRESS_OVER_SQUARE_TEMPERATURE_Small")
'--------------------------------------------------
' Parameter 1 : (String) "STRESS_OVER_SQUARE_TEMPERATURE_Small"
' Returned value : (Variant) (Long) 1
'--------------------------------------------------

Dim bSTR4975
bSTR4975 = ""
Dim bSTR4976
bSTR4976 = ""
Dim boolean2488
settingRepository1.GetAttrInfo "STRESS_OVER_SQUARE_TEMPERATURE_Small", bSTR4975, bSTR4976, boolean2488
'--------------------------------------------------
' Parameter 1 : (String) "STRESS_OVER_SQUARE_TEMPERATURE_Small"
' Parameter 2 : (String) "Default value"
' Parameter 3 : (String) "Unlocked"
' Parameter 4 : (Boolean) False
'--------------------------------------------------

long2489 = settingRepository1.GetAttr("STRESS_OVER_SQUARE_TEMPERATURE_ExtraSmall")
'--------------------------------------------------
' Parameter 1 : (String) "STRESS_OVER_SQUARE_TEMPERATURE_ExtraSmall"
' Returned value : (Variant) (Long) 1
'--------------------------------------------------

Dim bSTR4977
bSTR4977 = ""
Dim bSTR4978
bSTR4978 = ""
Dim boolean2489
settingRepository1.GetAttrInfo "STRESS_OVER_SQUARE_TEMPERATURE_ExtraSmall", bSTR4977, bSTR4978, boolean2489
'--------------------------------------------------
' Parameter 1 : (String) "STRESS_OVER_SQUARE_TEMPERATURE_ExtraSmall"
' Parameter 2 : (String) "Default value"
' Parameter 3 : (String) "Unlocked"
' Parameter 4 : (Boolean) False
'--------------------------------------------------

long2490 = settingRepository1.GetAttr("STRESS_OVER_SQUARE_TEMPERATURE_Nanometric")
'--------------------------------------------------
' Parameter 1 : (String) "STRESS_OVER_SQUARE_TEMPERATURE_Nanometric"
' Returned value : (Variant) (Long) 1
'--------------------------------------------------

Dim bSTR4979
bSTR4979 = ""
Dim bSTR4980
bSTR4980 = ""
Dim boolean2490
settingRepository1.GetAttrInfo "STRESS_OVER_SQUARE_TEMPERATURE_Nanometric", bSTR4979, bSTR4980, boolean2490
'--------------------------------------------------
' Parameter 1 : (String) "STRESS_OVER_SQUARE_TEMPERATURE_Nanometric"
' Parameter 2 : (String) "Default value"
' Parameter 3 : (String) "Unlocked"
' Parameter 4 : (Boolean) False
'--------------------------------------------------

End Sub
