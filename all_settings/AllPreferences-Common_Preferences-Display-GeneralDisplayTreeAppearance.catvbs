Language="VBSCRIPT"

Sub CATMain()

Set settingControllers1 = CATIA.SettingControllers

Set settingRepository1 = settingControllers1.Item("Tree")

long1 = settingRepository1.GetAttr("StructState")
'--------------------------------------------------
' Parameter 1 : (String) "StructState"
' Returned value : (Variant) (Long) 1
'--------------------------------------------------

Dim bSTR1
bSTR1 = ""
Dim bSTR2
bSTR2 = ""
Dim boolean1
settingRepository1.GetAttrInfo "StructState", bSTR1, bSTR2, boolean1
'--------------------------------------------------
' Parameter 1 : (String) "StructState"
' Parameter 2 : (String) "Default value"
' Parameter 3 : (String) "Unlocked"
' Parameter 4 : (Boolean) False
'--------------------------------------------------

bSTR3 = settingRepository1.GetAttr("Orientation")
'--------------------------------------------------
' Parameter 1 : (String) "Orientation"
' Returned value : (Variant) (String) "V"
'--------------------------------------------------

Dim bSTR4
bSTR4 = ""
Dim bSTR5
bSTR5 = ""
Dim boolean2
settingRepository1.GetAttrInfo "Orientation", bSTR4, bSTR5, boolean2
'--------------------------------------------------
' Parameter 1 : (String) "Orientation"
' Parameter 2 : (String) "Default value"
' Parameter 3 : (String) "Unlocked"
' Parameter 4 : (Boolean) False
'--------------------------------------------------

long2 = settingRepository1.GetAttr("LeavesDependant")
'--------------------------------------------------
' Parameter 1 : (String) "LeavesDependant"
' Returned value : (Variant) (Long) 1
'--------------------------------------------------

Dim bSTR6
bSTR6 = ""
Dim bSTR7
bSTR7 = ""
Dim boolean3
settingRepository1.GetAttrInfo "LeavesDependant", bSTR6, bSTR7, boolean3
'--------------------------------------------------
' Parameter 1 : (String) "LeavesDependant"
' Parameter 2 : (String) "Default value"
' Parameter 3 : (String) "Unlocked"
' Parameter 4 : (Boolean) False
'--------------------------------------------------

long3 = settingRepository1.GetAttr("LeavesSize")
'--------------------------------------------------
' Parameter 1 : (String) "LeavesSize"
' Returned value : (Variant) (Long) 8
'--------------------------------------------------

Dim bSTR8
bSTR8 = ""
Dim bSTR9
bSTR9 = ""
Dim boolean4
settingRepository1.GetAttrInfo "LeavesSize", bSTR8, bSTR9, boolean4
'--------------------------------------------------
' Parameter 1 : (String) "LeavesSize"
' Parameter 2 : (String) "Default value"
' Parameter 3 : (String) "Unlocked"
' Parameter 4 : (Boolean) False
'--------------------------------------------------

boolean5 = settingRepository1.GetAttr("ShowNoShow")
'--------------------------------------------------
' Parameter 1 : (String) "ShowNoShow"
' Returned value : (Variant) (Boolean) True
'--------------------------------------------------

Dim bSTR10
bSTR10 = ""
Dim bSTR11
bSTR11 = ""
Dim boolean6
settingRepository1.GetAttrInfo "ShowNoShow", bSTR10, bSTR11, boolean6
'--------------------------------------------------
' Parameter 1 : (String) "ShowNoShow"
' Parameter 2 : (String) "Default value"
' Parameter 3 : (String) "Unlocked"
' Parameter 4 : (Boolean) False
'--------------------------------------------------

boolean7 = settingRepository1.GetAttr("OpenTreeWindowExpanded")
'--------------------------------------------------
' Parameter 1 : (String) "OpenTreeWindowExpanded"
' Returned value : (Variant) (Boolean) False
'--------------------------------------------------

Dim bSTR12
bSTR12 = ""
Dim bSTR13
bSTR13 = ""
Dim boolean8
settingRepository1.GetAttrInfo "OpenTreeWindowExpanded", bSTR12, bSTR13, boolean8
'--------------------------------------------------
' Parameter 1 : (String) "OpenTreeWindowExpanded"
' Parameter 2 : (String) "Default value"
' Parameter 3 : (String) "Unlocked"
' Parameter 4 : (Boolean) False
'--------------------------------------------------

boolean9 = settingRepository1.GetAttr("SubTreePositionDimension")
'--------------------------------------------------
' Parameter 1 : (String) "SubTreePositionDimension"
' Returned value : (Variant) (Boolean) False
'--------------------------------------------------

Dim bSTR14
bSTR14 = ""
Dim bSTR15
bSTR15 = ""
Dim boolean10
settingRepository1.GetAttrInfo "SubTreePositionDimension", bSTR14, bSTR15, boolean10
'--------------------------------------------------
' Parameter 1 : (String) "SubTreePositionDimension"
' Parameter 2 : (String) "Default value"
' Parameter 3 : (String) "Unlocked"
' Parameter 4 : (Boolean) False
'--------------------------------------------------

End Sub
