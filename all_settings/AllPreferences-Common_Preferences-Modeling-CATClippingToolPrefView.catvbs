Language="VBSCRIPT"

Sub CATMain()

Set settingControllers1 = CATIA.SettingControllers

Set settingRepository1 = settingControllers1.Item("ClippingToolSettings")

long1 = settingRepository1.GetAttr("DefaultNormalDir")
'--------------------------------------------------
' Parameter 1 : (String) "DefaultNormalDir"
' Returned value : (Variant) (Long) 3
'--------------------------------------------------

Dim bSTR1
bSTR1 = ""
Dim bSTR2
bSTR2 = ""
Dim boolean1
settingRepository1.GetAttrInfo "DefaultNormalDir", bSTR1, bSTR2, boolean1
'--------------------------------------------------
' Parameter 1 : (String) "DefaultNormalDir"
' Parameter 2 : (String) "Default value"
' Parameter 3 : (String) "Unlocked"
' Parameter 4 : (Boolean) False
'--------------------------------------------------

long2 = settingRepository1.GetAttr("ClippingUpdateMode")
'--------------------------------------------------
' Parameter 1 : (String) "ClippingUpdateMode"
' Returned value : (Variant) (Long) 1
'--------------------------------------------------

Dim bSTR3
bSTR3 = ""
Dim bSTR4
bSTR4 = ""
Dim boolean2
settingRepository1.GetAttrInfo "ClippingUpdateMode", bSTR3, bSTR4, boolean2
'--------------------------------------------------
' Parameter 1 : (String) "ClippingUpdateMode"
' Parameter 2 : (String) "Default value"
' Parameter 3 : (String) "Unlocked"
' Parameter 4 : (Boolean) False
'--------------------------------------------------

End Sub
