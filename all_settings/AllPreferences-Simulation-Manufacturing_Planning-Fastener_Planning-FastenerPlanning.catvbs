Language="VBSCRIPT"

Sub CATMain()

Set settingControllers1 = CATIA.SettingControllers

Set settingRepository1 = settingControllers1.Item("DELMSDSysEdSettings")

boolean1 = settingRepository1.GetAttr("DragAndDropCheckButton")
'--------------------------------------------------
' Parameter 1 : (String) "DragAndDropCheckButton"
' Returned value : (Variant) (Boolean) True
'--------------------------------------------------

Dim bSTR1
bSTR1 = ""
Dim bSTR2
bSTR2 = ""
Dim boolean2
settingRepository1.GetAttrInfo "DragAndDropCheckButton", bSTR1, bSTR2, boolean2
'--------------------------------------------------
' Parameter 1 : (String) "DragAndDropCheckButton"
' Parameter 2 : (String) "Default value"
' Parameter 3 : (String) "Unlocked"
' Parameter 4 : (Boolean) False
'--------------------------------------------------

boolean3 = settingRepository1.GetAttr("KeepTimeConstraints")
'--------------------------------------------------
' Parameter 1 : (String) "KeepTimeConstraints"
' Returned value : (Variant) (Boolean) True
'--------------------------------------------------

Dim bSTR3
bSTR3 = ""
Dim bSTR4
bSTR4 = ""
Dim boolean4
settingRepository1.GetAttrInfo "KeepTimeConstraints", bSTR3, bSTR4, boolean4
'--------------------------------------------------
' Parameter 1 : (String) "KeepTimeConstraints"
' Parameter 2 : (String) "Default value"
' Parameter 3 : (String) "Unlocked"
' Parameter 4 : (Boolean) False
'--------------------------------------------------

uLong1 = settingRepository1.GetAttr("ManageLinksToResources")
'--------------------------------------------------
' Parameter 1 : (String) "ManageLinksToResources"
' Returned value : (Variant) (Unsigned Long) 1
'--------------------------------------------------

Dim bSTR5
bSTR5 = ""
Dim bSTR6
bSTR6 = ""
Dim boolean5
settingRepository1.GetAttrInfo "ManageLinksToResources", bSTR5, bSTR6, boolean5
'--------------------------------------------------
' Parameter 1 : (String) "ManageLinksToResources"
' Parameter 2 : (String) "Default value"
' Parameter 3 : (String) "Unlocked"
' Parameter 4 : (Boolean) False
'--------------------------------------------------

boolean6 = settingRepository1.GetAttr("KeepConstraint")
'--------------------------------------------------
' Parameter 1 : (String) "KeepConstraint"
' Returned value : (Variant) (Boolean) False
'--------------------------------------------------

Dim bSTR7
bSTR7 = ""
Dim bSTR8
bSTR8 = ""
Dim boolean7
settingRepository1.GetAttrInfo "KeepConstraint", bSTR7, bSTR8, boolean7
'--------------------------------------------------
' Parameter 1 : (String) "KeepConstraint"
' Parameter 2 : (String) "Default value"
' Parameter 3 : (String) "Unlocked"
' Parameter 4 : (Boolean) False
'--------------------------------------------------

boolean8 = settingRepository1.GetAttr("KeepPosition")
'--------------------------------------------------
' Parameter 1 : (String) "KeepPosition"
' Returned value : (Variant) (Boolean) False
'--------------------------------------------------

Dim bSTR9
bSTR9 = ""
Dim bSTR10
bSTR10 = ""
Dim boolean9
settingRepository1.GetAttrInfo "KeepPosition", bSTR9, bSTR10, boolean9
'--------------------------------------------------
' Parameter 1 : (String) "KeepPosition"
' Parameter 2 : (String) "Default value"
' Parameter 3 : (String) "Unlocked"
' Parameter 4 : (Boolean) False
'--------------------------------------------------

long1 = settingRepository1.GetAttr("KeepPositionExact")
'--------------------------------------------------
' Parameter 1 : (String) "KeepPositionExact"
' Returned value : (Variant) (Long) 0
'--------------------------------------------------

Dim bSTR11
bSTR11 = ""
Dim bSTR12
bSTR12 = ""
Dim boolean10
settingRepository1.GetAttrInfo "KeepPositionExact", bSTR11, bSTR12, boolean10
'--------------------------------------------------
' Parameter 1 : (String) "KeepPositionExact"
' Parameter 2 : (String) "Default value"
' Parameter 3 : (String) "Unlocked"
' Parameter 4 : (Boolean) False
'--------------------------------------------------

boolean11 = settingRepository1.GetAttr("CoherenceBLActivatedCtrlCheckButton")
'--------------------------------------------------
' Parameter 1 : (String) "CoherenceBLActivatedCtrlCheckButton"
' Returned value : (Variant) (Boolean) False
'--------------------------------------------------

Dim bSTR13
bSTR13 = ""
Dim bSTR14
bSTR14 = ""
Dim boolean12
settingRepository1.GetAttrInfo "CoherenceBLActivatedCtrlCheckButton", bSTR13, bSTR14, boolean12
'--------------------------------------------------
' Parameter 1 : (String) "CoherenceBLActivatedCtrlCheckButton"
' Parameter 2 : (String) "Default value"
' Parameter 3 : (String) "Unlocked"
' Parameter 4 : (Boolean) False
'--------------------------------------------------

boolean13 = settingRepository1.GetAttr("CoherenceCtrlCheckButton")
'--------------------------------------------------
' Parameter 1 : (String) "CoherenceCtrlCheckButton"
' Returned value : (Variant) (Boolean) True
'--------------------------------------------------

Dim bSTR15
bSTR15 = ""
Dim bSTR16
bSTR16 = ""
Dim boolean14
settingRepository1.GetAttrInfo "CoherenceCtrlCheckButton", bSTR15, bSTR16, boolean14
'--------------------------------------------------
' Parameter 1 : (String) "CoherenceCtrlCheckButton"
' Parameter 2 : (String) "Default value"
' Parameter 3 : (String) "Unlocked"
' Parameter 4 : (Boolean) False
'--------------------------------------------------

boolean15 = settingRepository1.GetAttr("LoadOutputs")
'--------------------------------------------------
' Parameter 1 : (String) "LoadOutputs"
' Returned value : (Variant) (Boolean) False
'--------------------------------------------------

Dim bSTR17
bSTR17 = ""
Dim bSTR18
bSTR18 = ""
Dim boolean16
settingRepository1.GetAttrInfo "LoadOutputs", bSTR17, bSTR18, boolean16
'--------------------------------------------------
' Parameter 1 : (String) "LoadOutputs"
' Parameter 2 : (String) "Default value"
' Parameter 3 : (String) "Unlocked"
' Parameter 4 : (Boolean) False
'--------------------------------------------------

long2 = settingRepository1.GetAttr("OutputFastenerMode")
'--------------------------------------------------
' Parameter 1 : (String) "OutputFastenerMode"
' Returned value : (Variant) (Long) 0
'--------------------------------------------------

Dim bSTR19
bSTR19 = ""
Dim bSTR20
bSTR20 = ""
Dim boolean17
settingRepository1.GetAttrInfo "OutputFastenerMode", bSTR19, bSTR20, boolean17
'--------------------------------------------------
' Parameter 1 : (String) "OutputFastenerMode"
' Parameter 2 : (String) "Default value"
' Parameter 3 : (String) "Unlocked"
' Parameter 4 : (Boolean) False
'--------------------------------------------------

boolean18 = settingRepository1.GetAttr("OutputBuildUpContextCategory")
'--------------------------------------------------
' Parameter 1 : (String) "OutputBuildUpContextCategory"
' Returned value : (Variant) (Boolean) False
'--------------------------------------------------

Dim bSTR21
bSTR21 = ""
Dim bSTR22
bSTR22 = ""
Dim boolean19
settingRepository1.GetAttrInfo "OutputBuildUpContextCategory", bSTR21, bSTR22, boolean19
'--------------------------------------------------
' Parameter 1 : (String) "OutputBuildUpContextCategory"
' Parameter 2 : (String) "Default value"
' Parameter 3 : (String) "Unlocked"
' Parameter 4 : (Boolean) False
'--------------------------------------------------

boolean20 = settingRepository1.GetAttr("OutputBuildUpAdditionalProductsCategory")
'--------------------------------------------------
' Parameter 1 : (String) "OutputBuildUpAdditionalProductsCategory"
' Returned value : (Variant) (Boolean) False
'--------------------------------------------------

Dim bSTR23
bSTR23 = ""
Dim bSTR24
bSTR24 = ""
Dim boolean21
settingRepository1.GetAttrInfo "OutputBuildUpAdditionalProductsCategory", bSTR23, bSTR24, boolean21
'--------------------------------------------------
' Parameter 1 : (String) "OutputBuildUpAdditionalProductsCategory"
' Parameter 2 : (String) "Default value"
' Parameter 3 : (String) "Unlocked"
' Parameter 4 : (Boolean) False
'--------------------------------------------------

long3 = settingRepository1.GetAttr("OutputBuildUpAdditionalProductsCategoryMode")
'--------------------------------------------------
' Parameter 1 : (String) "OutputBuildUpAdditionalProductsCategoryMode"
' Returned value : (Variant) (Long) 0
'--------------------------------------------------

Dim bSTR25
bSTR25 = ""
Dim bSTR26
bSTR26 = ""
Dim boolean22
settingRepository1.GetAttrInfo "OutputBuildUpAdditionalProductsCategoryMode", bSTR25, bSTR26, boolean22
'--------------------------------------------------
' Parameter 1 : (String) "OutputBuildUpAdditionalProductsCategoryMode"
' Parameter 2 : (String) "Default value"
' Parameter 3 : (String) "Unlocked"
' Parameter 4 : (Boolean) False
'--------------------------------------------------

boolean23 = settingRepository1.GetAttr("OutputBuildUpAdditionalIncludeExternalContext")
'--------------------------------------------------
' Parameter 1 : (String) "OutputBuildUpAdditionalIncludeExternalContext"
' Returned value : (Variant) (Boolean) False
'--------------------------------------------------

Dim bSTR27
bSTR27 = ""
Dim bSTR28
bSTR28 = ""
Dim boolean24
settingRepository1.GetAttrInfo "OutputBuildUpAdditionalIncludeExternalContext", bSTR27, bSTR28, boolean24
'--------------------------------------------------
' Parameter 1 : (String) "OutputBuildUpAdditionalIncludeExternalContext"
' Parameter 2 : (String) "Default value"
' Parameter 3 : (String) "Unlocked"
' Parameter 4 : (Boolean) False
'--------------------------------------------------

boolean25 = settingRepository1.GetAttr("CopyModelFromMfgItem")
'--------------------------------------------------
' Parameter 1 : (String) "CopyModelFromMfgItem"
' Returned value : (Variant) (Boolean) False
'--------------------------------------------------

Dim bSTR29
bSTR29 = ""
Dim bSTR30
bSTR30 = ""
Dim boolean26
settingRepository1.GetAttrInfo "CopyModelFromMfgItem", bSTR29, bSTR30, boolean26
'--------------------------------------------------
' Parameter 1 : (String) "CopyModelFromMfgItem"
' Parameter 2 : (String) "Default value"
' Parameter 3 : (String) "Unlocked"
' Parameter 4 : (Boolean) False
'--------------------------------------------------

boolean27 = settingRepository1.GetAttr("CopyModelFromWorkplan")
'--------------------------------------------------
' Parameter 1 : (String) "CopyModelFromWorkplan"
' Returned value : (Variant) (Boolean) False
'--------------------------------------------------

Dim bSTR31
bSTR31 = ""
Dim bSTR32
bSTR32 = ""
Dim boolean28
settingRepository1.GetAttrInfo "CopyModelFromWorkplan", bSTR31, bSTR32, boolean28
'--------------------------------------------------
' Parameter 1 : (String) "CopyModelFromWorkplan"
' Parameter 2 : (String) "Default value"
' Parameter 3 : (String) "Unlocked"
' Parameter 4 : (Boolean) False
'--------------------------------------------------

boolean29 = settingRepository1.GetAttr("CopyModelFromFatherOnSystem")
'--------------------------------------------------
' Parameter 1 : (String) "CopyModelFromFatherOnSystem"
' Returned value : (Variant) (Boolean) False
'--------------------------------------------------

Dim bSTR33
bSTR33 = ""
Dim bSTR34
bSTR34 = ""
Dim boolean30
settingRepository1.GetAttrInfo "CopyModelFromFatherOnSystem", bSTR33, bSTR34, boolean30
'--------------------------------------------------
' Parameter 1 : (String) "CopyModelFromFatherOnSystem"
' Parameter 2 : (String) "Default value"
' Parameter 3 : (String) "Unlocked"
' Parameter 4 : (Boolean) False
'--------------------------------------------------

boolean31 = settingRepository1.GetAttr("CopyModelFromFatherOnOperation")
'--------------------------------------------------
' Parameter 1 : (String) "CopyModelFromFatherOnOperation"
' Returned value : (Variant) (Boolean) False
'--------------------------------------------------

Dim bSTR35
bSTR35 = ""
Dim bSTR36
bSTR36 = ""
Dim boolean32
settingRepository1.GetAttrInfo "CopyModelFromFatherOnOperation", bSTR35, bSTR36, boolean32
'--------------------------------------------------
' Parameter 1 : (String) "CopyModelFromFatherOnOperation"
' Parameter 2 : (String) "Default value"
' Parameter 3 : (String) "Unlocked"
' Parameter 4 : (Boolean) False
'--------------------------------------------------

boolean33 = settingRepository1.GetAttr("CreateLinkAssembleProcessCheckButton")
'--------------------------------------------------
' Parameter 1 : (String) "CreateLinkAssembleProcessCheckButton"
' Returned value : (Variant) (Boolean) True
'--------------------------------------------------

Dim bSTR37
bSTR37 = ""
Dim bSTR38
bSTR38 = ""
Dim boolean34
settingRepository1.GetAttrInfo "CreateLinkAssembleProcessCheckButton", bSTR37, bSTR38, boolean34
'--------------------------------------------------
' Parameter 1 : (String) "CreateLinkAssembleProcessCheckButton"
' Parameter 2 : (String) "Default value"
' Parameter 3 : (String) "Unlocked"
' Parameter 4 : (Boolean) False
'--------------------------------------------------

boolean35 = settingRepository1.GetAttr("GroupUnderGeneralLoadinglOpCheckButton")
'--------------------------------------------------
' Parameter 1 : (String) "GroupUnderGeneralLoadinglOpCheckButton"
' Returned value : (Variant) (Boolean) False
'--------------------------------------------------

Dim bSTR39
bSTR39 = ""
Dim bSTR40
bSTR40 = ""
Dim boolean36
settingRepository1.GetAttrInfo "GroupUnderGeneralLoadinglOpCheckButton", bSTR39, bSTR40, boolean36
'--------------------------------------------------
' Parameter 1 : (String) "GroupUnderGeneralLoadinglOpCheckButton"
' Parameter 2 : (String) "Default value"
' Parameter 3 : (String) "Unlocked"
' Parameter 4 : (Boolean) False
'--------------------------------------------------

boolean37 = settingRepository1.GetAttr("CreateLoadingOperationForPreviousAssemblyCheckButton")
'--------------------------------------------------
' Parameter 1 : (String) "CreateLoadingOperationForPreviousAssemblyCheckButton"
' Returned value : (Variant) (Boolean) False
'--------------------------------------------------

Dim bSTR41
bSTR41 = ""
Dim bSTR42
bSTR42 = ""
Dim boolean38
settingRepository1.GetAttrInfo "CreateLoadingOperationForPreviousAssemblyCheckButton", bSTR41, bSTR42, boolean38
'--------------------------------------------------
' Parameter 1 : (String) "CreateLoadingOperationForPreviousAssemblyCheckButton"
' Parameter 2 : (String) "Default value"
' Parameter 3 : (String) "Unlocked"
' Parameter 4 : (Boolean) False
'--------------------------------------------------

boolean39 = settingRepository1.GetAttr("KeepPositionSameSystemStructure")
'--------------------------------------------------
' Parameter 1 : (String) "KeepPositionSameSystemStructure"
' Returned value : (Variant) (Boolean) False
'--------------------------------------------------

Dim bSTR43
bSTR43 = ""
Dim bSTR44
bSTR44 = ""
Dim boolean40
settingRepository1.GetAttrInfo "KeepPositionSameSystemStructure", bSTR43, bSTR44, boolean40
'--------------------------------------------------
' Parameter 1 : (String) "KeepPositionSameSystemStructure"
' Parameter 2 : (String) "Default value"
' Parameter 3 : (String) "Unlocked"
' Parameter 4 : (Boolean) False
'--------------------------------------------------

long4 = settingRepository1.GetAttr("KeepPositionExactSameSystemStructure")
'--------------------------------------------------
' Parameter 1 : (String) "KeepPositionExactSameSystemStructure"
' Returned value : (Variant) (Long) 0
'--------------------------------------------------

Dim bSTR45
bSTR45 = ""
Dim bSTR46
bSTR46 = ""
Dim boolean41
settingRepository1.GetAttrInfo "KeepPositionExactSameSystemStructure", bSTR45, bSTR46, boolean41
'--------------------------------------------------
' Parameter 1 : (String) "KeepPositionExactSameSystemStructure"
' Parameter 2 : (String) "Default value"
' Parameter 3 : (String) "Unlocked"
' Parameter 4 : (Boolean) False
'--------------------------------------------------

End Sub
