Language="VBSCRIPT"

Sub CATMain()

Set settingControllers1 = CATIA.SettingControllers

Set settingRepository1 = settingControllers1.Item("ELEditorToolsSymbolRep")

long1 = settingRepository1.GetAttr("DefaultRepresentationSymbolOption")
'--------------------------------------------------
' Parameter 1 : (String) "DefaultRepresentationSymbolOption"
' Returned value : (Variant) (Long) 0
'--------------------------------------------------

Dim bSTR1
bSTR1 = ""
Dim bSTR2
bSTR2 = ""
Dim boolean1
settingRepository1.GetAttrInfo "DefaultRepresentationSymbolOption", bSTR1, bSTR2, boolean1
'--------------------------------------------------
' Parameter 1 : (String) "DefaultRepresentationSymbolOption"
' Parameter 2 : (String) "Default value"
' Parameter 3 : (String) "Unlocked"
' Parameter 4 : (Boolean) False
'--------------------------------------------------

double1 = settingRepository1.GetAttr("OffsetGridValueOption")
'--------------------------------------------------
' Parameter 1 : (String) "OffsetGridValueOption"
' Returned value : (Variant) (Double) 20.000000
'--------------------------------------------------

Dim bSTR3
bSTR3 = ""
Dim bSTR4
bSTR4 = ""
Dim boolean2
settingRepository1.GetAttrInfo "OffsetGridValueOption", bSTR3, bSTR4, boolean2
'--------------------------------------------------
' Parameter 1 : (String) "OffsetGridValueOption"
' Parameter 2 : (String) "Default value"
' Parameter 3 : (String) "Unlocked"
' Parameter 4 : (Boolean) False
'--------------------------------------------------

double2 = settingRepository1.GetAttr("StepGridValueOption")
'--------------------------------------------------
' Parameter 1 : (String) "StepGridValueOption"
' Returned value : (Variant) (Double) 10.000000
'--------------------------------------------------

Dim bSTR5
bSTR5 = ""
Dim bSTR6
bSTR6 = ""
Dim boolean3
settingRepository1.GetAttrInfo "StepGridValueOption", bSTR5, bSTR6, boolean3
'--------------------------------------------------
' Parameter 1 : (String) "StepGridValueOption"
' Parameter 2 : (String) "Default value"
' Parameter 3 : (String) "Unlocked"
' Parameter 4 : (Boolean) False
'--------------------------------------------------

End Sub
