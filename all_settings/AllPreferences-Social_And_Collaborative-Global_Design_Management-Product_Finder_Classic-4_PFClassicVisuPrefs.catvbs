Language="VBSCRIPT"

Sub CATMain()

Set settingControllers1 = CATIA.SettingControllers

Set settingRepository1 = settingControllers1.Item("VPMNavigator")

boolean1 = settingRepository1.GetAttr("Navigation3D")
'--------------------------------------------------
' Parameter 1 : (String) "Navigation3D"
' Returned value : (Variant) (Boolean) True
'--------------------------------------------------

Dim bSTR1
bSTR1 = ""
Dim bSTR2
bSTR2 = ""
Dim boolean2
settingRepository1.GetAttrInfo "Navigation3D", bSTR1, bSTR2, boolean2
'--------------------------------------------------
' Parameter 1 : (String) "Navigation3D"
' Parameter 2 : (String) "Default value"
' Parameter 3 : (String) "Unlocked"
' Parameter 4 : (Boolean) False
'--------------------------------------------------

boolean3 = settingRepository1.GetAttr("NeverDisplayGeometryPFC")
'--------------------------------------------------
' Parameter 1 : (String) "NeverDisplayGeometryPFC"
' Returned value : (Variant) (Boolean) False
'--------------------------------------------------

Dim bSTR3
bSTR3 = ""
Dim bSTR4
bSTR4 = ""
Dim boolean4
settingRepository1.GetAttrInfo "NeverDisplayGeometryPFC", bSTR3, bSTR4, boolean4
'--------------------------------------------------
' Parameter 1 : (String) "NeverDisplayGeometryPFC"
' Parameter 2 : (String) "Default value"
' Parameter 3 : (String) "Unlocked"
' Parameter 4 : (Boolean) False
'--------------------------------------------------

Dim arrayOfVariantOfULong1
arrayOfVariantOfULong1 = settingRepository1.GetAttrArray("BackgroundColor")
'--------------------------------------------------
' Parameter 1 : (String) "BackgroundColor"
' Returned value : (Array) 
'    Array[0] : (Variant) (Unsigned Long) 212
'    Array[1] : (Variant) (Unsigned Long) 212
'    Array[2] : (Variant) (Unsigned Long) 223
'--------------------------------------------------

Dim bSTR5
bSTR5 = ""
Dim bSTR6
bSTR6 = ""
Dim boolean5
settingRepository1.GetAttrInfo "BackgroundColor", bSTR5, bSTR6, boolean5
'--------------------------------------------------
' Parameter 1 : (String) "BackgroundColor"
' Parameter 2 : (String) "Default value"
' Parameter 3 : (String) "Unlocked"
' Parameter 4 : (Boolean) False
'--------------------------------------------------

boolean6 = settingRepository1.GetAttr("NoMultiRep")
'--------------------------------------------------
' Parameter 1 : (String) "NoMultiRep"
' Returned value : (Variant) (Boolean) False
'--------------------------------------------------

Dim bSTR7
bSTR7 = ""
Dim bSTR8
bSTR8 = ""
Dim boolean7
settingRepository1.GetAttrInfo "NoMultiRep", bSTR7, bSTR8, boolean7
'--------------------------------------------------
' Parameter 1 : (String) "NoMultiRep"
' Parameter 2 : (String) "Default value"
' Parameter 3 : (String) "Unlocked"
' Parameter 4 : (Boolean) False
'--------------------------------------------------

uLong1 = settingRepository1.GetAttr("3DSearchMaxItemsBeforeWarn")
'--------------------------------------------------
' Parameter 1 : (String) "3DSearchMaxItemsBeforeWarn"
' Returned value : (Variant) (Unsigned Long) 0
'--------------------------------------------------

Dim bSTR9
bSTR9 = ""
Dim bSTR10
bSTR10 = ""
Dim boolean8
settingRepository1.GetAttrInfo "3DSearchMaxItemsBeforeWarn", bSTR9, bSTR10, boolean8
'--------------------------------------------------
' Parameter 1 : (String) "3DSearchMaxItemsBeforeWarn"
' Parameter 2 : (String) "Default value"
' Parameter 3 : (String) "Unlocked"
' Parameter 4 : (Boolean) False
'--------------------------------------------------

boolean9 = settingRepository1.GetAttr("AntiZFighting")
'--------------------------------------------------
' Parameter 1 : (String) "AntiZFighting"
' Returned value : (Variant) (Boolean) False
'--------------------------------------------------

Dim bSTR11
bSTR11 = ""
Dim bSTR12
bSTR12 = ""
Dim boolean10
settingRepository1.GetAttrInfo "AntiZFighting", bSTR11, bSTR12, boolean10
'--------------------------------------------------
' Parameter 1 : (String) "AntiZFighting"
' Parameter 2 : (String) "Default value"
' Parameter 3 : (String) "Unlocked"
' Parameter 4 : (Boolean) False
'--------------------------------------------------

long1 = settingRepository1.GetAttr("TurntableReframe")
'--------------------------------------------------
' Parameter 1 : (String) "TurntableReframe"
' Returned value : (Variant) (Long) 1
'--------------------------------------------------

Dim bSTR13
bSTR13 = ""
Dim bSTR14
bSTR14 = ""
Dim boolean11
settingRepository1.GetAttrInfo "TurntableReframe", bSTR13, bSTR14, boolean11
'--------------------------------------------------
' Parameter 1 : (String) "TurntableReframe"
' Parameter 2 : (String) "Default value"
' Parameter 3 : (String) "Unlocked"
' Parameter 4 : (Boolean) False
'--------------------------------------------------

long2 = settingRepository1.GetAttr("TurntableAnimation")
'--------------------------------------------------
' Parameter 1 : (String) "TurntableAnimation"
' Returned value : (Variant) (Long) 1
'--------------------------------------------------

Dim bSTR15
bSTR15 = ""
Dim bSTR16
bSTR16 = ""
Dim boolean12
settingRepository1.GetAttrInfo "TurntableAnimation", bSTR15, bSTR16, boolean12
'--------------------------------------------------
' Parameter 1 : (String) "TurntableAnimation"
' Parameter 2 : (String) "Default value"
' Parameter 3 : (String) "Unlocked"
' Parameter 4 : (Boolean) False
'--------------------------------------------------

long3 = settingRepository1.GetAttr("exploreStrategyPFC")
'--------------------------------------------------
' Parameter 1 : (String) "exploreStrategyPFC"
' Returned value : (Variant) (Long) 1
'--------------------------------------------------

Dim bSTR17
bSTR17 = ""
Dim bSTR18
bSTR18 = ""
Dim boolean13
settingRepository1.GetAttrInfo "exploreStrategyPFC", bSTR17, bSTR18, boolean13
'--------------------------------------------------
' Parameter 1 : (String) "exploreStrategyPFC"
' Parameter 2 : (String) "Default value"
' Parameter 3 : (String) "Unlocked"
' Parameter 4 : (Boolean) False
'--------------------------------------------------

uLong2 = settingRepository1.GetAttr("exploreWrapDensityPFC")
'--------------------------------------------------
' Parameter 1 : (String) "exploreWrapDensityPFC"
' Returned value : (Variant) (Unsigned Long) 5
'--------------------------------------------------

Dim bSTR19
bSTR19 = ""
Dim bSTR20
bSTR20 = ""
Dim boolean14
settingRepository1.GetAttrInfo "exploreWrapDensityPFC", bSTR19, bSTR20, boolean14
'--------------------------------------------------
' Parameter 1 : (String) "exploreWrapDensityPFC"
' Parameter 2 : (String) "Default value"
' Parameter 3 : (String) "Unlocked"
' Parameter 4 : (Boolean) False
'--------------------------------------------------

uLong3 = settingRepository1.GetAttr("exploreWrapDensityPFCCloud")
'--------------------------------------------------
' Parameter 1 : (String) "exploreWrapDensityPFCCloud"
' Returned value : (Variant) (Unsigned Long) 1
'--------------------------------------------------

Dim bSTR21
bSTR21 = ""
Dim bSTR22
bSTR22 = ""
Dim boolean15
settingRepository1.GetAttrInfo "exploreWrapDensityPFCCloud", bSTR21, bSTR22, boolean15
'--------------------------------------------------
' Parameter 1 : (String) "exploreWrapDensityPFCCloud"
' Parameter 2 : (String) "Default value"
' Parameter 3 : (String) "Unlocked"
' Parameter 4 : (Boolean) False
'--------------------------------------------------

long4 = settingRepository1.GetAttr("expandStrategyPFC")
'--------------------------------------------------
' Parameter 1 : (String) "expandStrategyPFC"
' Returned value : (Variant) (Long) 1
'--------------------------------------------------

Dim bSTR23
bSTR23 = ""
Dim bSTR24
bSTR24 = ""
Dim boolean16
settingRepository1.GetAttrInfo "expandStrategyPFC", bSTR23, bSTR24, boolean16
'--------------------------------------------------
' Parameter 1 : (String) "expandStrategyPFC"
' Parameter 2 : (String) "Default value"
' Parameter 3 : (String) "Unlocked"
' Parameter 4 : (Boolean) False
'--------------------------------------------------

uLong4 = settingRepository1.GetAttr("expandWrapDensityPFC")
'--------------------------------------------------
' Parameter 1 : (String) "expandWrapDensityPFC"
' Returned value : (Variant) (Unsigned Long) 5
'--------------------------------------------------

Dim bSTR25
bSTR25 = ""
Dim bSTR26
bSTR26 = ""
Dim boolean17
settingRepository1.GetAttrInfo "expandWrapDensityPFC", bSTR25, bSTR26, boolean17
'--------------------------------------------------
' Parameter 1 : (String) "expandWrapDensityPFC"
' Parameter 2 : (String) "Default value"
' Parameter 3 : (String) "Unlocked"
' Parameter 4 : (Boolean) False
'--------------------------------------------------

uLong5 = settingRepository1.GetAttr("expandWrapDensityPFCCloud")
'--------------------------------------------------
' Parameter 1 : (String) "expandWrapDensityPFCCloud"
' Returned value : (Variant) (Unsigned Long) 1
'--------------------------------------------------

Dim bSTR27
bSTR27 = ""
Dim bSTR28
bSTR28 = ""
Dim boolean18
settingRepository1.GetAttrInfo "expandWrapDensityPFCCloud", bSTR27, bSTR28, boolean18
'--------------------------------------------------
' Parameter 1 : (String) "expandWrapDensityPFCCloud"
' Parameter 2 : (String) "Default value"
' Parameter 3 : (String) "Unlocked"
' Parameter 4 : (Boolean) False
'--------------------------------------------------

uLong6 = settingRepository1.GetAttr("PixelCulling")
'--------------------------------------------------
' Parameter 1 : (String) "PixelCulling"
' Returned value : (Variant) (Unsigned Long) 25
'--------------------------------------------------

Dim bSTR29
bSTR29 = ""
Dim bSTR30
bSTR30 = ""
Dim boolean19
settingRepository1.GetAttrInfo "PixelCulling", bSTR29, bSTR30, boolean19
'--------------------------------------------------
' Parameter 1 : (String) "PixelCulling"
' Parameter 2 : (String) "Default value"
' Parameter 3 : (String) "Unlocked"
' Parameter 4 : (Boolean) False
'--------------------------------------------------

boolean20 = settingRepository1.GetAttr("StaticThumbnailsPFC")
'--------------------------------------------------
' Parameter 1 : (String) "StaticThumbnailsPFC"
' Returned value : (Variant) (Boolean) False
'--------------------------------------------------

Dim bSTR31
bSTR31 = ""
Dim bSTR32
bSTR32 = ""
Dim boolean21
settingRepository1.GetAttrInfo "StaticThumbnailsPFC", bSTR31, bSTR32, boolean21
'--------------------------------------------------
' Parameter 1 : (String) "StaticThumbnailsPFC"
' Parameter 2 : (String) "Default value"
' Parameter 3 : (String) "Unlocked"
' Parameter 4 : (Boolean) False
'--------------------------------------------------

boolean22 = settingRepository1.GetAttr("NeverDisplayGeometryPFC")
'--------------------------------------------------
' Parameter 1 : (String) "NeverDisplayGeometryPFC"
' Returned value : (Variant) (Boolean) False
'--------------------------------------------------

Dim bSTR33
bSTR33 = ""
Dim bSTR34
bSTR34 = ""
Dim boolean23
settingRepository1.GetAttrInfo "NeverDisplayGeometryPFC", bSTR33, bSTR34, boolean23
'--------------------------------------------------
' Parameter 1 : (String) "NeverDisplayGeometryPFC"
' Parameter 2 : (String) "Default value"
' Parameter 3 : (String) "Unlocked"
' Parameter 4 : (Boolean) False
'--------------------------------------------------

boolean24 = settingRepository1.GetAttr("NavRepOrNothingPFC")
'--------------------------------------------------
' Parameter 1 : (String) "NavRepOrNothingPFC"
' Returned value : (Variant) (Boolean) True
'--------------------------------------------------

Dim bSTR35
bSTR35 = ""
Dim bSTR36
bSTR36 = ""
Dim boolean25
settingRepository1.GetAttrInfo "NavRepOrNothingPFC", bSTR35, bSTR36, boolean25
'--------------------------------------------------
' Parameter 1 : (String) "NavRepOrNothingPFC"
' Parameter 2 : (String) "Default value"
' Parameter 3 : (String) "Unlocked"
' Parameter 4 : (Boolean) False
'--------------------------------------------------

boolean26 = settingRepository1.GetAttr("StaticThumbnailsPFC")
'--------------------------------------------------
' Parameter 1 : (String) "StaticThumbnailsPFC"
' Returned value : (Variant) (Boolean) False
'--------------------------------------------------

Dim bSTR37
bSTR37 = ""
Dim bSTR38
bSTR38 = ""
Dim boolean27
settingRepository1.GetAttrInfo "StaticThumbnailsPFC", bSTR37, bSTR38, boolean27
'--------------------------------------------------
' Parameter 1 : (String) "StaticThumbnailsPFC"
' Parameter 2 : (String) "Default value"
' Parameter 3 : (String) "Unlocked"
' Parameter 4 : (Boolean) False
'--------------------------------------------------

boolean28 = settingRepository1.GetAttr("NeverDisplayGeometryPFC")
'--------------------------------------------------
' Parameter 1 : (String) "NeverDisplayGeometryPFC"
' Returned value : (Variant) (Boolean) False
'--------------------------------------------------

Dim bSTR39
bSTR39 = ""
Dim bSTR40
bSTR40 = ""
Dim boolean29
settingRepository1.GetAttrInfo "NeverDisplayGeometryPFC", bSTR39, bSTR40, boolean29
'--------------------------------------------------
' Parameter 1 : (String) "NeverDisplayGeometryPFC"
' Parameter 2 : (String) "Default value"
' Parameter 3 : (String) "Unlocked"
' Parameter 4 : (Boolean) False
'--------------------------------------------------

End Sub
