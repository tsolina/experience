Language="VBSCRIPT"

Sub CATMain()

Set settingControllers1 = CATIA.SettingControllers

Set settingRepository1 = settingControllers1.Item("CATHgrSettings")

boolean1 = settingRepository1.GetAttr("HgrSwitchToNewCommandSet")
'--------------------------------------------------
' Parameter 1 : (String) "HgrSwitchToNewCommandSet"
' Returned value : (Variant) (Boolean) False
'--------------------------------------------------

Dim bSTR1
bSTR1 = ""
Dim bSTR2
bSTR2 = ""
Dim boolean2
settingRepository1.GetAttrInfo "HgrSwitchToNewCommandSet", bSTR1, bSTR2, boolean2
'--------------------------------------------------
' Parameter 1 : (String) "HgrSwitchToNewCommandSet"
' Parameter 2 : (String) "Default value"
' Parameter 3 : (String) "Unlocked"
' Parameter 4 : (Boolean) False
'--------------------------------------------------

End Sub
