Language="VBSCRIPT"

Sub CATMain()

Set settingControllers1 = CATIA.SettingControllers

Set settingRepository1 = settingControllers1.Item("HvcServantOptionsNewPreferences")

long1 = settingRepository1.GetAttr("AutoUpdate")
'--------------------------------------------------
' Parameter 1 : (String) "AutoUpdate"
' Returned value : (Variant) (Long) 0
'--------------------------------------------------

Dim bSTR1
bSTR1 = ""
Dim bSTR2
bSTR2 = ""
Dim boolean1
settingRepository1.GetAttrInfo "AutoUpdate", bSTR1, bSTR2, boolean1
'--------------------------------------------------
' Parameter 1 : (String) "AutoUpdate"
' Parameter 2 : (String) "Default value"
' Parameter 3 : (String) "Unlocked"
' Parameter 4 : (Boolean) False
'--------------------------------------------------

long2 = settingRepository1.GetAttr("WireframeViewManip")
'--------------------------------------------------
' Parameter 1 : (String) "WireframeViewManip"
' Returned value : (Variant) (Long) 0
'--------------------------------------------------

Dim bSTR3
bSTR3 = ""
Dim bSTR4
bSTR4 = ""
Dim boolean2
settingRepository1.GetAttrInfo "WireframeViewManip", bSTR3, bSTR4, boolean2
'--------------------------------------------------
' Parameter 1 : (String) "WireframeViewManip"
' Parameter 2 : (String) "Default value"
' Parameter 3 : (String) "Unlocked"
' Parameter 4 : (Boolean) False
'--------------------------------------------------

long3 = settingRepository1.GetAttr("HideLabelsViewManip")
'--------------------------------------------------
' Parameter 1 : (String) "HideLabelsViewManip"
' Returned value : (Variant) (Long) 0
'--------------------------------------------------

Dim bSTR5
bSTR5 = ""
Dim bSTR6
bSTR6 = ""
Dim boolean3
settingRepository1.GetAttrInfo "HideLabelsViewManip", bSTR5, bSTR6, boolean3
'--------------------------------------------------
' Parameter 1 : (String) "HideLabelsViewManip"
' Parameter 2 : (String) "Default value"
' Parameter 3 : (String) "Unlocked"
' Parameter 4 : (Boolean) False
'--------------------------------------------------

long4 = settingRepository1.GetAttr("Decimation")
'--------------------------------------------------
' Parameter 1 : (String) "Decimation"
' Returned value : (Variant) (Long) 0
'--------------------------------------------------

Dim bSTR7
bSTR7 = ""
Dim bSTR8
bSTR8 = ""
Dim boolean4
settingRepository1.GetAttrInfo "Decimation", bSTR7, bSTR8, boolean4
'--------------------------------------------------
' Parameter 1 : (String) "Decimation"
' Parameter 2 : (String) "Default value"
' Parameter 3 : (String) "Unlocked"
' Parameter 4 : (Boolean) False
'--------------------------------------------------

long5 = settingRepository1.GetAttr("NormalCompression")
'--------------------------------------------------
' Parameter 1 : (String) "NormalCompression"
' Returned value : (Variant) (Long) 1
'--------------------------------------------------

Dim bSTR9
bSTR9 = ""
Dim bSTR10
bSTR10 = ""
Dim boolean5
settingRepository1.GetAttrInfo "NormalCompression", bSTR9, bSTR10, boolean5
'--------------------------------------------------
' Parameter 1 : (String) "NormalCompression"
' Parameter 2 : (String) "Default value"
' Parameter 3 : (String) "Unlocked"
' Parameter 4 : (Boolean) False
'--------------------------------------------------

long6 = settingRepository1.GetAttr("ElementOrderReduction")
'--------------------------------------------------
' Parameter 1 : (String) "ElementOrderReduction"
' Returned value : (Variant) (Long) 0
'--------------------------------------------------

Dim bSTR11
bSTR11 = ""
Dim bSTR12
bSTR12 = ""
Dim boolean6
settingRepository1.GetAttrInfo "ElementOrderReduction", bSTR11, bSTR12, boolean6
'--------------------------------------------------
' Parameter 1 : (String) "ElementOrderReduction"
' Parameter 2 : (String) "Default value"
' Parameter 3 : (String) "Unlocked"
' Parameter 4 : (Boolean) False
'--------------------------------------------------

long7 = settingRepository1.GetAttr("UseInstancing")
'--------------------------------------------------
' Parameter 1 : (String) "UseInstancing"
' Returned value : (Variant) (Long) 0
'--------------------------------------------------

Dim bSTR13
bSTR13 = ""
Dim bSTR14
bSTR14 = ""
Dim boolean7
settingRepository1.GetAttrInfo "UseInstancing", bSTR13, bSTR14, boolean7
'--------------------------------------------------
' Parameter 1 : (String) "UseInstancing"
' Parameter 2 : (String) "Default value"
' Parameter 3 : (String) "Unlocked"
' Parameter 4 : (Boolean) False
'--------------------------------------------------

long8 = settingRepository1.GetAttr("AvoidCache")
'--------------------------------------------------
' Parameter 1 : (String) "AvoidCache"
' Returned value : (Variant) (Long) 0
'--------------------------------------------------

Dim bSTR15
bSTR15 = ""
Dim bSTR16
bSTR16 = ""
Dim boolean8
settingRepository1.GetAttrInfo "AvoidCache", bSTR15, bSTR16, boolean8
'--------------------------------------------------
' Parameter 1 : (String) "AvoidCache"
' Parameter 2 : (String) "Default value"
' Parameter 3 : (String) "Unlocked"
' Parameter 4 : (Boolean) False
'--------------------------------------------------

long9 = settingRepository1.GetAttr("LocalMachine")
'--------------------------------------------------
' Parameter 1 : (String) "LocalMachine"
' Returned value : (Variant) (Long) 1
'--------------------------------------------------

Dim bSTR17
bSTR17 = ""
Dim bSTR18
bSTR18 = ""
Dim boolean9
settingRepository1.GetAttrInfo "LocalMachine", bSTR17, bSTR18, boolean9
'--------------------------------------------------
' Parameter 1 : (String) "LocalMachine"
' Parameter 2 : (String) "Default value"
' Parameter 3 : (String) "Unlocked"
' Parameter 4 : (Boolean) False
'--------------------------------------------------

long10 = settingRepository1.GetAttr("UseCloudVizualization")
'--------------------------------------------------
' Parameter 1 : (String) "UseCloudVizualization"
' Returned value : (Variant) (Long) 0
'--------------------------------------------------

Dim bSTR19
bSTR19 = ""
Dim bSTR20
bSTR20 = ""
Dim boolean10
settingRepository1.GetAttrInfo "UseCloudVizualization", bSTR19, bSTR20, boolean10
'--------------------------------------------------
' Parameter 1 : (String) "UseCloudVizualization"
' Parameter 2 : (String) "Default value"
' Parameter 3 : (String) "Unlocked"
' Parameter 4 : (Boolean) False
'--------------------------------------------------

long11 = settingRepository1.GetAttr("DomainDecomposition")
'--------------------------------------------------
' Parameter 1 : (String) "DomainDecomposition"
' Returned value : (Variant) (Long) 2
'--------------------------------------------------

Dim bSTR21
bSTR21 = ""
Dim bSTR22
bSTR22 = ""
Dim boolean11
settingRepository1.GetAttrInfo "DomainDecomposition", bSTR21, bSTR22, boolean11
'--------------------------------------------------
' Parameter 1 : (String) "DomainDecomposition"
' Parameter 2 : (String) "Default value"
' Parameter 3 : (String) "Unlocked"
' Parameter 4 : (Boolean) False
'--------------------------------------------------

long12 = settingRepository1.GetAttr("FieldCache")
'--------------------------------------------------
' Parameter 1 : (String) "FieldCache"
' Returned value : (Variant) (Long) 0
'--------------------------------------------------

Dim bSTR23
bSTR23 = ""
Dim bSTR24
bSTR24 = ""
Dim boolean12
settingRepository1.GetAttrInfo "FieldCache", bSTR23, bSTR24, boolean12
'--------------------------------------------------
' Parameter 1 : (String) "FieldCache"
' Parameter 2 : (String) "Default value"
' Parameter 3 : (String) "Unlocked"
' Parameter 4 : (Boolean) False
'--------------------------------------------------

long13 = settingRepository1.GetAttr("ResultsStorageWarning")
'--------------------------------------------------
' Parameter 1 : (String) "ResultsStorageWarning"
' Returned value : (Variant) (Long) 1
'--------------------------------------------------

Dim bSTR25
bSTR25 = ""
Dim bSTR26
bSTR26 = ""
Dim boolean13
settingRepository1.GetAttrInfo "ResultsStorageWarning", bSTR25, bSTR26, boolean13
'--------------------------------------------------
' Parameter 1 : (String) "ResultsStorageWarning"
' Parameter 2 : (String) "Default value"
' Parameter 3 : (String) "Unlocked"
' Parameter 4 : (Boolean) False
'--------------------------------------------------

long14 = settingRepository1.GetAttr("ShowVisuSelectionModeUI")
'--------------------------------------------------
' Parameter 1 : (String) "ShowVisuSelectionModeUI"
' Returned value : (Variant) (Long) 1
'--------------------------------------------------

Dim bSTR27
bSTR27 = ""
Dim bSTR28
bSTR28 = ""
Dim boolean14
settingRepository1.GetAttrInfo "ShowVisuSelectionModeUI", bSTR27, bSTR28, boolean14
'--------------------------------------------------
' Parameter 1 : (String) "ShowVisuSelectionModeUI"
' Parameter 2 : (String) "Default value"
' Parameter 3 : (String) "Unlocked"
' Parameter 4 : (Boolean) False
'--------------------------------------------------

long15 = settingRepository1.GetAttr("DecimationValue")
'--------------------------------------------------
' Parameter 1 : (String) "DecimationValue"
' Returned value : (Variant) (Long) 1
'--------------------------------------------------

Dim bSTR29
bSTR29 = ""
Dim bSTR30
bSTR30 = ""
Dim boolean15
settingRepository1.GetAttrInfo "DecimationValue", bSTR29, bSTR30, boolean15
'--------------------------------------------------
' Parameter 1 : (String) "DecimationValue"
' Parameter 2 : (String) "Default value"
' Parameter 3 : (String) "Unlocked"
' Parameter 4 : (Boolean) False
'--------------------------------------------------

long16 = settingRepository1.GetAttr("LocalExecutionMaxNbCores")
'--------------------------------------------------
' Parameter 1 : (String) "LocalExecutionMaxNbCores"
' Returned value : (Variant) (Long) 1
'--------------------------------------------------

Dim bSTR31
bSTR31 = ""
Dim bSTR32
bSTR32 = ""
Dim boolean16
settingRepository1.GetAttrInfo "LocalExecutionMaxNbCores", bSTR31, bSTR32, boolean16
'--------------------------------------------------
' Parameter 1 : (String) "LocalExecutionMaxNbCores"
' Parameter 2 : (String) "Default value"
' Parameter 3 : (String) "Unlocked"
' Parameter 4 : (Boolean) False
'--------------------------------------------------

long17 = settingRepository1.GetAttr("ServantCores")
'--------------------------------------------------
' Parameter 1 : (String) "ServantCores"
' Returned value : (Variant) (Long) 4
'--------------------------------------------------

Dim bSTR33
bSTR33 = ""
Dim bSTR34
bSTR34 = ""
Dim boolean17
settingRepository1.GetAttrInfo "ServantCores", bSTR33, bSTR34, boolean17
'--------------------------------------------------
' Parameter 1 : (String) "ServantCores"
' Parameter 2 : (String) "Default value"
' Parameter 3 : (String) "Unlocked"
' Parameter 4 : (Boolean) False
'--------------------------------------------------

long18 = settingRepository1.GetAttr("RemoteServantCores")
'--------------------------------------------------
' Parameter 1 : (String) "RemoteServantCores"
' Returned value : (Variant) (Long) 4
'--------------------------------------------------

Dim bSTR35
bSTR35 = ""
Dim bSTR36
bSTR36 = ""
Dim boolean18
settingRepository1.GetAttrInfo "RemoteServantCores", bSTR35, bSTR36, boolean18
'--------------------------------------------------
' Parameter 1 : (String) "RemoteServantCores"
' Parameter 2 : (String) "Default value"
' Parameter 3 : (String) "Unlocked"
' Parameter 4 : (Boolean) False
'--------------------------------------------------

bSTR37 = settingRepository1.GetAttr("StationNameForCloudBatchExecution")
'--------------------------------------------------
' Parameter 1 : (String) "StationNameForCloudBatchExecution"
' Returned value : (Variant) (String) ""
'--------------------------------------------------

Dim bSTR38
bSTR38 = ""
Dim bSTR39
bSTR39 = ""
Dim boolean19
settingRepository1.GetAttrInfo "StationNameForCloudBatchExecution", bSTR38, bSTR39, boolean19
'--------------------------------------------------
' Parameter 1 : (String) "StationNameForCloudBatchExecution"
' Parameter 2 : (String) "Default value"
' Parameter 3 : (String) "Unlocked"
' Parameter 4 : (Boolean) False
'--------------------------------------------------

bSTR40 = settingRepository1.GetAttr("StationNameForCloudSimulationExecution")
'--------------------------------------------------
' Parameter 1 : (String) "StationNameForCloudSimulationExecution"
' Returned value : (Variant) (String) ""
'--------------------------------------------------

Dim bSTR41
bSTR41 = ""
Dim bSTR42
bSTR42 = ""
Dim boolean20
settingRepository1.GetAttrInfo "StationNameForCloudSimulationExecution", bSTR41, bSTR42, boolean20
'--------------------------------------------------
' Parameter 1 : (String) "StationNameForCloudSimulationExecution"
' Parameter 2 : (String) "Default value"
' Parameter 3 : (String) "Unlocked"
' Parameter 4 : (Boolean) False
'--------------------------------------------------

End Sub
