Language="VBSCRIPT"

Sub CATMain()

Set settingControllers1 = CATIA.SettingControllers

Set settingRepository1 = settingControllers1.Item("PLMEditorColor")

uLong1 = settingRepository1.GetAttr("LiveValidationVisibilityOptionsHideInstances")
'--------------------------------------------------
' Parameter 1 : (String) "LiveValidationVisibilityOptionsHideInstances"
' Returned value : (Variant) (Unsigned Long) 0
'--------------------------------------------------

Dim bSTR1
bSTR1 = ""
Dim bSTR2
bSTR2 = ""
Dim boolean1
settingRepository1.GetAttrInfo "LiveValidationVisibilityOptionsHideInstances", bSTR1, bSTR2, boolean1
'--------------------------------------------------
' Parameter 1 : (String) "LiveValidationVisibilityOptionsHideInstances"
' Parameter 2 : (String) "Default value"
' Parameter 3 : (String) "Unlocked"
' Parameter 4 : (Boolean) False
'--------------------------------------------------

uLong2 = settingRepository1.GetAttr("LiveValidationVisibilityOptionsHidePorts")
'--------------------------------------------------
' Parameter 1 : (String) "LiveValidationVisibilityOptionsHidePorts"
' Returned value : (Variant) (Unsigned Long) 0
'--------------------------------------------------

Dim bSTR3
bSTR3 = ""
Dim bSTR4
bSTR4 = ""
Dim boolean2
settingRepository1.GetAttrInfo "LiveValidationVisibilityOptionsHidePorts", bSTR3, bSTR4, boolean2
'--------------------------------------------------
' Parameter 1 : (String) "LiveValidationVisibilityOptionsHidePorts"
' Parameter 2 : (String) "Default value"
' Parameter 3 : (String) "Unlocked"
' Parameter 4 : (Boolean) False
'--------------------------------------------------

uLong3 = settingRepository1.GetAttr("LiveValidationVisibilityOptionsHideConnections")
'--------------------------------------------------
' Parameter 1 : (String) "LiveValidationVisibilityOptionsHideConnections"
' Returned value : (Variant) (Unsigned Long) 0
'--------------------------------------------------

Dim bSTR5
bSTR5 = ""
Dim bSTR6
bSTR6 = ""
Dim boolean3
settingRepository1.GetAttrInfo "LiveValidationVisibilityOptionsHideConnections", bSTR5, bSTR6, boolean3
'--------------------------------------------------
' Parameter 1 : (String) "LiveValidationVisibilityOptionsHideConnections"
' Parameter 2 : (String) "Default value"
' Parameter 3 : (String) "Unlocked"
' Parameter 4 : (Boolean) False
'--------------------------------------------------

End Sub
