Language="VBSCRIPT"

Sub CATMain()

Set settingControllers1 = CATIA.SettingControllers

Set settingRepository1 = settingControllers1.Item("CkeTolerance")

boolean1 = settingRepository1.GetAttr("defaultTolerance")
'--------------------------------------------------
' Parameter 1 : (String) "defaultTolerance"
' Returned value : (Variant) (Boolean) False
'--------------------------------------------------

Dim bSTR1
bSTR1 = ""
Dim bSTR2
bSTR2 = ""
Dim boolean2
settingRepository1.GetAttrInfo "defaultTolerance", bSTR1, bSTR2, boolean2
'--------------------------------------------------
' Parameter 1 : (String) "defaultTolerance"
' Parameter 2 : (String) "Default value"
' Parameter 3 : (String) "Unlocked"
' Parameter 4 : (Boolean) False
'--------------------------------------------------

double1 = settingRepository1.GetAttr("maxLengthTolerance")
'--------------------------------------------------
' Parameter 1 : (String) "maxLengthTolerance"
' Returned value : (Variant) (Double) 0.000000
'--------------------------------------------------

Dim bSTR3
bSTR3 = ""
Dim bSTR4
bSTR4 = ""
Dim boolean3
settingRepository1.GetAttrInfo "maxLengthTolerance", bSTR3, bSTR4, boolean3
'--------------------------------------------------
' Parameter 1 : (String) "maxLengthTolerance"
' Parameter 2 : (String) "Default value"
' Parameter 3 : (String) "Unlocked"
' Parameter 4 : (Boolean) False
'--------------------------------------------------

double2 = settingRepository1.GetAttr("minLengthTolerance")
'--------------------------------------------------
' Parameter 1 : (String) "minLengthTolerance"
' Returned value : (Variant) (Double) 0.000000
'--------------------------------------------------

Dim bSTR5
bSTR5 = ""
Dim bSTR6
bSTR6 = ""
Dim boolean4
settingRepository1.GetAttrInfo "minLengthTolerance", bSTR5, bSTR6, boolean4
'--------------------------------------------------
' Parameter 1 : (String) "minLengthTolerance"
' Parameter 2 : (String) "Default value"
' Parameter 3 : (String) "Unlocked"
' Parameter 4 : (Boolean) False
'--------------------------------------------------

double3 = settingRepository1.GetAttr("maxAngleTolerance")
'--------------------------------------------------
' Parameter 1 : (String) "maxAngleTolerance"
' Returned value : (Variant) (Double) 0.000000
'--------------------------------------------------

Dim bSTR7
bSTR7 = ""
Dim bSTR8
bSTR8 = ""
Dim boolean5
settingRepository1.GetAttrInfo "maxAngleTolerance", bSTR7, bSTR8, boolean5
'--------------------------------------------------
' Parameter 1 : (String) "maxAngleTolerance"
' Parameter 2 : (String) "Default value"
' Parameter 3 : (String) "Unlocked"
' Parameter 4 : (Boolean) False
'--------------------------------------------------

double4 = settingRepository1.GetAttr("minAngleTolerance")
'--------------------------------------------------
' Parameter 1 : (String) "minAngleTolerance"
' Returned value : (Variant) (Double) 0.000000
'--------------------------------------------------

Dim bSTR9
bSTR9 = ""
Dim bSTR10
bSTR10 = ""
Dim boolean6
settingRepository1.GetAttrInfo "minAngleTolerance", bSTR9, bSTR10, boolean6
'--------------------------------------------------
' Parameter 1 : (String) "minAngleTolerance"
' Parameter 2 : (String) "Default value"
' Parameter 3 : (String) "Unlocked"
' Parameter 4 : (Boolean) False
'--------------------------------------------------

End Sub
