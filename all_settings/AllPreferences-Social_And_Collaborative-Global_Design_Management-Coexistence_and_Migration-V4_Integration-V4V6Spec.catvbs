Language="VBSCRIPT"

Sub CATMain()

Set settingControllers1 = CATIA.SettingControllers

Set settingRepository1 = settingControllers1.Item("SpecV4")

long1 = settingRepository1.GetAttr("Step_Update")
'--------------------------------------------------
' Parameter 1 : (String) "Step_Update"
' Returned value : (Variant) (Long) 262144
'--------------------------------------------------

Dim bSTR1
bSTR1 = ""
Dim bSTR2
bSTR2 = ""
Dim boolean1
settingRepository1.GetAttrInfo "Step_Update", bSTR1, bSTR2, boolean1
'--------------------------------------------------
' Parameter 1 : (String) "Step_Update"
' Parameter 2 : (String) "Default value"
' Parameter 3 : (String) "Unlocked"
' Parameter 4 : (Boolean) False
'--------------------------------------------------

long2 = settingRepository1.GetAttr("DraftConeMode")
'--------------------------------------------------
' Parameter 1 : (String) "DraftConeMode"
' Returned value : (Variant) (Long) 0
'--------------------------------------------------

Dim bSTR3
bSTR3 = ""
Dim bSTR4
bSTR4 = ""
Dim boolean2
settingRepository1.GetAttrInfo "DraftConeMode", bSTR3, bSTR4, boolean2
'--------------------------------------------------
' Parameter 1 : (String) "DraftConeMode"
' Parameter 2 : (String) "Default value"
' Parameter 3 : (String) "Unlocked"
' Parameter 4 : (Boolean) False
'--------------------------------------------------

End Sub
