Language="VBSCRIPT"

Sub CATMain()

Set settingControllers1 = CATIA.SettingControllers

Set settingRepository1 = settingControllers1.Item("AssemblyDesignImport")

long1 = settingRepository1.GetAttr("BrokenCstsFbdiMode")
'--------------------------------------------------
' Parameter 1 : (String) "BrokenCstsFbdiMode"
' Returned value : (Variant) (Long) 0
'--------------------------------------------------

Dim bSTR1
bSTR1 = ""
Dim bSTR2
bSTR2 = ""
Dim boolean1
settingRepository1.GetAttrInfo "BrokenCstsFbdiMode", bSTR1, bSTR2, boolean1
'--------------------------------------------------
' Parameter 1 : (String) "BrokenCstsFbdiMode"
' Parameter 2 : (String) "Default value"
' Parameter 3 : (String) "Unlocked"
' Parameter 4 : (Boolean) False
'--------------------------------------------------

long2 = settingRepository1.GetAttr("AssemblyFeatureFbdiMode")
'--------------------------------------------------
' Parameter 1 : (String) "AssemblyFeatureFbdiMode"
' Returned value : (Variant) (Long) 1
'--------------------------------------------------

Dim bSTR3
bSTR3 = ""
Dim bSTR4
bSTR4 = ""
Dim boolean2
settingRepository1.GetAttrInfo "AssemblyFeatureFbdiMode", bSTR3, bSTR4, boolean2
'--------------------------------------------------
' Parameter 1 : (String) "AssemblyFeatureFbdiMode"
' Parameter 2 : (String) "Default value"
' Parameter 3 : (String) "Unlocked"
' Parameter 4 : (Boolean) False
'--------------------------------------------------

boolean3 = settingRepository1.GetAttr("AsmSymFbdiActivateStructAssocMode")
'--------------------------------------------------
' Parameter 1 : (String) "AsmSymFbdiActivateStructAssocMode"
' Returned value : (Variant) (Boolean) False
'--------------------------------------------------

Dim bSTR5
bSTR5 = ""
Dim bSTR6
bSTR6 = ""
Dim boolean4
settingRepository1.GetAttrInfo "AsmSymFbdiActivateStructAssocMode", bSTR5, bSTR6, boolean4
'--------------------------------------------------
' Parameter 1 : (String) "AsmSymFbdiActivateStructAssocMode"
' Parameter 2 : (String) "Default value"
' Parameter 3 : (String) "Unlocked"
' Parameter 4 : (Boolean) False
'--------------------------------------------------

boolean5 = settingRepository1.GetAttr("AsmSymFbdiAutoSolveStructDiffMode")
'--------------------------------------------------
' Parameter 1 : (String) "AsmSymFbdiAutoSolveStructDiffMode"
' Returned value : (Variant) (Boolean) False
'--------------------------------------------------

Dim bSTR7
bSTR7 = ""
Dim bSTR8
bSTR8 = ""
Dim boolean6
settingRepository1.GetAttrInfo "AsmSymFbdiAutoSolveStructDiffMode", bSTR7, bSTR8, boolean6
'--------------------------------------------------
' Parameter 1 : (String) "AsmSymFbdiAutoSolveStructDiffMode"
' Parameter 2 : (String) "Default value"
' Parameter 3 : (String) "Unlocked"
' Parameter 4 : (Boolean) False
'--------------------------------------------------

End Sub
