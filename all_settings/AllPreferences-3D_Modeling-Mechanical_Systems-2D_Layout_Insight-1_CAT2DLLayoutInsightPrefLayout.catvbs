Language="VBSCRIPT"

Sub CATMain()

Set settingControllers1 = CATIA.SettingControllers

Set settingRepository1 = settingControllers1.Item("CAT2DLToolsOptions")

boolean1 = settingRepository1.GetAttr("HideWhenStartWkb")
'--------------------------------------------------
' Parameter 1 : (String) "HideWhenStartWkb"
' Returned value : (Variant) (Boolean) True
'--------------------------------------------------

Dim bSTR1
bSTR1 = ""
Dim bSTR2
bSTR2 = ""
Dim boolean2
settingRepository1.GetAttrInfo "HideWhenStartWkb", bSTR1, bSTR2, boolean2
'--------------------------------------------------
' Parameter 1 : (String) "HideWhenStartWkb"
' Parameter 2 : (String) "Default value"
' Parameter 3 : (String) "Unlocked"
' Parameter 4 : (Boolean) False
'--------------------------------------------------

boolean3 = settingRepository1.GetAttr("RenderStylePerObject")
'--------------------------------------------------
' Parameter 1 : (String) "RenderStylePerObject"
' Returned value : (Variant) (Boolean) False
'--------------------------------------------------

Dim bSTR3
bSTR3 = ""
Dim bSTR4
bSTR4 = ""
Dim boolean4
settingRepository1.GetAttrInfo "RenderStylePerObject", bSTR3, bSTR4, boolean4
'--------------------------------------------------
' Parameter 1 : (String) "RenderStylePerObject"
' Parameter 2 : (String) "Default value"
' Parameter 3 : (String) "Unlocked"
' Parameter 4 : (Boolean) False
'--------------------------------------------------

boolean5 = settingRepository1.GetAttr("TileWindow")
'--------------------------------------------------
' Parameter 1 : (String) "TileWindow"
' Returned value : (Variant) (Boolean) False
'--------------------------------------------------

Dim bSTR5
bSTR5 = ""
Dim bSTR6
bSTR6 = ""
Dim boolean6
settingRepository1.GetAttrInfo "TileWindow", bSTR5, bSTR6, boolean6
'--------------------------------------------------
' Parameter 1 : (String) "TileWindow"
' Parameter 2 : (String) "Default value"
' Parameter 3 : (String) "Unlocked"
' Parameter 4 : (Boolean) False
'--------------------------------------------------

boolean7 = settingRepository1.GetAttr("CAT2DLFitAllInSheetOpt")
'--------------------------------------------------
' Parameter 1 : (String) "CAT2DLFitAllInSheetOpt"
' Returned value : (Variant) (Boolean) True
'--------------------------------------------------

Dim bSTR7
bSTR7 = ""
Dim bSTR8
bSTR8 = ""
Dim boolean8
settingRepository1.GetAttrInfo "CAT2DLFitAllInSheetOpt", bSTR7, bSTR8, boolean8
'--------------------------------------------------
' Parameter 1 : (String) "CAT2DLFitAllInSheetOpt"
' Parameter 2 : (String) "Default value"
' Parameter 3 : (String) "Unlocked"
' Parameter 4 : (Boolean) False
'--------------------------------------------------

boolean9 = settingRepository1.GetAttr("ForceRenderStyleOnLayoutViewer")
'--------------------------------------------------
' Parameter 1 : (String) "ForceRenderStyleOnLayoutViewer"
' Returned value : (Variant) (Boolean) False
'--------------------------------------------------

Dim bSTR9
bSTR9 = ""
Dim bSTR10
bSTR10 = ""
Dim boolean10
settingRepository1.GetAttrInfo "ForceRenderStyleOnLayoutViewer", bSTR9, bSTR10, boolean10
'--------------------------------------------------
' Parameter 1 : (String) "ForceRenderStyleOnLayoutViewer"
' Parameter 2 : (String) "Default value"
' Parameter 3 : (String) "Unlocked"
' Parameter 4 : (Boolean) False
'--------------------------------------------------

bSTR11 = settingRepository1.GetAttr("standard")
'--------------------------------------------------
' Parameter 1 : (String) "standard"
' Returned value : (Variant) (String) "ISO"
'--------------------------------------------------

Dim bSTR12
bSTR12 = ""
Dim bSTR13
bSTR13 = ""
Dim boolean11
settingRepository1.GetAttrInfo "standard", bSTR12, bSTR13, boolean11
'--------------------------------------------------
' Parameter 1 : (String) "standard"
' Parameter 2 : (String) "Default value"
' Parameter 3 : (String) "Unlocked"
' Parameter 4 : (Boolean) False
'--------------------------------------------------

long1 = settingRepository1.GetAttr("RenderStyle")
'--------------------------------------------------
' Parameter 1 : (String) "RenderStyle"
' Returned value : (Variant) (Long) 3
'--------------------------------------------------

Dim bSTR14
bSTR14 = ""
Dim bSTR15
bSTR15 = ""
Dim boolean12
settingRepository1.GetAttrInfo "RenderStyle", bSTR14, bSTR15, boolean12
'--------------------------------------------------
' Parameter 1 : (String) "RenderStyle"
' Parameter 2 : (String) "Default value"
' Parameter 3 : (String) "Unlocked"
' Parameter 4 : (Boolean) False
'--------------------------------------------------

long2 = settingRepository1.GetAttr("RenderStyle")
'--------------------------------------------------
' Parameter 1 : (String) "RenderStyle"
' Returned value : (Variant) (Long) 3
'--------------------------------------------------

Dim bSTR16
bSTR16 = ""
Dim bSTR17
bSTR17 = ""
Dim boolean13
settingRepository1.GetAttrInfo "RenderStyle", bSTR16, bSTR17, boolean13
'--------------------------------------------------
' Parameter 1 : (String) "RenderStyle"
' Parameter 2 : (String) "Default value"
' Parameter 3 : (String) "Unlocked"
' Parameter 4 : (Boolean) False
'--------------------------------------------------

long3 = settingRepository1.GetAttr("RenderStyle")
'--------------------------------------------------
' Parameter 1 : (String) "RenderStyle"
' Returned value : (Variant) (Long) 3
'--------------------------------------------------

Dim bSTR18
bSTR18 = ""
Dim bSTR19
bSTR19 = ""
Dim boolean14
settingRepository1.GetAttrInfo "RenderStyle", bSTR18, bSTR19, boolean14
'--------------------------------------------------
' Parameter 1 : (String) "RenderStyle"
' Parameter 2 : (String) "Default value"
' Parameter 3 : (String) "Unlocked"
' Parameter 4 : (Boolean) False
'--------------------------------------------------

End Sub
