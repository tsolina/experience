Language="VBSCRIPT"

Sub CATMain()

Set settingControllers1 = CATIA.SettingControllers

Set settingRepository1 = settingControllers1.Item("V4V5Space")

long1 = settingRepository1.GetAttr("SegmState")
'--------------------------------------------------
' Parameter 1 : (String) "SegmState"
' Returned value : (Variant) (Long) 0
'--------------------------------------------------

Dim bSTR1
bSTR1 = ""
Dim bSTR2
bSTR2 = ""
Dim boolean1
settingRepository1.GetAttrInfo "SegmState", bSTR1, bSTR2, boolean1
'--------------------------------------------------
' Parameter 1 : (String) "SegmState"
' Parameter 2 : (String) "Default value"
' Parameter 3 : (String) "Unlocked"
' Parameter 4 : (Boolean) False
'--------------------------------------------------

long2 = settingRepository1.GetAttr("DetailsModeUsual")
'--------------------------------------------------
' Parameter 1 : (String) "DetailsModeUsual"
' Returned value : (Variant) (Long) 1
'--------------------------------------------------

Dim bSTR3
bSTR3 = ""
Dim bSTR4
bSTR4 = ""
Dim boolean2
settingRepository1.GetAttrInfo "DetailsModeUsual", bSTR3, bSTR4, boolean2
'--------------------------------------------------
' Parameter 1 : (String) "DetailsModeUsual"
' Parameter 2 : (String) "Default value"
' Parameter 3 : (String) "Unlocked"
' Parameter 4 : (Boolean) False
'--------------------------------------------------

long3 = settingRepository1.GetAttr("DetailsModeExplode")
'--------------------------------------------------
' Parameter 1 : (String) "DetailsModeExplode"
' Returned value : (Variant) (Long) 0
'--------------------------------------------------

Dim bSTR5
bSTR5 = ""
Dim bSTR6
bSTR6 = ""
Dim boolean3
settingRepository1.GetAttrInfo "DetailsModeExplode", bSTR5, bSTR6, boolean3
'--------------------------------------------------
' Parameter 1 : (String) "DetailsModeExplode"
' Parameter 2 : (String) "Default value"
' Parameter 3 : (String) "Unlocked"
' Parameter 4 : (Boolean) False
'--------------------------------------------------

long4 = settingRepository1.GetAttr("DetailsModeWireframe")
'--------------------------------------------------
' Parameter 1 : (String) "DetailsModeWireframe"
' Returned value : (Variant) (Long) 0
'--------------------------------------------------

Dim bSTR7
bSTR7 = ""
Dim bSTR8
bSTR8 = ""
Dim boolean4
settingRepository1.GetAttrInfo "DetailsModeWireframe", bSTR7, bSTR8, boolean4
'--------------------------------------------------
' Parameter 1 : (String) "DetailsModeWireframe"
' Parameter 2 : (String) "Default value"
' Parameter 3 : (String) "Unlocked"
' Parameter 4 : (Boolean) False
'--------------------------------------------------

bSTR9 = settingRepository1.GetAttr("SolidMUState")
'--------------------------------------------------
' Parameter 1 : (String) "SolidMUState"
' Returned value : (Variant) (String) "CGR"
'--------------------------------------------------

Dim bSTR10
bSTR10 = ""
Dim bSTR11
bSTR11 = ""
Dim boolean5
settingRepository1.GetAttrInfo "SolidMUState", bSTR10, bSTR11, boolean5
'--------------------------------------------------
' Parameter 1 : (String) "SolidMUState"
' Parameter 2 : (String) "Default value"
' Parameter 3 : (String) "Unlocked"
' Parameter 4 : (Boolean) False
'--------------------------------------------------

long5 = settingRepository1.GetAttr("TextMigrState")
'--------------------------------------------------
' Parameter 1 : (String) "TextMigrState"
' Returned value : (Variant) (Long) 0
'--------------------------------------------------

Dim bSTR12
bSTR12 = ""
Dim bSTR13
bSTR13 = ""
Dim boolean6
settingRepository1.GetAttrInfo "TextMigrState", bSTR12, bSTR13, boolean6
'--------------------------------------------------
' Parameter 1 : (String) "TextMigrState"
' Parameter 2 : (String) "Default value"
' Parameter 3 : (String) "Unlocked"
' Parameter 4 : (Boolean) False
'--------------------------------------------------

long6 = settingRepository1.GetAttr("GapState")
'--------------------------------------------------
' Parameter 1 : (String) "GapState"
' Returned value : (Variant) (Long) 1
'--------------------------------------------------

Dim bSTR14
bSTR14 = ""
Dim bSTR15
bSTR15 = ""
Dim boolean7
settingRepository1.GetAttrInfo "GapState", bSTR14, bSTR15, boolean7
'--------------------------------------------------
' Parameter 1 : (String) "GapState"
' Parameter 2 : (String) "Default value"
' Parameter 3 : (String) "Unlocked"
' Parameter 4 : (Boolean) False
'--------------------------------------------------

float1 = settingRepository1.GetAttr("GapSize")
'--------------------------------------------------
' Parameter 1 : (String) "GapSize"
' Returned value : (Variant) (Float) 0.001000
'--------------------------------------------------

Dim bSTR16
bSTR16 = ""
Dim bSTR17
bSTR17 = ""
Dim boolean8
settingRepository1.GetAttrInfo "GapSize", bSTR16, bSTR17, boolean8
'--------------------------------------------------
' Parameter 1 : (String) "GapSize"
' Parameter 2 : (String) "Default value"
' Parameter 3 : (String) "Unlocked"
' Parameter 4 : (Boolean) False
'--------------------------------------------------

long7 = settingRepository1.GetAttr("CurvImprovState")
'--------------------------------------------------
' Parameter 1 : (String) "CurvImprovState"
' Returned value : (Variant) (Long) 1
'--------------------------------------------------

Dim bSTR18
bSTR18 = ""
Dim bSTR19
bSTR19 = ""
Dim boolean9
settingRepository1.GetAttrInfo "CurvImprovState", bSTR18, bSTR19, boolean9
'--------------------------------------------------
' Parameter 1 : (String) "CurvImprovState"
' Parameter 2 : (String) "Default value"
' Parameter 3 : (String) "Unlocked"
' Parameter 4 : (Boolean) False
'--------------------------------------------------

float2 = settingRepository1.GetAttr("CurvImprovSize")
'--------------------------------------------------
' Parameter 1 : (String) "CurvImprovSize"
' Returned value : (Variant) (Float) 0.001000
'--------------------------------------------------

Dim bSTR20
bSTR20 = ""
Dim bSTR21
bSTR21 = ""
Dim boolean10
settingRepository1.GetAttrInfo "CurvImprovSize", bSTR20, bSTR21, boolean10
'--------------------------------------------------
' Parameter 1 : (String) "CurvImprovSize"
' Parameter 2 : (String) "Default value"
' Parameter 3 : (String) "Unlocked"
' Parameter 4 : (Boolean) False
'--------------------------------------------------

End Sub
