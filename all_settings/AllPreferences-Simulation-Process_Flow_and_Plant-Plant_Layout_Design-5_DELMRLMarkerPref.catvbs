Language="VBSCRIPT"

Sub CATMain()

Set settingControllers1 = CATIA.SettingControllers

Set settingRepository1 = settingControllers1.Item("DELMrlMarkerSettings")

bSTR1 = settingRepository1.GetAttr("Location")
'--------------------------------------------------
' Parameter 1 : (String) "Location"
' Returned value : (Variant) (String) "${CATTemp}"
'--------------------------------------------------

Dim bSTR2
bSTR2 = ""
Dim bSTR3
bSTR3 = ""
Dim boolean1
settingRepository1.GetAttrInfo "Location", bSTR2, bSTR3, boolean1
'--------------------------------------------------
' Parameter 1 : (String) "Location"
' Parameter 2 : (String) "Default value"
' Parameter 3 : (String) "Unlocked"
' Parameter 4 : (Boolean) False
'--------------------------------------------------

End Sub
