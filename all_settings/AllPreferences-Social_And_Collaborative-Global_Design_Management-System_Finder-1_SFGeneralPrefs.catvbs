Language="VBSCRIPT"

Sub CATMain()

Set settingControllers1 = CATIA.SettingControllers

Set settingRepository1 = settingControllers1.Item("RFLPNavigator")

long1 = settingRepository1.GetAttr("ExploreInNewWindow")
'--------------------------------------------------
' Parameter 1 : (String) "ExploreInNewWindow"
' Returned value : (Variant) (Long) 1
'--------------------------------------------------

Dim bSTR1
bSTR1 = ""
Dim bSTR2
bSTR2 = ""
Dim boolean1
settingRepository1.GetAttrInfo "ExploreInNewWindow", bSTR1, bSTR2, boolean1
'--------------------------------------------------
' Parameter 1 : (String) "ExploreInNewWindow"
' Parameter 2 : (String) "Default value"
' Parameter 3 : (String) "Unlocked"
' Parameter 4 : (Boolean) False
'--------------------------------------------------

uLong1 = settingRepository1.GetAttr("SmartOpen")
'--------------------------------------------------
' Parameter 1 : (String) "SmartOpen"
' Returned value : (Variant) (Unsigned Long) 2
'--------------------------------------------------

Dim bSTR3
bSTR3 = ""
Dim bSTR4
bSTR4 = ""
Dim boolean2
settingRepository1.GetAttrInfo "SmartOpen", bSTR3, bSTR4, boolean2
'--------------------------------------------------
' Parameter 1 : (String) "SmartOpen"
' Parameter 2 : (String) "Default value"
' Parameter 3 : (String) "Unlocked"
' Parameter 4 : (Boolean) False
'--------------------------------------------------

long2 = settingRepository1.GetAttr("ExploreWithCompletion")
'--------------------------------------------------
' Parameter 1 : (String) "ExploreWithCompletion"
' Returned value : (Variant) (Long) 1
'--------------------------------------------------

Dim bSTR5
bSTR5 = ""
Dim bSTR6
bSTR6 = ""
Dim boolean3
settingRepository1.GetAttrInfo "ExploreWithCompletion", bSTR5, bSTR6, boolean3
'--------------------------------------------------
' Parameter 1 : (String) "ExploreWithCompletion"
' Parameter 2 : (String) "Default value"
' Parameter 3 : (String) "Unlocked"
' Parameter 4 : (Boolean) False
'--------------------------------------------------

long3 = settingRepository1.GetAttr("ExploreWithParent")
'--------------------------------------------------
' Parameter 1 : (String) "ExploreWithParent"
' Returned value : (Variant) (Long) 0
'--------------------------------------------------

Dim bSTR7
bSTR7 = ""
Dim bSTR8
bSTR8 = ""
Dim boolean4
settingRepository1.GetAttrInfo "ExploreWithParent", bSTR7, bSTR8, boolean4
'--------------------------------------------------
' Parameter 1 : (String) "ExploreWithParent"
' Parameter 2 : (String) "Default value"
' Parameter 3 : (String) "Unlocked"
' Parameter 4 : (Boolean) False
'--------------------------------------------------

long4 = settingRepository1.GetAttr("ExploreInContext")
'--------------------------------------------------
' Parameter 1 : (String) "ExploreInContext"
' Returned value : (Variant) (Long) 0
'--------------------------------------------------

Dim bSTR9
bSTR9 = ""
Dim bSTR10
bSTR10 = ""
Dim boolean5
settingRepository1.GetAttrInfo "ExploreInContext", bSTR9, bSTR10, boolean5
'--------------------------------------------------
' Parameter 1 : (String) "ExploreInContext"
' Parameter 2 : (String) "Default value"
' Parameter 3 : (String) "Unlocked"
' Parameter 4 : (Boolean) False
'--------------------------------------------------

Set settingRepository2 = settingControllers1.Item("VPMNavigator")

long5 = settingRepository2.GetAttr("DisplayThumbnailsExploreParents")
'--------------------------------------------------
' Parameter 1 : (String) "DisplayThumbnailsExploreParents"
' Returned value : (Variant) (Long) 1
'--------------------------------------------------

Dim bSTR11
bSTR11 = ""
Dim bSTR12
bSTR12 = ""
Dim boolean6
settingRepository2.GetAttrInfo "DisplayThumbnailsExploreParents", bSTR11, bSTR12, boolean6
'--------------------------------------------------
' Parameter 1 : (String) "DisplayThumbnailsExploreParents"
' Parameter 2 : (String) "Default value"
' Parameter 3 : (String) "Unlocked"
' Parameter 4 : (Boolean) False
'--------------------------------------------------

long6 = settingRepository2.GetAttr("DisplayTilesExploreParents")
'--------------------------------------------------
' Parameter 1 : (String) "DisplayTilesExploreParents"
' Returned value : (Variant) (Long) 1
'--------------------------------------------------

Dim bSTR13
bSTR13 = ""
Dim bSTR14
bSTR14 = ""
Dim boolean7
settingRepository2.GetAttrInfo "DisplayTilesExploreParents", bSTR13, bSTR14, boolean7
'--------------------------------------------------
' Parameter 1 : (String) "DisplayTilesExploreParents"
' Parameter 2 : (String) "Default value"
' Parameter 3 : (String) "Unlocked"
' Parameter 4 : (Boolean) False
'--------------------------------------------------

End Sub
