Language="VBSCRIPT"

Sub CATMain()

Set settingControllers1 = CATIA.SettingControllers

Set settingRepository1 = settingControllers1.Item("3DPlay_InAppSettings")

boolean1 = settingRepository1.GetAttr("3DPlay_JOYSTICK_RUN_MODE")
'--------------------------------------------------
' Parameter 1 : (String) "3DPlay_JOYSTICK_RUN_MODE"
' Returned value : (Variant) (Boolean) False
'--------------------------------------------------

Dim bSTR1
bSTR1 = ""
Dim bSTR2
bSTR2 = ""
Dim boolean2
settingRepository1.GetAttrInfo "3DPlay_JOYSTICK_RUN_MODE", bSTR1, bSTR2, boolean2
'--------------------------------------------------
' Parameter 1 : (String) "3DPlay_JOYSTICK_RUN_MODE"
' Parameter 2 : (String) "Default value"
' Parameter 3 : (String) "Unlocked"
' Parameter 4 : (Boolean) False
'--------------------------------------------------

boolean3 = settingRepository1.GetAttr("3DPlay_JOYSTICK_MODEL_ARROW")
'--------------------------------------------------
' Parameter 1 : (String) "3DPlay_JOYSTICK_MODEL_ARROW"
' Returned value : (Variant) (Boolean) True
'--------------------------------------------------

Dim bSTR3
bSTR3 = ""
Dim bSTR4
bSTR4 = ""
Dim boolean4
settingRepository1.GetAttrInfo "3DPlay_JOYSTICK_MODEL_ARROW", bSTR3, bSTR4, boolean4
'--------------------------------------------------
' Parameter 1 : (String) "3DPlay_JOYSTICK_MODEL_ARROW"
' Parameter 2 : (String) "Default value"
' Parameter 3 : (String) "Unlocked"
' Parameter 4 : (Boolean) False
'--------------------------------------------------

float1 = settingRepository1.GetAttr("3DPlay_LEFT_JOYSTICK_SENSIBILITY")
'--------------------------------------------------
' Parameter 1 : (String) "3DPlay_LEFT_JOYSTICK_SENSIBILITY"
' Returned value : (Variant) (Float) 0.500000
'--------------------------------------------------

Dim bSTR5
bSTR5 = ""
Dim bSTR6
bSTR6 = ""
Dim boolean5
settingRepository1.GetAttrInfo "3DPlay_LEFT_JOYSTICK_SENSIBILITY", bSTR5, bSTR6, boolean5
'--------------------------------------------------
' Parameter 1 : (String) "3DPlay_LEFT_JOYSTICK_SENSIBILITY"
' Parameter 2 : (String) "Default value"
' Parameter 3 : (String) "Unlocked"
' Parameter 4 : (Boolean) False
'--------------------------------------------------

float2 = settingRepository1.GetAttr("3DPlay_RIGHT_JOYSTICK_SENSIBILITY")
'--------------------------------------------------
' Parameter 1 : (String) "3DPlay_RIGHT_JOYSTICK_SENSIBILITY"
' Returned value : (Variant) (Float) 0.500000
'--------------------------------------------------

Dim bSTR7
bSTR7 = ""
Dim bSTR8
bSTR8 = ""
Dim boolean6
settingRepository1.GetAttrInfo "3DPlay_RIGHT_JOYSTICK_SENSIBILITY", bSTR7, bSTR8, boolean6
'--------------------------------------------------
' Parameter 1 : (String) "3DPlay_RIGHT_JOYSTICK_SENSIBILITY"
' Parameter 2 : (String) "Default value"
' Parameter 3 : (String) "Unlocked"
' Parameter 4 : (Boolean) False
'--------------------------------------------------

End Sub
