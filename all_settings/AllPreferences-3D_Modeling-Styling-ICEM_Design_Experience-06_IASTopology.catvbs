Language="VBSCRIPT"

Sub CATMain()

Set settingControllers1 = CATIA.SettingControllers

Set settingRepository1 = settingControllers1.Item("ShapeDesignGeneral")

double1 = settingRepository1.GetAttr("TMMergingDistance")
'--------------------------------------------------
' Parameter 1 : (String) "TMMergingDistance"
' Returned value : (Variant) (Double) 0.001000
'--------------------------------------------------

Dim bSTR1
bSTR1 = ""
Dim bSTR2
bSTR2 = ""
Dim boolean1
settingRepository1.GetAttrInfo "TMMergingDistance", bSTR1, bSTR2, boolean1
'--------------------------------------------------
' Parameter 1 : (String) "TMMergingDistance"
' Parameter 2 : (String) "Default value"
' Parameter 3 : (String) "Unlocked"
' Parameter 4 : (Boolean) False
'--------------------------------------------------

End Sub
