Language="VBSCRIPT"

Sub CATMain()

Set settingControllers1 = CATIA.SettingControllers

Set settingRepository1 = settingControllers1.Item("ELEditorToolsOptions")

uLong1 = settingRepository1.GetAttr("SchApplicativeSpecTreeMode")
'--------------------------------------------------
' Parameter 1 : (String) "SchApplicativeSpecTreeMode"
' Returned value : (Variant) (Unsigned Long) 1
'--------------------------------------------------

Dim bSTR1
bSTR1 = ""
Dim bSTR2
bSTR2 = ""
Dim boolean1
settingRepository1.GetAttrInfo "SchApplicativeSpecTreeMode", bSTR1, bSTR2, boolean1
'--------------------------------------------------
' Parameter 1 : (String) "SchApplicativeSpecTreeMode"
' Parameter 2 : (String) "Default value"
' Parameter 3 : (String) "Unlocked"
' Parameter 4 : (Boolean) False
'--------------------------------------------------

uLong2 = settingRepository1.GetAttr("SchApplicativeSpecTreeCableMode")
'--------------------------------------------------
' Parameter 1 : (String) "SchApplicativeSpecTreeCableMode"
' Returned value : (Variant) (Unsigned Long) 1
'--------------------------------------------------

Dim bSTR3
bSTR3 = ""
Dim bSTR4
bSTR4 = ""
Dim boolean2
settingRepository1.GetAttrInfo "SchApplicativeSpecTreeCableMode", bSTR3, bSTR4, boolean2
'--------------------------------------------------
' Parameter 1 : (String) "SchApplicativeSpecTreeCableMode"
' Parameter 2 : (String) "Default value"
' Parameter 3 : (String) "Unlocked"
' Parameter 4 : (Boolean) False
'--------------------------------------------------

End Sub
