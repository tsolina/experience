Language="VBSCRIPT"

Sub CATMain()

Set settingControllers1 = CATIA.SettingControllers

Set settingRepository1 = settingControllers1.Item("PLMEditorColor")

uLong1 = settingRepository1.GetAttr("TooltipDisplayName")
'--------------------------------------------------
' Parameter 1 : (String) "TooltipDisplayName"
' Returned value : (Variant) (Unsigned Long) 1
'--------------------------------------------------

Dim bSTR1
bSTR1 = ""
Dim bSTR2
bSTR2 = ""
Dim boolean1
settingRepository1.GetAttrInfo "TooltipDisplayName", bSTR1, bSTR2, boolean1
'--------------------------------------------------
' Parameter 1 : (String) "TooltipDisplayName"
' Parameter 2 : (String) "Default value"
' Parameter 3 : (String) "Unlocked"
' Parameter 4 : (Boolean) False
'--------------------------------------------------

uLong2 = settingRepository1.GetAttr("TooltipFctLogDisplayAttr")
'--------------------------------------------------
' Parameter 1 : (String) "TooltipFctLogDisplayAttr"
' Returned value : (Variant) (Unsigned Long) 0
'--------------------------------------------------

Dim bSTR3
bSTR3 = ""
Dim bSTR4
bSTR4 = ""
Dim boolean2
settingRepository1.GetAttrInfo "TooltipFctLogDisplayAttr", bSTR3, bSTR4, boolean2
'--------------------------------------------------
' Parameter 1 : (String) "TooltipFctLogDisplayAttr"
' Parameter 2 : (String) "Default value"
' Parameter 3 : (String) "Unlocked"
' Parameter 4 : (Boolean) False
'--------------------------------------------------

uLong3 = settingRepository1.GetAttr("TooltipRequirementDisplayAttr")
'--------------------------------------------------
' Parameter 1 : (String) "TooltipRequirementDisplayAttr"
' Returned value : (Variant) (Unsigned Long) 0
'--------------------------------------------------

Dim bSTR5
bSTR5 = ""
Dim bSTR6
bSTR6 = ""
Dim boolean3
settingRepository1.GetAttrInfo "TooltipRequirementDisplayAttr", bSTR5, bSTR6, boolean3
'--------------------------------------------------
' Parameter 1 : (String) "TooltipRequirementDisplayAttr"
' Parameter 2 : (String) "Default value"
' Parameter 3 : (String) "Unlocked"
' Parameter 4 : (Boolean) False
'--------------------------------------------------

End Sub
