Language="VBSCRIPT"

Sub CATMain()

Set settingControllers1 = CATIA.SettingControllers

Set settingRepository1 = settingControllers1.Item("PreferencesSearchOptions")

boolean1 = settingRepository1.GetAttr("TreeFiltering")
'--------------------------------------------------
' Parameter 1 : (String) "TreeFiltering"
' Returned value : (Variant) (Boolean) False
'--------------------------------------------------

Dim bSTR1
bSTR1 = ""
Dim bSTR2
bSTR2 = ""
Dim boolean2
settingRepository1.GetAttrInfo "TreeFiltering", bSTR1, bSTR2, boolean2
'--------------------------------------------------
' Parameter 1 : (String) "TreeFiltering"
' Parameter 2 : (String) "Default value"
' Parameter 3 : (String) "Unlocked"
' Parameter 4 : (Boolean) False
'--------------------------------------------------

boolean3 = settingRepository1.GetAttr("IndexGenerationInProgress")
'--------------------------------------------------
' Parameter 1 : (String) "IndexGenerationInProgress"
' Returned value : (Variant) (Boolean) False
'--------------------------------------------------

Dim bSTR3
bSTR3 = ""
Dim bSTR4
bSTR4 = ""
Dim boolean4
settingRepository1.GetAttrInfo "IndexGenerationInProgress", bSTR3, bSTR4, boolean4
'--------------------------------------------------
' Parameter 1 : (String) "IndexGenerationInProgress"
' Parameter 2 : (String) "Default value"
' Parameter 3 : (String) "Unlocked"
' Parameter 4 : (Boolean) False
'--------------------------------------------------

long1 = settingRepository1.GetAttr("PageExpandOptions")
'--------------------------------------------------
' Parameter 1 : (String) "PageExpandOptions"
' Returned value : (Variant) (Long) 1
'--------------------------------------------------

Dim bSTR5
bSTR5 = ""
Dim bSTR6
bSTR6 = ""
Dim boolean5
settingRepository1.GetAttrInfo "PageExpandOptions", bSTR5, bSTR6, boolean5
'--------------------------------------------------
' Parameter 1 : (String) "PageExpandOptions"
' Parameter 2 : (String) "Default value"
' Parameter 3 : (String) "Unlocked"
' Parameter 4 : (Boolean) False
'--------------------------------------------------

long2 = settingRepository1.GetAttr("NumberOfPagesToExpand")
'--------------------------------------------------
' Parameter 1 : (String) "NumberOfPagesToExpand"
' Returned value : (Variant) (Long) 1
'--------------------------------------------------

Dim bSTR7
bSTR7 = ""
Dim bSTR8
bSTR8 = ""
Dim boolean6
settingRepository1.GetAttrInfo "NumberOfPagesToExpand", bSTR7, bSTR8, boolean6
'--------------------------------------------------
' Parameter 1 : (String) "NumberOfPagesToExpand"
' Parameter 2 : (String) "Default value"
' Parameter 3 : (String) "Unlocked"
' Parameter 4 : (Boolean) False
'--------------------------------------------------

End Sub
