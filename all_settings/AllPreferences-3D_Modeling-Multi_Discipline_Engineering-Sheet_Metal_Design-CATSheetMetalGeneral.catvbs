Language="VBSCRIPT"

Sub CATMain()

Set settingControllers1 = CATIA.SettingControllers

Set settingRepository1 = settingControllers1.Item("SheetMetalDesign")

long1 = settingRepository1.GetAttr("SHM_Import_View")
'--------------------------------------------------
' Parameter 1 : (String) "SHM_Import_View"
' Returned value : (Variant) (Long) 0
'--------------------------------------------------

Dim bSTR1
bSTR1 = ""
Dim bSTR2
bSTR2 = ""
Dim boolean1
settingRepository1.GetAttrInfo "SHM_Import_View", bSTR1, bSTR2, boolean1
'--------------------------------------------------
' Parameter 1 : (String) "SHM_Import_View"
' Parameter 2 : (String) "Default value"
' Parameter 3 : (String) "Unlocked"
' Parameter 4 : (Boolean) False
'--------------------------------------------------

End Sub
