Language="VBSCRIPT"

Sub CATMain()

Set settingControllers1 = CATIA.SettingControllers

Set settingRepository1 = settingControllers1.Item("DELPLMWorkInstructionSettings")

long1 = settingRepository1.GetAttr("WorkInstructionDisplayMode")
'--------------------------------------------------
' Parameter 1 : (String) "WorkInstructionDisplayMode"
' Returned value : (Variant) (Long) 0
'--------------------------------------------------

Dim bSTR1
bSTR1 = ""
Dim bSTR2
bSTR2 = ""
Dim boolean1
settingRepository1.GetAttrInfo "WorkInstructionDisplayMode", bSTR1, bSTR2, boolean1
'--------------------------------------------------
' Parameter 1 : (String) "WorkInstructionDisplayMode"
' Parameter 2 : (String) "Default value"
' Parameter 3 : (String) "Unlocked"
' Parameter 4 : (Boolean) False
'--------------------------------------------------

long2 = settingRepository1.GetAttr("ActivateViewsOnOperationSelection")
'--------------------------------------------------
' Parameter 1 : (String) "ActivateViewsOnOperationSelection"
' Returned value : (Variant) (Long) 0
'--------------------------------------------------

Dim bSTR3
bSTR3 = ""
Dim bSTR4
bSTR4 = ""
Dim boolean2
settingRepository1.GetAttrInfo "ActivateViewsOnOperationSelection", bSTR3, bSTR4, boolean2
'--------------------------------------------------
' Parameter 1 : (String) "ActivateViewsOnOperationSelection"
' Parameter 2 : (String) "Default value"
' Parameter 3 : (String) "Unlocked"
' Parameter 4 : (Boolean) False
'--------------------------------------------------

long3 = settingRepository1.GetAttr("AutoActivateFirstSysOrWpOrParOperOption")
'--------------------------------------------------
' Parameter 1 : (String) "AutoActivateFirstSysOrWpOrParOperOption"
' Returned value : (Variant) (Long) 0
'--------------------------------------------------

Dim bSTR5
bSTR5 = ""
Dim bSTR6
bSTR6 = ""
Dim boolean3
settingRepository1.GetAttrInfo "AutoActivateFirstSysOrWpOrParOperOption", bSTR5, bSTR6, boolean3
'--------------------------------------------------
' Parameter 1 : (String) "AutoActivateFirstSysOrWpOrParOperOption"
' Parameter 2 : (String) "Default value"
' Parameter 3 : (String) "Unlocked"
' Parameter 4 : (Boolean) False
'--------------------------------------------------

long4 = settingRepository1.GetAttr("SystemSelectionUIDisplayThumbNailsOption")
'--------------------------------------------------
' Parameter 1 : (String) "SystemSelectionUIDisplayThumbNailsOption"
' Returned value : (Variant) (Long) 0
'--------------------------------------------------

Dim bSTR7
bSTR7 = ""
Dim bSTR8
bSTR8 = ""
Dim boolean4
settingRepository1.GetAttrInfo "SystemSelectionUIDisplayThumbNailsOption", bSTR7, bSTR8, boolean4
'--------------------------------------------------
' Parameter 1 : (String) "SystemSelectionUIDisplayThumbNailsOption"
' Parameter 2 : (String) "Default value"
' Parameter 3 : (String) "Unlocked"
' Parameter 4 : (Boolean) False
'--------------------------------------------------

bSTR9 = settingRepository1.GetAttr("VisualRepForOrientationViewer")
'--------------------------------------------------
' Parameter 1 : (String) "VisualRepForOrientationViewer"
' Returned value : (Variant) (String) "startup\WorkInstructions\LightWeightRepresentation\WKIOrientationGraphic.cgr"
'--------------------------------------------------

Dim bSTR10
bSTR10 = ""
Dim bSTR11
bSTR11 = ""
Dim boolean5
settingRepository1.GetAttrInfo "VisualRepForOrientationViewer", bSTR10, bSTR11, boolean5
'--------------------------------------------------
' Parameter 1 : (String) "VisualRepForOrientationViewer"
' Parameter 2 : (String) "Default value"
' Parameter 3 : (String) "Unlocked"
' Parameter 4 : (Boolean) False
'--------------------------------------------------

boolean6 = settingRepository1.GetAttr("AuthoringAreaDisplayMode")
'--------------------------------------------------
' Parameter 1 : (String) "AuthoringAreaDisplayMode"
' Returned value : (Variant) (Boolean) False
'--------------------------------------------------

Dim bSTR12
bSTR12 = ""
Dim bSTR13
bSTR13 = ""
Dim boolean7
settingRepository1.GetAttrInfo "AuthoringAreaDisplayMode", bSTR12, bSTR13, boolean7
'--------------------------------------------------
' Parameter 1 : (String) "AuthoringAreaDisplayMode"
' Parameter 2 : (String) "Default value"
' Parameter 3 : (String) "Unlocked"
' Parameter 4 : (Boolean) False
'--------------------------------------------------

uLong1 = settingRepository1.GetAttr("AuthoringAreaDisplayRatio")
'--------------------------------------------------
' Parameter 1 : (String) "AuthoringAreaDisplayRatio"
' Returned value : (Variant) (Unsigned Long) 2
'--------------------------------------------------

Dim bSTR14
bSTR14 = ""
Dim bSTR15
bSTR15 = ""
Dim boolean8
settingRepository1.GetAttrInfo "AuthoringAreaDisplayRatio", bSTR14, bSTR15, boolean8
'--------------------------------------------------
' Parameter 1 : (String) "AuthoringAreaDisplayRatio"
' Parameter 2 : (String) "Default value"
' Parameter 3 : (String) "Unlocked"
' Parameter 4 : (Boolean) False
'--------------------------------------------------

Dim arrayOfVariantOfULong1
arrayOfVariantOfULong1 = settingRepository1.GetAttrArray("AuthoringAreaColor")
'--------------------------------------------------
' Parameter 1 : (String) "AuthoringAreaColor"
' Returned value : (Array) 
'    Array[0] : (Variant) (Unsigned Long) 0
'    Array[1] : (Variant) (Unsigned Long) 0
'    Array[2] : (Variant) (Unsigned Long) 255
'--------------------------------------------------

Dim bSTR16
bSTR16 = ""
Dim bSTR17
bSTR17 = ""
Dim boolean9
settingRepository1.GetAttrInfo "AuthoringAreaColor", bSTR16, bSTR17, boolean9
'--------------------------------------------------
' Parameter 1 : (String) "AuthoringAreaColor"
' Parameter 2 : (String) "Default value"
' Parameter 3 : (String) "Unlocked"
' Parameter 4 : (Boolean) False
'--------------------------------------------------

long5 = settingRepository1.GetAttr("AuthoringAreaLineWidth")
'--------------------------------------------------
' Parameter 1 : (String) "AuthoringAreaLineWidth"
' Returned value : (Variant) (Long) 3
'--------------------------------------------------

Dim bSTR18
bSTR18 = ""
Dim bSTR19
bSTR19 = ""
Dim boolean10
settingRepository1.GetAttrInfo "AuthoringAreaLineWidth", bSTR18, bSTR19, boolean10
'--------------------------------------------------
' Parameter 1 : (String) "AuthoringAreaLineWidth"
' Parameter 2 : (String) "Default value"
' Parameter 3 : (String) "Unlocked"
' Parameter 4 : (Boolean) False
'--------------------------------------------------

long6 = settingRepository1.GetAttr("AuthoringAreaLineType")
'--------------------------------------------------
' Parameter 1 : (String) "AuthoringAreaLineType"
' Returned value : (Variant) (Long) 3
'--------------------------------------------------

Dim bSTR20
bSTR20 = ""
Dim bSTR21
bSTR21 = ""
Dim boolean11
settingRepository1.GetAttrInfo "AuthoringAreaLineType", bSTR20, bSTR21, boolean11
'--------------------------------------------------
' Parameter 1 : (String) "AuthoringAreaLineType"
' Parameter 2 : (String) "Default value"
' Parameter 3 : (String) "Unlocked"
' Parameter 4 : (Boolean) False
'--------------------------------------------------

long7 = settingRepository1.GetAttr("WorkInstructionOpSequenceMode")
'--------------------------------------------------
' Parameter 1 : (String) "WorkInstructionOpSequenceMode"
' Returned value : (Variant) (Long) 0
'--------------------------------------------------

Dim bSTR22
bSTR22 = ""
Dim bSTR23
bSTR23 = ""
Dim boolean12
settingRepository1.GetAttrInfo "WorkInstructionOpSequenceMode", bSTR22, bSTR23, boolean12
'--------------------------------------------------
' Parameter 1 : (String) "WorkInstructionOpSequenceMode"
' Parameter 2 : (String) "Default value"
' Parameter 3 : (String) "Unlocked"
' Parameter 4 : (Boolean) False
'--------------------------------------------------

long8 = settingRepository1.GetAttr("WorkInstructionOpThumbnailMode")
'--------------------------------------------------
' Parameter 1 : (String) "WorkInstructionOpThumbnailMode"
' Returned value : (Variant) (Long) 0
'--------------------------------------------------

Dim bSTR24
bSTR24 = ""
Dim bSTR25
bSTR25 = ""
Dim boolean13
settingRepository1.GetAttrInfo "WorkInstructionOpThumbnailMode", bSTR24, bSTR25, boolean13
'--------------------------------------------------
' Parameter 1 : (String) "WorkInstructionOpThumbnailMode"
' Parameter 2 : (String) "Default value"
' Parameter 3 : (String) "Unlocked"
' Parameter 4 : (Boolean) False
'--------------------------------------------------

End Sub
