Language="VBSCRIPT"

Sub CATMain()

Set settingControllers1 = CATIA.SettingControllers

Set settingRepository1 = settingControllers1.Item("ELEditorToolsOptions")

uLong1 = settingRepository1.GetAttr("SchPortAddOrDeleteChkButton")
'--------------------------------------------------
' Parameter 1 : (String) "SchPortAddOrDeleteChkButton"
' Returned value : (Variant) (Unsigned Long) 1
'--------------------------------------------------

Dim bSTR1
bSTR1 = ""
Dim bSTR2
bSTR2 = ""
Dim boolean1
settingRepository1.GetAttrInfo "SchPortAddOrDeleteChkButton", bSTR1, bSTR2, boolean1
'--------------------------------------------------
' Parameter 1 : (String) "SchPortAddOrDeleteChkButton"
' Parameter 2 : (String) "Default value"
' Parameter 3 : (String) "Unlocked"
' Parameter 4 : (Boolean) False
'--------------------------------------------------

uLong2 = settingRepository1.GetAttr("Schematic_AllowCompSelectionDuringRoute_Elec")
'--------------------------------------------------
' Parameter 1 : (String) "Schematic_AllowCompSelectionDuringRoute_Elec"
' Returned value : (Variant) (Unsigned Long) 1
'--------------------------------------------------

Dim bSTR3
bSTR3 = ""
Dim bSTR4
bSTR4 = ""
Dim boolean2
settingRepository1.GetAttrInfo "Schematic_AllowCompSelectionDuringRoute_Elec", bSTR3, bSTR4, boolean2
'--------------------------------------------------
' Parameter 1 : (String) "Schematic_AllowCompSelectionDuringRoute_Elec"
' Parameter 2 : (String) "Default value"
' Parameter 3 : (String) "Unlocked"
' Parameter 4 : (Boolean) False
'--------------------------------------------------

uLong3 = settingRepository1.GetAttr("Schematic_AllowPortCreationDuringRoute_Elec")
'--------------------------------------------------
' Parameter 1 : (String) "Schematic_AllowPortCreationDuringRoute_Elec"
' Returned value : (Variant) (Unsigned Long) 1
'--------------------------------------------------

Dim bSTR5
bSTR5 = ""
Dim bSTR6
bSTR6 = ""
Dim boolean3
settingRepository1.GetAttrInfo "Schematic_AllowPortCreationDuringRoute_Elec", bSTR5, bSTR6, boolean3
'--------------------------------------------------
' Parameter 1 : (String) "Schematic_AllowPortCreationDuringRoute_Elec"
' Parameter 2 : (String) "Default value"
' Parameter 3 : (String) "Unlocked"
' Parameter 4 : (Boolean) False
'--------------------------------------------------

End Sub
